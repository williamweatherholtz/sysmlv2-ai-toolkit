// Verification of the five serve-discipline SystemRequirements (sprint 393, chartered by d0182).
// Each SR was EXERCISED against the live system or INSPECTED against the shipped code, and the result
// records what is TRUE — two of the five FAIL, because their machinery waits on the D0185 typed-contract
// trigger, and an honest fail beats an absent edge (D0098: gates enforce truth, not completeness).
// Added as new items per D0108 (the SRs are claudeOpus5's; a non-owner ADDS, never edits).
package ServeDisciplineVerification {
    private import EngineElement::*;
    private import EngineVerification::*;
    private import EngineRelationships::*;

    verification srServeApproveGateHumanV1 : Test { :>> id = "dc997eeb-ad92-4695-ac95-c4dda2c4c7ef"; :>> title = "The launch approval is a named human's attestation, bound to the exact reviewed plan"; :>> createdAt = "2026-08-21"; :>> createdBy = "claudeFable5"; :>> method = VerificationMethod::demo; :>> procedureText = "Exercised live against a scratch serve instance (sprint 393). GET /api/agent/plan renders the parsed action, target, executability and EXACT prompt, plus planHash - the identity of what the human reviewed. Execution refusals, all observed as real HTTP responses: approved=true with NO approver -> refused naming srServeApproveGateHuman; approved_by=claudeFable5 (an AI actor) -> refused (not a registered Person - kind refused before any role could matter); a stale plan_hash -> refused (the route changed since review, fresh approval required - clause 3); a missing plan_hash -> refused. The approval is RECORDED: every launched run's machine-local record and tracked run summary now carry approvedBy, and the summary's procedureText names the approver, the process, and the spawn HEAD - the authored fact naming actor, time, and routed target the SR demands. RESIDUALS, stated: (a) the Person check binds to the registered-Person set directly rather than through attestation-policy.toml's per-class declaration - equivalent today (the policy's human-only classes and the Person registry agree), a seam if a policy ever declares a narrower class; (b) a directed-critique stream (non-launch) checks the approver identically but records the approval only in its output artifacts' provenance, not as a separate authored fact - the launch path is the fully-conformant one."; }
    part srServeApproveGateHumanV1R1 : TestResult { :>> id = "591c58ce-1766-4b9a-b833-3c8f9cc047b3"; :>> outcome = VerdictKind::pass; :>> judgedAgainst = "174eeab"; :>> judgedAt = "2026-08-21"; :>> judgedBy = "claudeFable5"; }
    #Verify dependency from srServeApproveGateHumanV1 to srServeApproveGateHuman;

    verification srServeSingleSpawnPointV1 : Test { :>> id = "8109a3fc-213f-4ce5-abdc-8ae08aaed676"; :>> title = "Exactly one agent-spawn site, asserted by an automated check"; :>> createdAt = "2026-08-21"; :>> createdBy = "claudeFable5"; :>> method = VerificationMethod::test; :>> procedureText = "The agent is spawned from exactly one site (serve.rs api_agent_stream, the claude -p invocation); the only other .spawn() calls in the crate are git plumbing in orient.rs with a different command shape entirely. The SR's required automated check exists as unit test single_agent_spawn_point: it counts the agent invocation's distinctive argument marker across serve.rs, main.rs, launcher.rs, orient.rs and deck.rs and FAILS THE GATE on any second spawn path - a bypass now breaks a test rather than passing unnoticed. Typed-target clause: the spawn is reachable only through the routed AgentReq whose launch targets must satisfy is_launchable (a non-declared target is rejected with the valid set referenced), which is routing-level rather than type-level unrepresentability - the launch-target VALUE is still a string internally; stated as the residual."; }
    part srServeSingleSpawnPointV1R1 : TestResult { :>> id = "d9dd12d4-2a0e-4a8b-b6ed-1aa844a7038d"; :>> outcome = VerdictKind::pass; :>> judgedAgainst = "174eeab"; :>> judgedAt = "2026-08-21"; :>> judgedBy = "claudeFable5"; }
    #Verify dependency from srServeSingleSpawnPointV1 to srServeSingleSpawnPoint;

    verification srServeBoundedReachableContextV1 : Test { :>> id = "4e28d336-f1d7-48e9-940c-6194c234a1b7"; :>> title = "Declared inputs only, with the unenforceable reachability bound STATED in every launch record"; :>> createdAt = "2026-08-21"; :>> createdBy = "claudeFable5"; :>> method = VerificationMethod::inspect; :>> procedureText = "Input bound: each launch passes only the routed target's derived prompt - request_plan computes it fresh per request, and no prior-launch state is accumulated (the stream holds no cross-run context; the run id, actor and snapshot are per-launch). Reachability bound: NOT enforceable - the spawned claude -p has repository read access - and the SR's own escape clause requires exactly that this residual be STATED in the launch record rather than implied. It now is: every tracked run summary carries the REACHABILITY RESIDUAL sentence naming what was bounded (declared inputs), what was not (whole-repository reads), and what the enforced control actually is (the post-run whole-tree gate plus unconditional human diff review). The anti-drift property is claimed exactly as broadly as it is enforced, which is the requirement."; }
    part srServeBoundedReachableContextV1R1 : TestResult { :>> id = "fb401b23-3d40-4d41-8511-58985f09202f"; :>> outcome = VerdictKind::pass; :>> judgedAgainst = "174eeab"; :>> judgedAt = "2026-08-21"; :>> judgedBy = "claudeFable5"; }
    #Verify dependency from srServeBoundedReachableContextV1 to srServeBoundedReachableContext;

    verification srServeLaunchContractV1 : Test { :>> id = "418a1a28-7941-441e-b932-203dfbe87b14"; :>> title = "Launchables are model-computed; the output-schema half does not exist yet"; :>> createdAt = "2026-08-21"; :>> createdBy = "claudeFable5"; :>> method = VerificationMethod::inspect; :>> procedureText = "HONEST FAIL, recorded rather than omitted. What holds: the launchable set is computed at request time from the declared model (view::launchables over processes/skills/rules; /api/launchables serves it; a non-declared target is refused with the valid set referenced - no separately-authored launch list exists). What does NOT hold: no declared per-target OUTPUT SCHEMA contract exists, so nothing resolves one, and a schema-less target is still offered for launch - the 'no schema, no launch' clause is unenforced. The remedy is already decided, not missing: D0185 (accepted) makes typed launch/output contracts a TRIGGER-GATED direction, and the launch form's own field text states 'typed fields arrive with D0185's typed contracts'. This result flips when that trigger fires and the contract lands; until then the truthful state is FAIL."; }
    part srServeLaunchContractV1R1 : TestResult { :>> id = "8597564a-c3ef-4d07-b609-349e17ecc574"; :>> outcome = VerdictKind::fail; :>> judgedAgainst = "174eeab"; :>> judgedAt = "2026-08-21"; :>> judgedBy = "claudeFable5"; }
    #Verify dependency from srServeLaunchContractV1 to srServeLaunchContract;

    verification srServeOutputValidationV1 : Test { :>> id = "cbe0db48-fbdb-4749-85c5-6b581aee04e8"; :>> title = "Side effects are gated and reviewed; schema validation and bounded repair do not exist yet"; :>> createdAt = "2026-08-21"; :>> createdBy = "claudeFable5"; :>> method = VerificationMethod::inspect; :>> procedureText = "HONEST FAIL, recorded rather than omitted. What holds (the side-effect half): a run spawns only on a CLEAN tree (single-writer), so its effects are exactly the working-tree diff; the post-run gate runs validate + activation-filtered guards + blocking rules over that diff; a red gate records the run FAILED while the diff still awaits human review UNCONDITIONALLY; the K5 completion check flags a run that changed files but recorded nothing tracked - failed side effects are recorded as facts, never silently discarded. What does NOT hold: there is no declared output schema to validate against (see srServeLaunchContractV1), therefore no validate-and-return-for-repair loop and no bounded retry count - the schema-validation half is unbuilt and waits on the same D0185 trigger. FAIL until the contract machinery lands; the pass criterion is the full loop, not the compensating controls."; }
    part srServeOutputValidationV1R1 : TestResult { :>> id = "5a2d91ef-739d-470f-a65c-32742b13b439"; :>> outcome = VerdictKind::fail; :>> judgedAgainst = "174eeab"; :>> judgedAt = "2026-08-21"; :>> judgedBy = "claudeFable5"; }
    #Verify dependency from srServeOutputValidationV1 to srServeOutputValidation;
    verification srK16OutwardPublishGatedV1 : Test { :>> id = "560fe777-bf66-400e-a1fd-9f1756ab60f5"; :>> title = "The publish boundary proven gated in both directions on the live pipeline"; :>> createdAt = "2026-08-22"; :>> createdBy = "claudeFable5"; :>> method = VerificationMethod::demo; :>> procedureText = "Sprint 409 exercised the requirement's exact claim on the REAL pipeline before the requirement existed (the SR elevates that evidence to a standing contract per D0195 clause 8): NEGATIVE - a deliberately red fixture tagged v0.0.0-gatetest produced gate=failure, build=SKIPPED, zero artifacts, release list unchanged; POSITIVE - a workflow_dispatch smoke produced gate + all three platform builds success with publish correctly skipped absent a tag. The trunk half is srDcGateOnMergedTree's machinery (land + the pre-push behind-check, two-clone-proven in sprint 410)."; }
    part srK16OutwardPublishGatedV1R1 : TestResult { :>> id = "349a1ea2-071e-46ac-8501-87ef2db0f089"; :>> outcome = VerdictKind::pass; :>> judgedAgainst = "cf3f25d"; :>> judgedAt = "2026-08-22"; :>> judgedBy = "claudeFable5"; }
    #Verify dependency from srK16OutwardPublishGatedV1 to srK16OutwardPublishGated;

}
