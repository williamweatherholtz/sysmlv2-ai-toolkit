// Exercise records for 12 SystemRequirements the verification lens reported EXAMINED but never
// EXERCISED (sprint 396). "Exercised" means THE SYSTEM WAS RUN against the requirement - every
// record below cites a run: a live probe, a build both ways (positive + negative control), a guard
// executing at the gate, or this session's own recorded round-trips. The 8 remaining
// never-exercised SRs are build-gated (D0185/D0189/D0190, view-state unchartered) or human-gated
// (srConsoleObligationActionable needs their browser) - each already carries an honest examined
// record naming that. Added per D0108.
package ExerciseVerification {
    private import EngineElement::*;
    private import EngineVerification::*;
    private import EngineRelationships::*;

    verification sr02DecisionRecordX1 : Test { :>> id = "8c15bdd1-b389-4213-b859-a1e7806d4570"; :>> title = "Decision authoring exercised: three decisions round-tripped this session"; :>> createdAt = "2026-08-21"; :>> createdBy = "claudeFable5"; :>> method = VerificationMethod::demo; :>> procedureText = "Run, not read: D0189 (a SCOPE CUT superseding twelve issues and the unstartable frontier items - exactly the statement's 'including scope cuts'), D0190 and D0191 were all authored through keel record decision in this one session, each with rationale enforced by the command's own required flags (D0103); D0191 then round-tripped to accepted through the write API's human sign-off path. #Supersede edges are live model edges consumed by views (the serve-discipline file's corrected->original supersedes were read back through the computed verification lens in sprint 393)."; }
    part sr02DecisionRecordX1R1 : TestResult { :>> id = "798789a3-9384-410d-80ff-dc017969874e"; :>> outcome = VerdictKind::pass; :>> judgedAgainst = "bae0cf6"; :>> judgedAt = "2026-08-21"; :>> judgedBy = "claudeFable5"; }
    #Verify dependency from sr02DecisionRecordX1 to sr02DecisionRecord;

    verification sr05GitNativeX1 : Test { :>> id = "c0dbd30b-84e1-45b5-bc81-b90dbacd586e"; :>> title = "Git-native truth and the SHA causal clock exercised by today's drift cycle"; :>> createdAt = "2026-08-21"; :>> createdBy = "claudeFable5"; :>> method = VerificationMethod::demo; :>> procedureText = "All 432 tracking files are .sysml text in this git repository - validate counts them on every gate. The causal-clock clause was exercised twice today without being asked to: commits moved HEAD, the suspicion computation flagged three reproducible tasks SUSPECT purely from judgedAgainst-SHA movement, and keel reverify --all-drift re-ran their checks and stamped fresh TestResults at the new HEAD (0433ca6, then 2af2ac9). Suspicion computed FROM commit SHAs is the requirement, running live."; }
    part sr05GitNativeX1R1 : TestResult { :>> id = "15427544-758e-40a2-9ab0-e21f429a5e21"; :>> outcome = VerdictKind::pass; :>> judgedAgainst = "bae0cf6"; :>> judgedAt = "2026-08-21"; :>> judgedBy = "claudeFable5"; }
    #Verify dependency from sr05GitNativeX1 to sr05GitNative;

    verification sr06ProcessModelX1 : Test { :>> id = "f7c80b04-648d-4fb9-ad74-be60ce5caca8"; :>> title = "Process definitions are executable model: activation computed from process files, exercised by editing one"; :>> createdAt = "2026-08-21"; :>> createdBy = "claudeFable5"; :>> method = VerificationMethod::demo; :>> procedureText = "Sprint 395 exercised the whole path: adding one assert-constraint line to deploy.sysml changed the COMPUTED activation (the unit's guard set, the hardening lens's enforced count 11 -> 13) with no registry or code edit - the process file IS the executable definition (D0139(D)). The launchable set is computed at request time from .engine/processes (/api/launchables, probed in sprint 394's srServeLaunchContract record), and skills are registered model files the process-skill guard checks on every gate."; }
    part sr06ProcessModelX1R1 : TestResult { :>> id = "5da1e0fe-7bac-497b-8e18-6a41c835d497"; :>> outcome = VerdictKind::pass; :>> judgedAgainst = "bae0cf6"; :>> judgedAt = "2026-08-21"; :>> judgedBy = "claudeFable5"; }
    #Verify dependency from sr06ProcessModelX1 to sr06ProcessModel;

    verification sr07AgentLoopX1 : Test { :>> id = "50086241-f40f-4768-ba42-516426761d47"; :>> title = "The agent loop exercised end to end, including the gate refusing and the loop recovering"; :>> createdAt = "2026-08-21"; :>> createdBy = "claudeFable5"; :>> method = VerificationMethod::demo; :>> procedureText = "This session ran the loop the requirement describes, repeatedly and with a live negative path: orient (computed frontier) -> execute (sprints 391-395) -> validate green -> record -> commit through the pre-commit gate. The gate's teeth were demonstrated on sprint 395's FIRST commit attempt, which the process-change guard REFUSED (process files changed with no co-committed #ProspectiveChange Decision); the loop corrected the record - the D0070 marker on D0191 - rather than bypassing, and the second attempt landed. An AI agent completed every step from CLAUDE.md + the toolchain alone, which is the statement's operative claim."; }
    part sr07AgentLoopX1R1 : TestResult { :>> id = "deea5f41-85c7-472c-b86d-42a755a51f9c"; :>> outcome = VerdictKind::pass; :>> judgedAgainst = "bae0cf6"; :>> judgedAt = "2026-08-21"; :>> judgedBy = "claudeFable5"; }
    #Verify dependency from sr07AgentLoopX1 to sr07AgentLoop;

    verification sr09SelfBuildX1 : Test { :>> id = "1987a64d-9ca8-4009-802f-dcff4faef494"; :>> title = "Self-hosting exercised: the engine's own controls catch the engine's own defects"; :>> createdAt = "2026-08-21"; :>> createdBy = "claudeFable5"; :>> method = VerificationMethod::demo; :>> procedureText = "395 sprints of .tracking history exist and ARE the evidence base this session kept consuming (the frontier, the burndown, the verification lens all compute over it). The sharper exercise is the engine catching itself, live, this week: guard 43's first run caught a missing authored release and a tag/record skew four releases of discipline had missed; the guard-population meta-test caught verification-trace going quiet the moment the campaign emptied it; the duplicate-identity guard caught a decision-number collision with a parallel session. Process correctness evidenced by the tracked history of the process failing loudly and correcting - the statement's own definition."; }
    part sr09SelfBuildX1R1 : TestResult { :>> id = "f33f9093-624a-47ae-b4fe-d2b144025a90"; :>> outcome = VerdictKind::pass; :>> judgedAgainst = "bae0cf6"; :>> judgedAt = "2026-08-21"; :>> judgedBy = "claudeFable5"; }
    #Verify dependency from sr09SelfBuildX1 to sr09SelfBuild;

    verification sr13SpecPinX1 : Test { :>> id = "fc94e549-7681-45a9-8d42-e7e6766e01d6"; :>> title = "The spec pin is real now, verified in both directions"; :>> createdAt = "2026-08-21"; :>> createdBy = "claudeFable5"; :>> method = VerificationMethod::test; :>> procedureText = "HONEST STATE FIRST: until today the embedded digest was the all-zeros not-yet-pinned sentinel, so the divergence check existed and had never verified anything (offline/network-error paths warn-skip by design). Exercised by completing it: the live manifest at the embedded canonical URL was fetched and its SHA-256 (e86a23b3...) pinned as the compile-time constant. POSITIVE: cargo build with SYSML_V2_SPEC_OFFLINE=0 fetches, matches, embeds verified:<sha>. NEGATIVE CONTROL: one flipped hex character -> the build FAILS with the SHA-mismatch message naming expected and actual; restored -> green. CI carries no offline flag, so networked CI builds verify the pin and a moved spec fails the build for review - the statement's exact demand."; }
    part sr13SpecPinX1R1 : TestResult { :>> id = "fd04ce03-48bf-4c45-a49f-718575f21178"; :>> outcome = VerdictKind::pass; :>> judgedAgainst = "bae0cf6"; :>> judgedAt = "2026-08-21"; :>> judgedBy = "claudeFable5"; }
    #Verify dependency from sr13SpecPinX1 to sr13SpecPin;

    verification sr17ServeDirectedNoChatX1 : Test { :>> id = "feefff84-7bfe-4e22-a01e-b666fa82f9fb"; :>> title = "No free-form AI surface: the refusal observed live"; :>> createdAt = "2026-08-21"; :>> createdBy = "claudeFable5"; :>> method = VerificationMethod::demo; :>> procedureText = "Probed live during sprint 393's approve-gate work: an agent-stream request whose action is neither critique nor launch is refused with the error naming this requirement ('the console has no free-form AI surface... every AI action is directed at a named element'). Directed actions produce recorded artifacts by construction: a critique's output contract is severity-carrying Issues through the write API, and a launch produces run records (exercised further by srServeApproveGateHumanV1). No chat surface exists to probe - the absence is the pass, and the refusal is its observable edge."; }
    part sr17ServeDirectedNoChatX1R1 : TestResult { :>> id = "244fa890-b589-42dd-8ecd-6816fb98cad8"; :>> outcome = VerdictKind::pass; :>> judgedAgainst = "bae0cf6"; :>> judgedAt = "2026-08-21"; :>> judgedBy = "claudeFable5"; }
    #Verify dependency from sr17ServeDirectedNoChatX1 to sr17ServeDirectedNoChat;

    verification srConsoleArrivalBoundedX1 : Test { :>> id = "b9ee7892-d2e5-41c3-9d55-4baf9badc528"; :>> title = "Arrival bound exercised: 32 viewpoints, 6 top-level choices"; :>> createdAt = "2026-08-21"; :>> createdBy = "claudeFable5"; :>> method = VerificationMethod::demo; :>> procedureText = "Probed live against the running console: /api/surfaces returns 6 top-level surfaces carrying 32 declared viewpoints - the choice count is the declared grouping's cardinality, a 5x compression that could not hold if viewpoints added choices. Complements sprint 394's structural inspect (srConsoleArrivalBoundedV1) with the running system's actual numbers."; }
    part srConsoleArrivalBoundedX1R1 : TestResult { :>> id = "25c2d980-c3ff-4a95-9270-a263a582a135"; :>> outcome = VerdictKind::pass; :>> judgedAgainst = "bae0cf6"; :>> judgedAt = "2026-08-21"; :>> judgedBy = "claudeFable5"; }
    #Verify dependency from srConsoleArrivalBoundedX1 to srConsoleArrivalBounded;

    verification srConsoleObligationsOnArrivalX1 : Test { :>> id = "7f94d4da-0208-4dec-98ea-9fa4ba685584"; :>> title = "Obligation classes served live, all viewpoint-derived"; :>> createdAt = "2026-08-21"; :>> createdBy = "claudeFable5"; :>> method = VerificationMethod::demo; :>> procedureText = "Probed live: /api/obligations serves 4 obligation classes - acceptancesPendingVP, authorityQueueVP, findingsAwaitingDispositionVP, sittingReviewVP - every one a declared act-surface Viewpoint, none enumerated in page code. The arrival page's obligationBar consumes this on every render before any navigation (sprint 394's inspect covers the rendering half; this is the serving half, running)."; }
    part srConsoleObligationsOnArrivalX1R1 : TestResult { :>> id = "dc92d898-fbf6-4bce-a556-5562aea50782"; :>> outcome = VerdictKind::pass; :>> judgedAgainst = "bae0cf6"; :>> judgedAt = "2026-08-21"; :>> judgedBy = "claudeFable5"; }
    #Verify dependency from srConsoleObligationsOnArrivalX1 to srConsoleObligationsOnArrival;

    verification srDcActorRoleModeledX1 : Test { :>> id = "d1071f0b-3a49-4d84-94ca-483296797f95"; :>> title = "Roles consumed from the model by a guard that runs at every gate"; :>> createdAt = "2026-08-21"; :>> createdBy = "claudeFable5"; :>> method = VerificationMethod::test; :>> procedureText = "The system RUNS against the role data on every gate: the attestation-authority guard (160 attestation records scanned in today's live runs) resolves each attesting actor's kind and role from the model and checks them against attestation-policy.toml's per-class declarations - kind before role. A role held as prose could not be consumed by that predicate; the guard executing is the exercise. (Sprint 394's srDcActorRoleModeledV1 carries the inspect half: the fields and the declared vocabulary.)"; }
    part srDcActorRoleModeledX1R1 : TestResult { :>> id = "039513c0-613f-46d3-a972-dc332239fef6"; :>> outcome = VerdictKind::pass; :>> judgedAgainst = "bae0cf6"; :>> judgedAt = "2026-08-21"; :>> judgedBy = "claudeFable5"; }
    #Verify dependency from srDcActorRoleModeledX1 to srDcActorRoleModeled;

    verification srGovTieredAffordancesX1 : Test { :>> id = "3ffe425e-0bef-4406-9b0c-7904a3626aee"; :>> title = "The tiers fired live and their effect is measured, not assumed"; :>> createdAt = "2026-08-21"; :>> createdBy = "claudeFable5"; :>> method = VerificationMethod::demo; :>> procedureText = "Exercised by this session's own instrumented run: the fire-ledger recorded 458+ hook fires across the tiers (post-edit 104, pre-bash 334, pre-write 5, stop 5) and keel enforcement-report computed the per-event fires/blocks over it - the MEASURED-evidence machinery the statement requires, running on real data. The per-edit tier blocked real unfilled scaffolds this week (scaffold-placeholder on sprint 395's skeleton) and the turn-boundary gate blocked a real dishonest state; neither blocked anything else - blocking clear violations, warning on the rest, which is the graded behavior demanded."; }
    part srGovTieredAffordancesX1R1 : TestResult { :>> id = "123c632a-cde1-498f-933b-fe54df9e738b"; :>> outcome = VerdictKind::pass; :>> judgedAgainst = "bae0cf6"; :>> judgedAt = "2026-08-21"; :>> judgedBy = "claudeFable5"; }
    #Verify dependency from srGovTieredAffordancesX1 to srGovTieredAffordances;

    verification srRelRecordedReleaseX1 : Test { :>> id = "906a4a4d-b204-4a60-9405-fe761b8138ab"; :>> title = "The recorded-release claim now has a predicate that runs - and it caught two defects on its first run"; :>> createdAt = "2026-08-21"; :>> createdBy = "claudeFable5"; :>> method = VerificationMethod::test; :>> procedureText = "Guard 43 (release-recorded, D0191) runs the requirement's reconciliation at every gate: all 5 local tags checked for an authored Release item whose recorded commit matches the tag. Its FIRST run demonstrated both catch paths against real data - v0.1.0 had no Release item at all (backfilled) and v0.2.0's tag sits two housekeeping commits past its recorded commit (an accurate standing warning, the owner's to reconcile). A check that has caught real instances of both defect shapes it exists for is exercised in the strongest sense available."; }
    part srRelRecordedReleaseX1R1 : TestResult { :>> id = "cb379f7b-b81c-4280-b3a9-fddece6dbe2d"; :>> outcome = VerdictKind::pass; :>> judgedAgainst = "bae0cf6"; :>> judgedAt = "2026-08-21"; :>> judgedBy = "claudeFable5"; }
    #Verify dependency from srRelRecordedReleaseX1 to srRelRecordedRelease;
}
