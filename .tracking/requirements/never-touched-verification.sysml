// Verification of the 14 remaining never-examined-never-exercised SystemRequirements (sprint 394).
// Every claim below cites a live probe against the running console (127.0.0.1:7777 / a scratch
// instance), a unit test, gh release data, or a grep of the shipped source - never the SR's own
// rationale. FIVE record FAIL: what is unbuilt is recorded as unbuilt (D0098). Added per D0108.
package NeverTouchedVerification {
    private import EngineElement::*;
    private import EngineVerification::*;
    private import EngineRelationships::*;

    verification srConsoleNavigationDerivedV1 : Test { :>> id = "eb9260d3-262c-4bd5-afb1-7315a74fd785"; :>> title = "Navigation is computed from the Viewpoint registry"; :>> createdAt = "2026-08-21"; :>> createdBy = "claudeFable5"; :>> method = VerificationMethod::demo; :>> procedureText = "Probed live: GET /api/surfaces returns navigation COMPUTED from the declared Viewpoint registry (its own response text names D0154 and states the derivation: top-level choices are the DISTINCT declared surfaces). The console fetches this at render time and its source declares - and grep confirms - NO literal list of surfaces, tabs or sections anywhere in the page (the header comment records that twelve hardcoded tabs were removed for exactly this SR). Declaring a viewpoint with a new surface adds a choice; one on an existing surface does not."; }
    part srConsoleNavigationDerivedV1R1 : TestResult { :>> id = "ba840ca8-6704-4b4f-89b1-9adf1af8f7d2"; :>> outcome = VerdictKind::pass; :>> judgedAgainst = "aeaca42"; :>> judgedAt = "2026-08-21"; :>> judgedBy = "claudeFable5"; }
    #Verify dependency from srConsoleNavigationDerivedV1 to srConsoleNavigationDerived;

    verification srConsoleArrivalBoundedV1 : Test { :>> id = "74bf7bd5-bcfe-4260-96dc-b4b5ddac8f0c"; :>> title = "Top-level choices are a function of declared grouping, not viewpoint count"; :>> createdAt = "2026-08-21"; :>> createdBy = "claudeFable5"; :>> method = VerificationMethod::inspect; :>> procedureText = "The /api/surfaces computation groups by DISTINCT declared `surface` values (probed; the endpoint states it), so N added viewpoints leave the top-level count unchanged unless one names a NEW surface - which is the declared-grouping function the SR demands, not a per-viewpoint tab. Viewpoints declaring no surface appear under one explicit unsurfaced group rather than adding choices. Not re-probed by actually adding a viewpoint (that writes to the registry); the derivation is structural in the endpoint."; }
    part srConsoleArrivalBoundedV1R1 : TestResult { :>> id = "2d3ceb11-cca7-40ef-84bd-7459b2713afd"; :>> outcome = VerdictKind::pass; :>> judgedAgainst = "aeaca42"; :>> judgedAt = "2026-08-21"; :>> judgedBy = "claudeFable5"; }
    #Verify dependency from srConsoleArrivalBoundedV1 to srConsoleArrivalBounded;

    verification srConsoleViewStatusExplicitV1 : Test { :>> id = "89f8676b-eedd-4b6e-8786-3e9f995bf683"; :>> title = "Every rendered view carries a status discriminant, four states distinguishable"; :>> createdAt = "2026-08-21"; :>> createdBy = "claudeFable5"; :>> method = VerificationMethod::test; :>> procedureText = "The server wraps every render in with_status (unit-tested in view_status_tests, including the array-body case: no render path emits content without a status); the page's statusBanner draws each state distinctly, and error paths render FAILURE as failure - the obligations bar's catch branch literally renders 'this is a FAILURE, not nothing owed'. Live responses probed on /api/surfaces, /api/projects and /api/scope all carried viewStatus."; }
    part srConsoleViewStatusExplicitV1R1 : TestResult { :>> id = "cb3c1707-8655-43c2-ab31-5de29214f6eb"; :>> outcome = VerdictKind::pass; :>> judgedAgainst = "aeaca42"; :>> judgedAt = "2026-08-21"; :>> judgedBy = "claudeFable5"; }
    #Verify dependency from srConsoleViewStatusExplicitV1 to srConsoleViewStatusExplicit;

    verification srConsoleObligationsOnArrivalV1 : Test { :>> id = "31b02f8e-72ac-495f-b156-18ba9a6f62e7"; :>> title = "Obligations render on arrival, classes derived from declared act-surface viewpoints"; :>> createdAt = "2026-08-21"; :>> createdBy = "claudeFable5"; :>> method = VerificationMethod::inspect; :>> procedureText = "render() awaits obligationBar() FIRST and prepends it to the arrival view - no navigation act reaches the obligations, they are already there. The class set comes from /api/obligations, whose classes are the declared act-surface viewpoints (the page's own empty-state text says so: declare a viewpoint with surface=act to add one) - derived, not enumerated in page code. A computation failure renders as failure, never as nothing-owed."; }
    part srConsoleObligationsOnArrivalV1R1 : TestResult { :>> id = "977316be-d856-429c-98fe-db262ed59026"; :>> outcome = VerdictKind::pass; :>> judgedAgainst = "aeaca42"; :>> judgedAt = "2026-08-21"; :>> judgedBy = "claudeFable5"; }
    #Verify dependency from srConsoleObligationsOnArrivalV1 to srConsoleObligationsOnArrival;

    verification srConsoleProjectRebindV1 : Test { :>> id = "888803fa-97a5-4c4b-b5e1-c6a1f4e0817d"; :>> title = "The API rebinds projects; the surface shows none of it"; :>> createdAt = "2026-08-21"; :>> createdBy = "claudeFable5"; :>> method = VerificationMethod::inspect; :>> procedureText = "HONEST FAIL. The API half exists and was probed: GET /api/projects returns the bound set with activeProject, and POST /api/project switches in-process without restart (issue178 made it a declared write endpoint). The SURFACE half does not: grep finds ZERO occurrences of 'project' in console.html - no switcher, and the active project is NOT visible at all times (or ever) on the surface, which is a named clause of the SR. Fails on the visibility clause and the surface-switch clause; the parse-failure refusal branch is API-side only."; }
    part srConsoleProjectRebindV1R1 : TestResult { :>> id = "8f8290fa-63b7-45c3-958d-3c397ca988a2"; :>> outcome = VerdictKind::fail; :>> judgedAgainst = "aeaca42"; :>> judgedAt = "2026-08-21"; :>> judgedBy = "claudeFable5"; }
    #Verify dependency from srConsoleProjectRebindV1 to srConsoleProjectRebind;

    verification srConsoleModelScopeResolvedV1 : Test { :>> id = "cf36256d-0406-40af-8768-6258d0974b24"; :>> title = "Scope resolves at the API; the surface never names it"; :>> createdAt = "2026-08-21"; :>> createdBy = "claudeFable5"; :>> method = VerificationMethod::inspect; :>> procedureText = "HONEST FAIL. GET /api/scope resolves an item to a scope and names this repository COINCIDENT (probed) - the resolution machinery exists. But the SR requires the scope in view to be NAMED ON THE SURFACE at all times without interaction, and the console renders scope nowhere: grep finds no scope badge, banner or label in console.html. Fails on the always-visible clause; the resolution clause alone is not the requirement."; }
    part srConsoleModelScopeResolvedV1R1 : TestResult { :>> id = "9c842ba5-2067-4911-ac55-d8b105ec23dd"; :>> outcome = VerdictKind::fail; :>> judgedAgainst = "aeaca42"; :>> judgedAt = "2026-08-21"; :>> judgedBy = "claudeFable5"; }
    #Verify dependency from srConsoleModelScopeResolvedV1 to srConsoleModelScopeResolved;

    verification srViewerPersistedViewStateV1 : Test { :>> id = "1df206d3-63cc-45ff-9864-98e31e18ef69"; :>> title = "No declared view-state artifact exists"; :>> createdAt = "2026-08-21"; :>> createdBy = "claudeFable5"; :>> method = VerificationMethod::inspect; :>> procedureText = "HONEST FAIL. The SR requires a viewer session's viewpoint selection, filters and view state persisted as a DECLARED artifact in the repository (.engine/views form) and restored on re-open. Nothing does this: the console keeps selection in the URL hash and in-memory state, the deck keeps verdict drafts in browser localStorage keyed by item uuid, and .engine/views holds viewpoint DEFINITIONS, not sessions. Unbuilt end to end."; }
    part srViewerPersistedViewStateV1R1 : TestResult { :>> id = "7ba79dbb-b0e9-4d10-82d9-91c9cd7a8b93"; :>> outcome = VerdictKind::fail; :>> judgedAgainst = "aeaca42"; :>> judgedAt = "2026-08-21"; :>> judgedBy = "claudeFable5"; }
    #Verify dependency from srViewerPersistedViewStateV1 to srViewerPersistedViewState;

    verification srDcActorRoleModeledV1 : Test { :>> id = "cd4f20ea-ef8f-4b9d-8e91-53bbb6e141d0"; :>> title = "Actor roles are model data with a project-declared vocabulary"; :>> createdAt = "2026-08-21"; :>> createdBy = "claudeFable5"; :>> method = VerificationMethod::inspect; :>> procedureText = "Role is a field on Actor/Person instances in .tracking/actors.sysml (probed: wweatherholtz role=supervisor, the AI actors role=contributor) - model data, queryable, not prose. The vocabulary is project-declared where it CONSTRAINS: .engine/contracts/attestation-policy.toml names permitted roles per attestation class (roles=[supervisor] probed), with the recorded forward-only rule that an empty list means any role so pre-D0146 actors are not retro-failed. A downstream team declares its own roles by writing its own actors + policy."; }
    part srDcActorRoleModeledV1R1 : TestResult { :>> id = "52e399a6-818c-419d-bdcb-3f39ca499d2a"; :>> outcome = VerdictKind::pass; :>> judgedAgainst = "aeaca42"; :>> judgedAt = "2026-08-21"; :>> judgedBy = "claudeFable5"; }
    #Verify dependency from srDcActorRoleModeledV1 to srDcActorRoleModeled;

    verification srDcEngineVersionParityV1 : Test { :>> id = "450885f9-d8ef-4ec0-912c-070c2c2f930f"; :>> title = "No declared engine version, no parity check"; :>> createdAt = "2026-08-21"; :>> createdBy = "claudeFable5"; :>> method = VerificationMethod::inspect; :>> procedureText = "HONEST FAIL. The SR requires the project to DECLARE the engine version its checks are defined against and a contributor's toolchain to be compared against it before authoring. No such declaration exists (grep across .engine/contracts and src finds no engine-version parity mechanism), and nothing compares a contributor's binary to anything - the two field incidents this gap already caused are on record (issue089: a v0.2.0 binary against a pre-D0133 on-disk engine, 566 violations; issue090: absent rules read as violations). The chartered remedy exists as dcProjectMigrationTool (vintage DETECTION is its first clause) - this result flips when a declared version + parity check land."; }
    part srDcEngineVersionParityV1R1 : TestResult { :>> id = "d6859d32-3a40-4e33-8569-a73ac8a30bd5"; :>> outcome = VerdictKind::fail; :>> judgedAgainst = "aeaca42"; :>> judgedAt = "2026-08-21"; :>> judgedBy = "claudeFable5"; }
    // R2 (sprint 408): D0190's machinery landed and was probed - the fail flips exactly as the
    // decision's clause 4 required. engine-version.toml declared (init writes it, migrate re-stamps);
    // a deliberately stale declaration (0.1.0) fired the SKEW warning at keel validate naming
    // keel migrate; the matching declaration silenced it; keel --version reports the declared state.
    part srDcEngineVersionParityV1R2 : TestResult { :>> id = "7fa3ab0b-1948-4e64-a82e-fb7d7cebde78"; :>> outcome = VerdictKind::pass; :>> judgedAgainst = "8d603de"; :>> judgedAt = "2026-08-22"; :>> judgedBy = "claudeFable5"; }
    #Verify dependency from srDcEngineVersionParityV1 to srDcEngineVersionParity;

    verification srDcTwoLaneIntegrationV1 : Test { :>> id = "c7612380-d171-4193-9cc2-28834913a2c2"; :>> title = "Two integration lanes, routed by what a contribution changes"; :>> createdAt = "2026-08-21"; :>> createdBy = "claudeFable5"; :>> method = VerificationMethod::demo; :>> procedureText = "Both lanes are shipped machinery, exercised constantly. TRUNK LANE (RECORD/EXECUTE): keel sync integrates by merge and gates the result; keel land pushes and on rejection gates the MERGED tree before retrying - this session alone landed sprints 390-393 through it, each gated at the merge. CHANGE LANE: schema/process changes go through a recorded Decision with explicit human acceptance (D0106 machinery; the review queue and deck exist to record exactly that sign-off), and the CR process itself is frozen. Routing is by change class per the response contract's routing table, enforced at the turn boundary by hook stop."; }
    part srDcTwoLaneIntegrationV1R1 : TestResult { :>> id = "712df499-a9bf-445a-af6d-e28b59ef3259"; :>> outcome = VerdictKind::pass; :>> judgedAgainst = "aeaca42"; :>> judgedAt = "2026-08-21"; :>> judgedBy = "claudeFable5"; }
    #Verify dependency from srDcTwoLaneIntegrationV1 to srDcTwoLaneIntegration;

    verification srGovTieredAffordancesV1 : Test { :>> id = "ca1f4309-e061-40af-a689-c4fcf5accfff"; :>> title = "Gating tiers exist and are added on measured evidence"; :>> createdAt = "2026-08-21"; :>> createdBy = "claudeFable5"; :>> method = VerificationMethod::inspect; :>> procedureText = "The tiers exist exactly as graded: the turn-boundary stop gate blocks dishonest state; the per-edit post-tool tier runs the fast checks (D0134); the pre-action deny tier exists for protected fact surfaces (D0176 three-tier write path) with ask and recorded-override grades below it. The MEASURED-evidence clause is machinery, not intent: every hook fire appends to the fire-ledger (D0180), keel enforcement-report reads it, and the guided adoption profile keeps new controls advisory-first with promotion requiring cited ledger evidence (the D0174 profile design records roughly three sprints as the promotion bar). Blocking is reserved for clear violations; the rest warn - the honest-state rule (D0098) is the grading criterion."; }
    part srGovTieredAffordancesV1R1 : TestResult { :>> id = "11f9f09c-1e3d-487c-b64b-ba4a07c277b0"; :>> outcome = VerdictKind::pass; :>> judgedAgainst = "aeaca42"; :>> judgedAt = "2026-08-21"; :>> judgedBy = "claudeFable5"; }
    #Verify dependency from srGovTieredAffordancesV1 to srGovTieredAffordances;

    verification srRelPublishedArtifactV1 : Test { :>> id = "492850a8-b201-4262-a8ae-bb3953836ee0"; :>> title = "A tag publishes downloadable binaries carrying the embedded engine"; :>> createdAt = "2026-08-21"; :>> createdBy = "claudeFable5"; :>> method = VerificationMethod::demo; :>> procedureText = "Probed against GitHub: releases v0.2.0 through v0.2.3 exist and v0.2.3 carries three platform artifacts (keel-linux-x86_64, keel-macos-aarch64, keel-windows-x86_64.exe) published by CI on tag. The engine keel init ships is embedded IN the binary at build time (include_dir; K3 parity by construction), so the download IS binary-plus-engine and obtaining a version is a download, not a local build."; }
    part srRelPublishedArtifactV1R1 : TestResult { :>> id = "20edcc4b-df68-4065-8500-15bfdec4974a"; :>> outcome = VerdictKind::pass; :>> judgedAgainst = "aeaca42"; :>> judgedAt = "2026-08-21"; :>> judgedBy = "claudeFable5"; }
    #Verify dependency from srRelPublishedArtifactV1 to srRelPublishedArtifact;

    verification srRelRecordedReleaseV1 : Test { :>> id = "08a3953a-ac7a-46b0-96f6-4b1e62bd7577"; :>> title = "Each release is an authored Release item; contents computed from its commit"; :>> createdAt = "2026-08-21"; :>> createdBy = "claudeFable5"; :>> method = VerificationMethod::inspect; :>> procedureText = "Releases are authored facts: .tracking/baselines.sysml carries a Release item per shipped version (release020-023 inspected: commit SHA + purpose + the version in the title), and the baseline is computed as-of that commit rather than hand-written. READ AGAINST THE AMENDED SCHEMA: the SR's letter names a membershipRule field, which accepted D0142 removed as dead schema (it lived on the never-instantiated part def Release; the live occurrence def carries commit + purpose) - the membership rule IS the commit under D0036/D0042's design, where contents are a query over the tree at that SHA. Residual stated plainly: the version lives in the title string, not a typed field."; }
    part srRelRecordedReleaseV1R1 : TestResult { :>> id = "b1f306eb-cf37-48b9-8f66-377cc1380d63"; :>> outcome = VerdictKind::pass; :>> judgedAgainst = "aeaca42"; :>> judgedAt = "2026-08-21"; :>> judgedBy = "claudeFable5"; }
    #Verify dependency from srRelRecordedReleaseV1 to srRelRecordedRelease;

    verification srRelSemverReconciledV1 : Test { :>> id = "681aabd8-3c1a-4e73-a84a-b147cb25390d"; :>> title = "Three versions, no reconciliation"; :>> createdAt = "2026-08-21"; :>> createdBy = "claudeFable5"; :>> method = VerificationMethod::inspect; :>> procedureText = "HONEST FAIL. Probed: the crate/binary reports 0.2.3, the API/write contract reports 2.0.0 (KEEL_API_VERSION, bumped this week for the required-judged-by break), and the claude-surface generator carries its own SURFACE_VERSION - three independently-moving version identities with no single declared semver reconciling them and no toolchain check against a declared value (the parity gap is srDcEngineVersionParityV1's same finding from the release side). This result flips when one declared version binds them or a recorded Decision states why they intentionally diverge."; }
    part srRelSemverReconciledV1R1 : TestResult { :>> id = "6c9ef1dc-9010-4fcc-b379-229d45911ee7"; :>> outcome = VerdictKind::fail; :>> judgedAgainst = "aeaca42"; :>> judgedAt = "2026-08-21"; :>> judgedBy = "claudeFable5"; }
    // R2 (sprint 408): reconciled per D0190 - the binary version IS the declared semver; keel
    // --version and /api/version now report the API contract and claude-surface versions AS DERIVED
    // FACTS beside it (probed live: api 2.0.0 / binary 0.2.3 / surface 0.2.3), with breaking API
    // changes recorded in release Decisions rather than versioned apart, and the toolchain checkable
    // against the project's declaration via the parity warning.
    part srRelSemverReconciledV1R2 : TestResult { :>> id = "5711e159-e725-482c-822a-6340123f6e8e"; :>> outcome = VerdictKind::pass; :>> judgedAgainst = "8d603de"; :>> judgedAt = "2026-08-22"; :>> judgedBy = "claudeFable5"; }
    #Verify dependency from srRelSemverReconciledV1 to srRelSemverReconciled;
}
