// =====================================================================
// ProprietyRound1 — the control-propriety panel over this session's eight solutions (D0257, st032).
//
// INDEPENDENCE, stated per the process's own rule: every target below was AUTHORED by the assessor
// (claudeOpus5), so every `sound` verdict here is a TESTIMONY, not a receipt (D0080/D0232). The
// stance is eliminative throughout - argue against before crediting - and this round's own record
// is the evidence that self-audit under that stance still convicts: it found one `unsound` on a
// guard shipped two days ago and one on a convention shipped yesterday.
//
// One ProprietyFinding per target x lens (atomic, invariant 2). Verdict semantics: `sound` = the
// named refutations were tried and failed; `conditional` = the named defeater STANDS; `unsound` =
// demonstrated against the mechanism, routed to an Issue.
// =====================================================================
package ProprietyRound1 {
    private import EngineElement::*;
    private import EnginePropriety::*;

    // ── T1: guard 53, manifest-key-portability ──────────────────────────────────────────────────

    part pf01 : ProprietyFinding { :>> id = "c1a10001-0829-4c1e-9f10-000000000001"; :>> title = "g53 x overfit"; :>> createdAt = "2026-08-29"; :>> createdBy = "claudeOpus5"; :>> target = "guard:manifest-key-portability"; :>> lens = ProprietyLens::overfit; :>> verdict = ProprietyVerdict::sound; :>> rationale = "Detects by SHAPE (drive letter, leading slash, leading tilde), never by the observed instance or this machine's username - a guard matching 'WilliamWeatherholtz' would have been the overfit form, and it was explicitly considered and rejected in the guard's own doc."; :>> defeater = "TRIED: mutated the specimen to another user, another drive, a POSIX home path - all three shapes are caught. A UNC path (//server/share) is a fourth absolute shape the guard does NOT match; it is also not producible by unit_files today, which is why this stays sound rather than conditional."; }
    part pf02 : ProprietyFinding { :>> id = "c1a10001-0829-4c1e-9f10-000000000002"; :>> title = "g53 x classCoverage"; :>> createdAt = "2026-08-29"; :>> createdBy = "claudeOpus5"; :>> target = "guard:manifest-key-portability"; :>> lens = ProprietyLens::classCoverage; :>> verdict = ProprietyVerdict::unsound; :>> rationale = "The class is 'a manifest key that resolves outside the receiving project'. ABSOLUTE keys are one member; a RELATIVE key with traversal segments (file...__SL__..__SL__elsewhere decodes to ../../elsewhere) is another member, escapes the project root identically, and PASSES the guard - demonstrated by decoding by hand against the guard's own absolute-only predicate."; :>> defeater = "STANDS: a hand-edited or future-code-produced key containing '..' segments. Routed as issue307; the fix is one more shape in the same predicate."; }
    part pf03 : ProprietyFinding { :>> id = "c1a10001-0829-4c1e-9f10-000000000003"; :>> title = "g53 x changeRobustness"; :>> createdAt = "2026-08-29"; :>> createdBy = "claudeOpus5"; :>> target = "guard:manifest-key-portability"; :>> lens = ProprietyLens::changeRobustness; :>> verdict = ProprietyVerdict::conditional; :>> rationale = "Depends on two incidentals: the 'file.' key prefix and the '__SL__' encoding. If D0183's manifest format ever changes either, the guard scans 0 keys and PASSES - vacuous, silently, because pass-at-zero is not warned for this guard."; :>> defeater = "STANDS: a manifest format change. Cheap partial mitigation: the guard already reports its scanned count, so a reader comparing 83-key history to a sudden 0 can see it - but a reader is not a control."; }
    part pf04 : ProprietyFinding { :>> id = "c1a10001-0829-4c1e-9f10-000000000004"; :>> title = "g53 x circumventability"; :>> createdAt = "2026-08-29"; :>> createdBy = "claudeOpus5"; :>> target = "guard:manifest-key-portability"; :>> lens = ProprietyLens::circumventability; :>> verdict = ProprietyVerdict::conditional; :>> rationale = "Two routes: SKIP_VALIDATE=1 bypasses the whole commit gate (documented, deliberate, and backstopped by CI re-running the guard on push - the bypass buys a local commit, not a landed one); and the traversal route of pf02, which is not a bypass but a hole."; :>> defeater = "STANDS: a push path that skips CI would make SKIP_VALIDATE decisive; today none exists (branch protection + the gate workflow). The traversal hole is pf02's issue."; }
    part pf05 : ProprietyFinding { :>> id = "c1a10001-0829-4c1e-9f10-000000000005"; :>> title = "g53 x measurability"; :>> createdAt = "2026-08-29"; :>> createdBy = "claudeOpus5"; :>> target = "guard:manifest-key-portability"; :>> lens = ProprietyLens::measurability; :>> verdict = ProprietyVerdict::sound; :>> rationale = "Pure string predicate over a committed file: any third party re-runs `keel guard manifest-key-portability` and re-derives the verdict. Binary, deterministic, no judgment in the loop."; :>> defeater = "TRIED: none credible - the check has no qualitative component to dispute."; }

    // ── T2: guard 54, control-map-reconciled ────────────────────────────────────────────────────

    part pf06 : ProprietyFinding { :>> id = "c1a10001-0829-4c1e-9f10-000000000006"; :>> title = "g54 x overfit"; :>> createdAt = "2026-08-29"; :>> createdBy = "claudeOpus5"; :>> target = "guard:control-map-reconciled"; :>> lens = ProprietyLens::overfit; :>> verdict = ProprietyVerdict::conditional; :>> rationale = "Generalises past the launcher specimen (any event naming an undeclared control fails, any event with no binding fails) - but the anchor set is control-events.toml, which is exactly where the specimen lived. The guard reconciles the map against EVENTS, not against enforcement."; :>> defeater = "STANDS: an implemented control that emits NO declared event (ctlBranchProtection is one today) can still be absent from the map with no violation - the specimen's class is only partly fenced, see pf07."; }
    part pf07 : ProprietyFinding { :>> id = "c1a10001-0829-4c1e-9f10-000000000007"; :>> title = "g54 x classCoverage"; :>> createdAt = "2026-08-29"; :>> createdBy = "claudeOpus5"; :>> target = "guard:control-map-reconciled"; :>> lens = ProprietyLens::classCoverage; :>> verdict = ProprietyVerdict::conditional; :>> rationale = "The class (D0254) is implemented-but-undeclared. The guard covers its event-emitting SUBCLASS. An event-less mechanism - a CI job, a remote configuration, a build-time check - is in the class and outside the fence; ctlAdoptionCheck was declared by hand this week precisely because no event names it."; :>> defeater = "STANDS: the next event-less enforcement mechanism. Accepted for now rather than routed: the event-less subclass has no machine-readable anchor to reconcile against, and inventing a second hand-maintained list to fence it would recreate the drift this guard exists to end. Recorded as a disposition candidate, not silence."; }
    part pf08 : ProprietyFinding { :>> id = "c1a10001-0829-4c1e-9f10-000000000008"; :>> title = "g54 x changeRobustness"; :>> createdAt = "2026-08-29"; :>> createdBy = "claudeOpus5"; :>> target = "guard:control-map-reconciled"; :>> lens = ProprietyLens::changeRobustness; :>> verdict = ProprietyVerdict::conditional; :>> rationale = "The declared-control set is harvested by matching 'part ctl' as a NAMING CONVENTION across .tracking. A control declared as `part guardFoo : SystemSafetyConstraint` is invisible to the harvest, so an event binding it would FALSELY fail - the guard's correctness depends on a prefix no rule enforces."; :>> defeater = "STANDS: the first ctl-less control name. The honest fix is harvesting by TYPE (SystemSafetyConstraint) rather than by prefix; noted in issue307's resolver scope since it is the same file and class of fix."; }
    part pf09 : ProprietyFinding { :>> id = "c1a10001-0829-4c1e-9f10-000000000009"; :>> title = "g54 x circumventability"; :>> createdAt = "2026-08-29"; :>> createdBy = "claudeOpus5"; :>> target = "guard:control-map-reconciled"; :>> lens = ProprietyLens::circumventability; :>> verdict = ProprietyVerdict::conditional; :>> rationale = "The sanctioned escape is `control = \"none\"` plus a controlNote - and NOTHING verifies the note's truth. An author can bind any event to none with a plausible sentence and the guard passes. The note is reviewable by a human, which is a backstop of the qualitative kind."; :>> defeater = "STANDS: a false controlNote. Structural closure is impossible (truth of prose is not machine-checkable); the mitigation is that the notes live in a keystone-locked file, so changing one requires a co-committed marked Decision - the route is loud, not closed."; }
    part pf10 : ProprietyFinding { :>> id = "c1a10001-0829-4c1e-9f10-000000000010"; :>> title = "g54 x measurability"; :>> createdAt = "2026-08-29"; :>> createdBy = "claudeOpus5"; :>> target = "guard:control-map-reconciled"; :>> lens = ProprietyLens::measurability; :>> verdict = ProprietyVerdict::sound; :>> rationale = "Set difference between two committed files; re-derivable by anyone, proven armed by injection (FAIL 17/1 on a phantom control, PASS 16/0 restored)."; :>> defeater = "TRIED: the arming injection. The qualitative residue (controlNote truth) is pf09's finding, not a measurability defect - what the guard CLAIMS to measure, it measures objectively."; }

    // ── T3: the write-lock probe ────────────────────────────────────────────────────────────────

    part pf11 : ProprietyFinding { :>> id = "c1a10001-0829-4c1e-9f10-000000000011"; :>> title = "writeLockProbe x overfit"; :>> createdAt = "2026-08-29"; :>> createdBy = "claudeOpus5"; :>> target = "keel-cli/tests/write_lock_actually_serialises.rs"; :>> lens = ProprietyLens::overfit; :>> verdict = ProprietyVerdict::conditional; :>> rationale = "The issue184 specimen was four concurrent `record issue` calls; the probe uses six concurrent `record statement` calls - a variant, not the specimen, which is the right shape. But one entry point stands in for all of them."; :>> defeater = "STANDS: a race specific to a DIFFERENT write path (issue-numbering vs statement-numbering differ in their read-modify-write). Mitigated by the lock being model-wide and taken by the shared with_file_lock - the probe proves the lock, pf12 covers the residual."; }
    part pf12 : ProprietyFinding { :>> id = "c1a10001-0829-4c1e-9f10-000000000012"; :>> title = "writeLockProbe x classCoverage"; :>> createdAt = "2026-08-29"; :>> createdBy = "claudeOpus5"; :>> target = "keel-cli/tests/write_lock_actually_serialises.rs"; :>> lens = ProprietyLens::classCoverage; :>> verdict = ProprietyVerdict::conditional; :>> rationale = "The class is 'lost writes under concurrency'. The probe proves the LOCK serialises writers who TAKE it; it cannot prove every write path takes it. A future write path that skips with_file_lock reintroduces issue184 while this probe stays green."; :>> defeater = "STANDS: an unwrapped write path. The structural fix would be a lint/guard that every file-mutating fn in write.rs routes through the lock - flagged in the round summary as candidate work, cheap to add and objective."; }
    part pf13 : ProprietyFinding { :>> id = "c1a10001-0829-4c1e-9f10-000000000013"; :>> title = "writeLockProbe x changeRobustness"; :>> createdAt = "2026-08-29"; :>> createdBy = "claudeOpus5"; :>> target = "keel-cli/tests/write_lock_actually_serialises.rs"; :>> lens = ProprietyLens::changeRobustness; :>> verdict = ProprietyVerdict::conditional; :>> rationale = "Counts landed statements by matching ': Statement' in the intake files - a format dependence. If the statement-authoring template changes that literal, landed reads 0 and the assertion landed==exited_zero FAILS LOUDLY (0 != 6), which is the good direction: this probe dies noisily, not vacuously."; :>> defeater = "STANDS but benign in direction: a template change breaks the test visibly rather than passing it emptily. The keel_bin() path discovery is the second incidental; a harness layout change also fails loudly (panic on missing binary, by design)."; }
    part pf14 : ProprietyFinding { :>> id = "c1a10001-0829-4c1e-9f10-000000000014"; :>> title = "writeLockProbe x circumventability"; :>> createdAt = "2026-08-29"; :>> createdBy = "claudeOpus5"; :>> target = "keel-cli/tests/write_lock_actually_serialises.rs"; :>> lens = ProprietyLens::circumventability; :>> verdict = ProprietyVerdict::sound; :>> rationale = "A probe is circumvented by NOT RUNNING it; this one rides `cargo test --workspace`, which CI runs on every push and the reverify contract re-runs at HEAD - skipping it locally buys nothing that lands."; :>> defeater = "TRIED: the only route is removing the test file, which is a visible diff in a reviewed tree, and CI's test count dropping is loud. No quiet route found."; }
    part pf15 : ProprietyFinding { :>> id = "c1a10001-0829-4c1e-9f10-000000000015"; :>> title = "writeLockProbe x measurability"; :>> createdAt = "2026-08-29"; :>> createdBy = "claudeOpus5"; :>> target = "keel-cli/tests/write_lock_actually_serialises.rs"; :>> lens = ProprietyLens::measurability; :>> verdict = ProprietyVerdict::sound; :>> rationale = "Counts read from the TREE, never from the writers' exit codes - the probe's own design note, because an exit code is testimony and the tree is the receipt. Deterministic assertion, re-runnable by anyone."; :>> defeater = "TRIED: scheduling nondeterminism (six processes may serialise trivially on a fast machine, understating contention) - real, but it weakens the STRENGTH of the evidence, not its objectivity; a lost write, when it occurs, is detected objectively."; }

    // ── T4: the launcher probes ─────────────────────────────────────────────────────────────────

    part pf16 : ProprietyFinding { :>> id = "c1a10001-0829-4c1e-9f10-000000000016"; :>> title = "launcherProbes x overfit"; :>> createdAt = "2026-08-29"; :>> createdBy = "claudeOpus5"; :>> target = "keel-cli/tests/launcher_controls_actually_fire.rs"; :>> lens = ProprietyLens::overfit; :>> verdict = ProprietyVerdict::sound; :>> rationale = "No motivating defect existed (the launcher had never run), so there was no specimen to overfit to; the probes assert the module's DECLARED contract - refusal, snapshot, the 14 fields - not an incident's shape."; :>> defeater = "TRIED: asked whether asserting the declared field list merely restates the declaration - it does not, because the declaration was EXEMPT from existence checks, so the probe is the only thing making the declaration mean anything."; }
    part pf17 : ProprietyFinding { :>> id = "c1a10001-0829-4c1e-9f10-000000000017"; :>> title = "launcherProbes x classCoverage"; :>> createdAt = "2026-08-29"; :>> createdBy = "claudeOpus5"; :>> target = "keel-cli/tests/launcher_controls_actually_fire.rs"; :>> lens = ProprietyLens::classCoverage; :>> verdict = ProprietyVerdict::conditional; :>> rationale = "prepare/finish are proven; the SSE wiring in serve.rs that CALLS them is not - the probe enters below the layer where a wiring defect would live. And only the EMPTY-diff half of finish is asserted (no summary); the non-empty half (one tracked summary, judgedAgainst the spawn HEAD) is unprobed."; :>> defeater = "STANDS: a serve.rs wiring defect, or a regression in the non-empty-diff summary path. The second is cheap to add to the same fixture (touch a file between prepare and finish) and is named in the round summary as candidate work."; }
    part pf18 : ProprietyFinding { :>> id = "c1a10001-0829-4c1e-9f10-000000000018"; :>> title = "launcherProbes x changeRobustness"; :>> createdAt = "2026-08-29"; :>> createdBy = "claudeOpus5"; :>> target = "keel-cli/tests/launcher_controls_actually_fire.rs"; :>> lens = ProprietyLens::changeRobustness; :>> verdict = ProprietyVerdict::sound; :>> rationale = "The field assertion iterates RUN_RECORD_FIELDS - the shipped constant, not a copy - so adding a 15th field updates the probe automatically, and removing one fails it. The fixture builds a real git repo, so git-behaviour drift surfaces as a fixture error, not a false verdict."; :>> defeater = "TRIED: renaming a field in the constant - the probe follows it by construction. The residual incidental is the JSON quoting shape ('\"field\"'), which a serialisation change would break LOUDLY."; }
    part pf19 : ProprietyFinding { :>> id = "c1a10001-0829-4c1e-9f10-000000000019"; :>> title = "launcherProbes x circumventability"; :>> createdAt = "2026-08-29"; :>> createdBy = "claudeOpus5"; :>> target = "keel-cli/tests/launcher_controls_actually_fire.rs"; :>> lens = ProprietyLens::circumventability; :>> verdict = ProprietyVerdict::sound; :>> rationale = "Rides the workspace suite like the write-lock probe (pf14's argument applies unchanged)."; :>> defeater = "TRIED: same routes as pf14, same loud failures."; }
    part pf20 : ProprietyFinding { :>> id = "c1a10001-0829-4c1e-9f10-000000000020"; :>> title = "launcherProbes x measurability"; :>> createdAt = "2026-08-29"; :>> createdBy = "claudeOpus5"; :>> target = "keel-cli/tests/launcher_controls_actually_fire.rs"; :>> lens = ProprietyLens::measurability; :>> verdict = ProprietyVerdict::sound; :>> rationale = "Deterministic fixtures, assertions on file contents and refusal messages; re-runnable."; :>> defeater = "TRIED: none credible."; }

    // ── T5: the hook/push probes ────────────────────────────────────────────────────────────────

    part pf21 : ProprietyFinding { :>> id = "c1a10001-0829-4c1e-9f10-000000000021"; :>> title = "hookPushProbes x overfit"; :>> createdAt = "2026-08-29"; :>> createdBy = "claudeOpus5"; :>> target = "keel-cli/tests/hook_and_push_controls_actually_fire.rs"; :>> lens = ProprietyLens::overfit; :>> verdict = ProprietyVerdict::sound; :>> rationale = "The pre-push probe deliberately tests the FORCED push - the case only this hook catches - after its first run showed the plain-behind case is git's own, not the hook's. That reframing is anti-overfit in action: the probe was refitted to the control's actual class, not its folklore."; :>> defeater = "TRIED: pushed the plain-behind variant - refused upstream by git, correctly attributed to git in the probe's comment rather than credited to the hook."; }
    part pf22 : ProprietyFinding { :>> id = "c1a10001-0829-4c1e-9f10-000000000022"; :>> title = "hookPushProbes x classCoverage"; :>> createdAt = "2026-08-29"; :>> createdBy = "claudeOpus5"; :>> target = "keel-cli/tests/hook_and_push_controls_actually_fire.rs"; :>> lens = ProprietyLens::classCoverage; :>> verdict = ProprietyVerdict::conditional; :>> rationale = "The pre-write probe covers the STRICT profile's three tiers - and this project runs GUIDED, so the tier the self-build actually lives under (advisory prints, no deny) is unprobed. The probe proves the profile the fleet's strictest member would use, not the one in daily service here."; :>> defeater = "STANDS: a regression in the guided-profile advisory path. Cheap to add (same fixture, profile flipped); named in the round summary as candidate work."; }
    part pf23 : ProprietyFinding { :>> id = "c1a10001-0829-4c1e-9f10-000000000023"; :>> title = "hookPushProbes x changeRobustness"; :>> createdAt = "2026-08-29"; :>> createdBy = "claudeOpus5"; :>> target = "keel-cli/tests/hook_and_push_controls_actually_fire.rs"; :>> lens = ProprietyLens::changeRobustness; :>> verdict = ProprietyVerdict::conditional; :>> rationale = "The reverify fixture hand-authors a task/result in template syntax; a schema change to TestResult fields breaks the fixture LOUDLY (parse or count failure). The pre-push probe wires core.hooksPath at the real .githooks - robust to hook edits by construction, dependent only on hook FILE NAMES."; :>> defeater = "STANDS: renaming .githooks/pre-push would silently un-wire the probe's hook (git ignores a missing hook) and the forced push would SUCCEED, failing the assertion loudly - again the good direction. No silent-pass route found; the conditional is for the hand-authored fixture drift."; }
    part pf24 : ProprietyFinding { :>> id = "c1a10001-0829-4c1e-9f10-000000000024"; :>> title = "hookPushProbes x circumventability"; :>> createdAt = "2026-08-29"; :>> createdBy = "claudeOpus5"; :>> target = "keel-cli/tests/hook_and_push_controls_actually_fire.rs"; :>> lens = ProprietyLens::circumventability; :>> verdict = ProprietyVerdict::conditional; :>> rationale = "The probe cannot close the control's own biggest bypass: `git push --no-verify` skips pre-push entirely, by git's design. The probe proves the hook fires WHEN CONSULTED; nothing local can prove it is consulted. The backstop is remote: CI's audit-history re-derives verdicts over pushed ranges and branch protection refuses force-pushes at the server."; :>> defeater = "STANDS: --no-verify plus a remote without branch protection. In THIS repo the backstops exist (probed at sprint 401); in a downstream repo they are the adopter's to configure, and keel init's docs say so. Accepted with that boundary stated."; }
    part pf25 : ProprietyFinding { :>> id = "c1a10001-0829-4c1e-9f10-000000000025"; :>> title = "hookPushProbes x measurability"; :>> createdAt = "2026-08-29"; :>> createdBy = "claudeOpus5"; :>> target = "keel-cli/tests/hook_and_push_controls_actually_fire.rs"; :>> lens = ProprietyLens::measurability; :>> verdict = ProprietyVerdict::sound; :>> rationale = "Every assertion is on observable process output, file contents, or push exit status; the reverify probe's red half is kept honest by its green half stamping exactly one result - the both-ways discipline, objectively checked."; :>> defeater = "TRIED: the vacuous first draft of the reverify fixture IS the defeater that was found and eliminated - the shipped probe manufactures real drift precisely so the no-stamp assertion has something to fail against."; }

    // ── T6: the pre-push creation fix (D0256) ───────────────────────────────────────────────────

    part pf26 : ProprietyFinding { :>> id = "c1a10001-0829-4c1e-9f10-000000000026"; :>> title = "prePushFix x overfit"; :>> createdAt = "2026-08-29"; :>> createdBy = "claudeOpus5"; :>> target = ".githooks/pre-push creation-skip (D0256)"; :>> lens = ProprietyLens::overfit; :>> verdict = ProprietyVerdict::sound; :>> rationale = "The fix implements the CLASS the adjacent comment already named ('deleting or creating refs is not a behind-ness question') rather than special-casing the empty-remote specimen: any ref creation skips, symmetric with deletion."; :>> defeater = "TRIED: creating main on a NON-empty remote (other branches exist) - remote_sha is still zeros for the new ref, still correctly skipped. Creating over an EXISTING main is not creation (remote_sha nonzero) and is still checked."; }
    part pf27 : ProprietyFinding { :>> id = "c1a10001-0829-4c1e-9f10-000000000027"; :>> title = "prePushFix x classCoverage"; :>> createdAt = "2026-08-29"; :>> createdBy = "claudeOpus5"; :>> target = ".githooks/pre-push creation-skip (D0256)"; :>> lens = ProprietyLens::classCoverage; :>> verdict = ProprietyVerdict::sound; :>> rationale = "The class 'no behind-ness question exists' has exactly two members in git's ref algebra - creation and deletion - and both are now skipped by the same zero-sha test."; :>> defeater = "TRIED: hunted a third member (ref renames arrive as delete+create, orphan histories still have a behind-ness answer via merge-base failing, which correctly refuses). None found."; }
    part pf28 : ProprietyFinding { :>> id = "c1a10001-0829-4c1e-9f10-000000000028"; :>> title = "prePushFix x changeRobustness"; :>> createdAt = "2026-08-29"; :>> createdBy = "claudeOpus5"; :>> target = ".githooks/pre-push creation-skip (D0256)"; :>> lens = ProprietyLens::changeRobustness; :>> verdict = ProprietyVerdict::sound; :>> rationale = "Depends only on git's stable pre-push stdin contract (local_ref local_sha remote_ref remote_sha), unchanged since git 1.8; the zero-sha sentinel is the same one the deletion case has used here from the start."; :>> defeater = "TRIED: SHA-256 repositories widen the zero string - the pattern matches the 40-zero form only. A sha256 repo would re-open issue306 loudly (first push refused again), caught by the probe the moment CI runs one. Accepted as beyond current scope; git's own hook examples share the assumption."; }
    part pf29 : ProprietyFinding { :>> id = "c1a10001-0829-4c1e-9f10-000000000029"; :>> title = "prePushFix x circumventability"; :>> createdAt = "2026-08-29"; :>> createdBy = "claudeOpus5"; :>> target = ".githooks/pre-push creation-skip (D0256)"; :>> lens = ProprietyLens::circumventability; :>> verdict = ProprietyVerdict::conditional; :>> rationale = "Inherits the hook class's bypass (--no-verify, pf24) unchanged - the fix neither widens nor narrows it. A skip is not a new hole: a creation push was never a behind-ness question, so nothing checkable was removed."; :>> defeater = "STANDS: pf24's, unchanged."; }
    part pf30 : ProprietyFinding { :>> id = "c1a10001-0829-4c1e-9f10-000000000030"; :>> title = "prePushFix x measurability"; :>> createdAt = "2026-08-29"; :>> createdBy = "claudeOpus5"; :>> target = ".githooks/pre-push creation-skip (D0256)"; :>> lens = ProprietyLens::measurability; :>> verdict = ProprietyVerdict::sound; :>> rationale = "Proven both ways by the probe: the bootstrap push passes, the forced rewrite refuses, both as exit statuses anyone can re-run."; :>> defeater = "TRIED: none credible."; }

    // ── T7: the provenBy convention (control-arming.toml) ───────────────────────────────────────

    part pf31 : ProprietyFinding { :>> id = "c1a10001-0829-4c1e-9f10-000000000031"; :>> title = "provenBy x overfit"; :>> createdAt = "2026-08-29"; :>> createdBy = "claudeOpus5"; :>> target = "control-arming.toml provenBy convention (D0253)"; :>> lens = ProprietyLens::overfit; :>> verdict = ProprietyVerdict::sound; :>> rationale = "The convention is general by construction: any control, any test file, one field. It encodes the D0253 distinction (proven-by-test vs checkable-by-view) rather than the write-lock incident."; :>> defeater = "TRIED: asked whether it only fits Rust tests - it names a path, so a shell probe or CI job record would serve identically."; }
    part pf32 : ProprietyFinding { :>> id = "c1a10001-0829-4c1e-9f10-000000000032"; :>> title = "provenBy x classCoverage"; :>> createdAt = "2026-08-29"; :>> createdBy = "claudeOpus5"; :>> target = "control-arming.toml provenBy convention (D0253)"; :>> lens = ProprietyLens::classCoverage; :>> verdict = ProprietyVerdict::conditional; :>> rationale = "It covers 'this control has a probe' - it cannot say the probe is SUFFICIENT. pf17 and pf22 are live examples: provenBy points at real tests whose class coverage this very panel found partial. The field claims existence, and a reader may read adequacy."; :>> defeater = "STANDS: a weak probe behind a confident provenBy. The panel itself is the mitigation - propriety findings sit beside the arming contract and say which provenBy claims are partial."; }
    part pf33 : ProprietyFinding { :>> id = "c1a10001-0829-4c1e-9f10-000000000033"; :>> title = "provenBy x changeRobustness"; :>> createdAt = "2026-08-29"; :>> createdBy = "claudeOpus5"; :>> target = "control-arming.toml provenBy convention (D0253)"; :>> lens = ProprietyLens::changeRobustness; :>> verdict = ProprietyVerdict::unsound; :>> rationale = "NOTHING verifies the named file exists. provenBy = 'a/test/that/never/existed.rs' passes every gate today; so does a stale pointer after a test file is renamed. A dangling provenBy is worse than none - it is a receipt-shaped testimony, the precise confusion D0232 exists to prevent, sitting in the contract that is supposed to end that confusion."; :>> defeater = "STANDS, demonstrated by construction (no check exists to fail). Routed as issue308: extend an existing guard to resolve every provenBy path against the tree - objective, one string test per entry."; }
    part pf34 : ProprietyFinding { :>> id = "c1a10001-0829-4c1e-9f10-000000000034"; :>> title = "provenBy x circumventability"; :>> createdAt = "2026-08-29"; :>> createdBy = "claudeOpus5"; :>> target = "control-arming.toml provenBy convention (D0253)"; :>> lens = ProprietyLens::circumventability; :>> verdict = ProprietyVerdict::conditional; :>> rationale = "The file is keystone-locked, so ADDING a provenBy requires a marked Decision - the write route is loud. But pf33 means the loud route can carry a false claim with no machine noticing; the lock authenticates the ACT, not the CONTENT."; :>> defeater = "STANDS until issue308 lands; then the cheap half (existence) closes and the qualitative half (adequacy) remains pf32's."; }
    part pf35 : ProprietyFinding { :>> id = "c1a10001-0829-4c1e-9f10-000000000035"; :>> title = "provenBy x measurability"; :>> createdAt = "2026-08-29"; :>> createdBy = "claudeOpus5"; :>> target = "control-arming.toml provenBy convention (D0253)"; :>> lens = ProprietyLens::measurability; :>> verdict = ProprietyVerdict::conditional; :>> rationale = "Path existence and the named test's pass/fail are objective; 'this test exercises THAT control' is a human-readable claim no machine can verify - the binding between control and probe is qualitative and always will be."; :>> defeater = "STANDS inherently: the binding is judgment. Mitigation is the probe DISCIPLINE (allow-then-refuse, injection arming) making a mis-bound probe unlikely to pass, plus this panel reading the bindings."; }

    // ── T8: the no-op version fix (issue302, next_unit_version) ─────────────────────────────────

    part pf36 : ProprietyFinding { :>> id = "c1a10001-0829-4c1e-9f10-000000000036"; :>> title = "versionFix x overfit"; :>> createdAt = "2026-08-29"; :>> createdBy = "claudeOpus5"; :>> target = "process_cmd.rs next_unit_version / hashes_match (issue302)"; :>> lens = ProprietyLens::overfit; :>> verdict = ProprietyVerdict::sound; :>> rationale = "The unit test mutates past the specimen: same-set-reordered stays current, one-changed-hash is not, an ADDED file is not - the added-file case being a variant the incident never exhibited."; :>> defeater = "TRIED: a REMOVED file - caught by the length check in hashes_match. A same-length swap of path names with hashes preserved would pass sorted comparison only if the (path,hash) PAIRS match, which is the correct semantics."; }
    part pf37 : ProprietyFinding { :>> id = "c1a10001-0829-4c1e-9f10-000000000037"; :>> title = "versionFix x classCoverage"; :>> createdAt = "2026-08-29"; :>> createdBy = "claudeOpus5"; :>> target = "process_cmd.rs next_unit_version / hashes_match (issue302)"; :>> lens = ProprietyLens::classCoverage; :>> verdict = ProprietyVerdict::conditional; :>> rationale = "The class is 'a version that moves without content moving'. The EXPORT path is fixed; the two IMPORT paths compute their own hashes and were left unrefactored - the named residual from sprint 484, still standing."; :>> defeater = "STANDS: an import-path no-op bump. Bounded by guard 53 catching absolute keys those paths might also produce, but the version semantics there are unguarded; already recorded in sprint 484's closeOut, not re-filed."; }
    part pf38 : ProprietyFinding { :>> id = "c1a10001-0829-4c1e-9f10-000000000038"; :>> title = "versionFix x changeRobustness"; :>> createdAt = "2026-08-29"; :>> createdBy = "claudeOpus5"; :>> target = "process_cmd.rs next_unit_version / hashes_match (issue302)"; :>> lens = ProprietyLens::changeRobustness; :>> verdict = ProprietyVerdict::sound; :>> rationale = "Pure functions over (path,hash) pairs, extracted precisely so the comparison is testable without a filesystem; hash algorithm changes flow through file_hash uniformly on both sides of the comparison."; :>> defeater = "TRIED: a hash-algorithm change mid-history would make every unit read as changed ONCE (one spurious bump per unit), then stabilise - visible, self-limiting, and honest in direction."; }
    part pf39 : ProprietyFinding { :>> id = "c1a10001-0829-4c1e-9f10-000000000039"; :>> title = "versionFix x circumventability"; :>> createdAt = "2026-08-29"; :>> createdBy = "claudeOpus5"; :>> target = "process_cmd.rs next_unit_version / hashes_match (issue302)"; :>> lens = ProprietyLens::circumventability; :>> verdict = ProprietyVerdict::conditional; :>> rationale = "Hand-editing the version in installed-units.toml bypasses the computation entirely; the file is a committed contract but not keystone-locked."; :>> defeater = "STANDS: a hand bump. Low stakes while the library is unpublished; worth revisiting when D0250's publish path lands, where a false version propagates to other machines."; }
    part pf40 : ProprietyFinding { :>> id = "c1a10001-0829-4c1e-9f10-000000000040"; :>> title = "versionFix x measurability"; :>> createdAt = "2026-08-29"; :>> createdBy = "claudeOpus5"; :>> target = "process_cmd.rs next_unit_version / hashes_match (issue302)"; :>> lens = ProprietyLens::measurability; :>> verdict = ProprietyVerdict::sound; :>> rationale = "Byte-identity of a committed file across a no-op restamp is the objective form of the claim, and the sprint-484 Gherkin states it exactly that way."; :>> defeater = "TRIED: none credible."; }

    // ── Disposition of pf07's standing conditional (D0092 lifecycle; D0165 delegates the verdict) ──
    private import EngineVerification::*;

    verification pf07Disp1 : Test {
        :>> id = "344116ff-b056-4823-bc86-840f0db3298e";
        :>> title = "pf07 disposition: acceptRisk - event-less controls stay hand-reconciled";
        :>> createdAt = "2026-08-29"; :>> createdBy = "claudeOpus5";
        :>> method = VerificationMethod::confirmation;
        :>> disposition = DispositionKind::acceptRisk;
        :>> procedureText = "ACCEPT-RISK, selected by the human on the program-summary page (st036, verbatim: '[x] Accept the residual as a recorded disposition (acceptRisk)'). The residual: guard 54 reconciles the control map only against control-events.toml, so an implemented control that emits NO declared event - a CI job, a remote configuration - can be absent from the map with no violation (the D0254 class, event-less subclass). ACCEPTED because pf07's own defeater analysis holds: no machine-readable anchor exists for event-less enforcement, and inventing a second hand-maintained list to fence it would recreate the drift the guard exists to end. THE FLIP CONDITION, recorded so the acceptance is falsifiable: a second implemented-but-undeclared control found in the field reopens this as build-the-anchor (workflow files are parseable). Known live instances at acceptance: ctlAdoptionCheck and ctlAuditAdherence were both declared BY HAND this week, which is the residual working as accepted, not failing.";
    }
    part pf07Disp1R1 : TestResult { :>> id = "54a0a800-4a29-4c4c-b92d-ef23cec5bdc1"; :>> outcome = VerdictKind::pass; :>> judgedAgainst = "616d613"; :>> judgedAt = "2026-08-29"; :>> judgedBy = "claudeOpus5"; }
    #Verify dependency from pf07Disp1 to pf07;
}
