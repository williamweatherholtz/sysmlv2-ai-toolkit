// Intake for 2026-09-03 — their words, my translation, the triage verdict (D0166/D0216).
// Written by `keel record statement` / `keel record story` (D0236): a Statement's text is
// VERBATIM, so it is escaped for the literal and otherwise untouched.
package ProjectIntake20260903 {
    private import EngineElement::*;
    private import EngineIntake::*;
    private import EngineRelationships::*;

    part st071 : Statement {
        :>> id = "15e001df-611f-45c4-abdf-0cb4562b3749";
        :>> title = "0/0 is 0 percent, not a clean sweep of 100: nothing is done yet";
        :>> createdAt = "2026-09-03"; :>> createdBy = "claudeOpus5";
        :>> text = "this happens regularly - projects inheriting keel get a clean sweep of 100% when 0/0 should be considered 0% to indicate that nothing is done yet.  make those changes where relevant?";
        :>> saidBy = "wweatherholtz"; :>> saidAt = "2026-09-02"; :>> channel = StatementChannel::chat;
    }

    part us073 : UserStory {
        :>> id = "0fe84648-59ed-403e-b75e-febc0ab7718a";
        :>> title = "An empty population reads as nothing done, never as complete";
        :>> createdAt = "2026-09-03"; :>> createdBy = "claudeOpus5";
        :>> asA = "the owner of a project that just inherited keel";
        :>> iWant = "every ratio and readiness verdict to read 0 percent or 'nothing to assure' when there is nothing to measure";
        :>> soThat = "a fresh project does not open on a clean sweep of green that says everything is done when nothing has been authored";
        :>> implication = ImplicationKind::verifiedRequirement;
        :>> triageNote = "MEASURED on a fresh scaffold before the change: report assurance showed three 100 percent cards and READY; tier-satisfaction reported pct 100 per empty tier. Four sites defaulted an empty denominator to full (reports.rs pct, verification.rs pct, tier-satisfaction's missing-tier default, ReadinessBlockers::ready over an empty governed set) and one test pinned it as 'vacuously complete'. Fixed in the same sprint with a source-scan test so a fifth spelling cannot land.";
    }
    #DerivedFrom dependency from us073 to st071;

    part st072 : Statement {
        :>> id = "95407628-ca83-43b1-a770-679b1f7f0cd3";
        :>> title = "Colour passing vs failing, in keel itself so every project gets it";
        :>> createdAt = "2026-09-03"; :>> createdBy = "claudeOpus5";
        :>> text = "make it colored so i can tell passing vs failing. and push this back up to keel so other projects use";
        :>> saidBy = "wweatherholtz"; :>> saidAt = "2026-09-03"; :>> channel = StatementChannel::chat;
    }

    part us074 : UserStory {
        :>> id = "84314b4c-cabc-4f79-833f-705f9f9452da";
        :>> title = "A verdict is legible at a glance: pass green, fail red, warning yellow, in every project";
        :>> createdAt = "2026-09-03"; :>> createdBy = "claudeOpus5";
        :>> asA = "a human reading keel's gate output";
        :>> iWant = "PASS, FAIL, WARN, ERROR and the control-defect notes coloured in the terminal, in the binary every project runs";
        :>> soThat = "I can tell passing from failing without reading each line, and no project has to configure it";
        :>> implication = ImplicationKind::implementationChange;
        :>> triageNote = "Colour only when stdout is a terminal (NO_COLOR and KEEL_COLOR respected), so every text-parsing consumer - hooks, CI, tests, land - sees the same bytes; the words never change. Chat cannot carry colour, so the tool is where it lives.";
    }
    #DerivedFrom dependency from us074 to st072;

    part st073 : Statement {
        :>> id = "e4507698-fe31-4acc-9d14-421f56b5e487";
        :>> title = "Remove exec-summary as a process";
        :>> createdAt = "2026-09-03"; :>> createdBy = "claudeOpus5";
        :>> text = "remove exec-summary as a process";
        :>> saidBy = "wweatherholtz"; :>> saidAt = "2026-09-03"; :>> channel = StatementChannel::chat;
    }

    part us075 : UserStory {
        :>> id = "4f168112-eb13-47aa-8b74-04c0d00e8d9d";
        :>> title = "The engine does not carry exec-summary";
        :>> createdAt = "2026-09-03"; :>> createdBy = "claudeOpus5";
        :>> asA = "the owner of the engine";
        :>> iWant = "the exec-summary process, skill, template and unit record gone from the engine, with decision-surfacing rendering its own page";
        :>> soThat = "one process states how a decision reaches me, and the engine ships nothing it does not use";
        :>> implication = ImplicationKind::process;
        :>> triageNote = "Executed as D0288 the same hour: files deleted, unit record and id removed, five dependents rewritten with no tombstones; the library's published copy at v3 is untouched and said so.";
    }
    #DerivedFrom dependency from us075 to st073;

    part st074 : Statement {
        :>> id = "e6271ffc-3ebc-4b3d-ade4-392ebbb253ed";
        :>> title = "Quoted user text is authoritative for acceptance - an explicit exception until a better non-local channel exists";
        :>> createdAt = "2026-09-03"; :>> createdBy = "claudeOpus5";
        :>> text = "i want an exception for user text that was quoted to be authoritative.  yes i know AI could misquote me, but they could go modify the keel files also and they're not doing that.  so permit it - workflow is awful if i need to go to terminal to type acceptance directly on everything.  until we have a better non-local authoritative channel for providing feedback that isn't github issues, i just want to have that exception in place";
        :>> saidBy = "wweatherholtz"; :>> saidAt = "2026-09-03"; :>> channel = StatementChannel::chat;
    }

    part us076 : UserStory {
        :>> id = "be390b82-0c69-4a93-83e4-1737141d5935";
        :>> title = "The accept command honours the recording delegation the policy already declares";
        :>> createdAt = "2026-09-03"; :>> createdBy = "claudeOpus5";
        :>> asA = "the human who accepts decisions in chat";
        :>> iWant = "an acceptance I give in chat, quoted verbatim, to be recordable by the agent without my going to a terminal or GitHub";
        :>> soThat = "the workflow stops stalling on a gesture the policy stopped requiring on 2026-08-22";
        :>> implication = ImplicationKind::implementationChange;
        :>> triageNote = "The delegation already existed (D0192 option A, attestation-policy.toml decisionAcceptance.delegatedRecording) and the substance rule already demanded the quote; only cmd_accept's channel layer (D0178/P1.3) refused every agent session regardless. D0289 makes the command honour the declared policy: quoted note -> recorded citing the delegation; unquoted -> refused and told to quote; delegation withdrawn -> refused as before. The human's stated limit is D0192's stated limit, and the withdrawal is one deleted line.";
    }
    #DerivedFrom dependency from us076 to st074;

    part st075 : Statement {
        :>> id = "3aca8bab-9917-4548-9019-edb3f3b63e8d";
        :>> title = "D0289 supersedes layer 3 of D0178 - the human's authoritative word on the supersession";
        :>> createdAt = "2026-09-03"; :>> createdBy = "claudeOpus5";
        :>> text = "D0289 supersedes layer 3 of D0178: from an agent session, my words quoted verbatim in the acceptance note are the channel, under the D0192 delegation, until a better non-local channel exists";
        :>> saidBy = "wweatherholtz"; :>> saidAt = "2026-09-03"; :>> channel = StatementChannel::chat;
    }

    part us077 : UserStory {
        :>> id = "a0aae10a-733f-4630-a12d-e05a99c35865";
        :>> title = "A supersession is recorded as an edge and the human's word, never only as a deleted line";
        :>> createdAt = "2026-09-03"; :>> createdBy = "claudeOpus5";
        :>> asA = "the human whose word ends a delegation";
        :>> iWant = "D0289 to carry the supersede edge to D0178 layer 3 and my quote as its receipt, and every withdrawal in the policy to require a superseding Decision";
        :>> soThat = "what is in force is computable from the model, not remembered";
        :>> implication = ImplicationKind::process;
        :>> triageNote = "Recorded as D0290 with the receipt on D0289 and the four TO WITHDRAW comments rewritten.";
    }
    #DerivedFrom dependency from us077 to st075;

    part st076 : Statement {
        :>> id = "a809ec27-dfb7-4b15-9358-c2c568bbb18f";
        :>> title = "GH#53 keel accept writes --note bare, but acceptQuotesDelegatedWords needs a single-quoted span - so the one command only a human may run lands red";
        :>> createdAt = "2026-09-03"; :>> createdBy = "claudeOpus5";
        :>> text = "Observed on v0.3.1 in a downstream project that had just adopted the d0192 delegation.\n\n## What happened\n\nA human ran `keel accept <d> --note ''<their sentence>'' --by <person> --date <today>` six times, from their own terminal — the channel `D0178/K6` requires, and the reason the agent session could not do it for them.\n\nAll six wrote cleanly. `keel guard .` then went from ALL PASS to **six violations**, one per acceptance:\n\n```\nERROR dXXXX: accepted on/after the delegation cutoff but its acceptance event neither\nquotes the human's words (a single-quoted span) nor cites their gesture - a record made\nunder the d0192 recording delegation must carry its channel evidence\n```\n\n## Why\n\n`cmd_accept` writes `--note` verbatim into the acceptance event `procedureText`. `acceptQuotesDelegatedWords` (`keel-cli/src/view/checks.rs:132`) then reads that same field and requires `quotes_conversational_words` to hold — a **single-quoted span of >= 10 chars**, or a gesture word (`deck` / `console` / `github comment`).\n\nA note that is simply *what the human said* satisfies neither. It only passes if the human happens to type quote marks around their own sentence, which nothing tells them to do: the usage line reads\n\n```\n--note ''<what the human said>''\n```\n\nThe two halves are consistent in intent and incompatible in format, and the writer is the thing that knows which field it wrote.\n\n## Why this placement is the expensive one\n\nThis is `D0054` — a mandated path whose friction guarantees non-compliance — aimed at the single act the whole autonomous loop pauses for, and the one path with the least practice behind it because an AI is forbidden from taking it.\n\nThe failure mode is not the red build. It is that the human did the honest thing, in the sanctioned channel, and the tool told them no — with the diagnostic arriving later, from a different subsystem, in different words. The next person to hit this is invited to route around the *gate* rather than around the syntax.\n\n## Suggested fix, in preference order\n\n1. **`cmd_accept` quotes the note itself** when it writes `procedureText` (or appends a `channel: own terminal, via keel accept` citation). It is the writer; it knows the field and the channel. Zero burden on the human, and no format for anyone to remember.\n2. Have the predicate accept a distinct `note` attribute that `cmd_accept` writes, so the substance check reads a field designed for it rather than sniffing prose.\n3. At minimum, make `cmd_accept` **refuse at the point of use** with the same words the guard will later use — a wrong record never gets written, and the human learns the format from the tool rather than from a downstream gate.\n\nOption 1 alone would have made all six land green.\n\n## Downstream workaround\n\nDelimiters added to the six records and nothing else; the words are byte-identical, and each record states that an AI added the quotes after the fact under the delegation, so the provenance of the edit stays legible. A local suite test now fails the moment an acceptance is recorded without its evidence — but that is a downstream patch for an upstream format mismatch.";
        :>> saidBy = "williamweatherholtz"; :>> saidAt = "2026-09-03"; :>> channel = StatementChannel::github;
        :>> sourceUrl = "https://github.com/williamweatherholtz/sysmlv2-ai-toolkit/issues/53";
        :>> sourceTrust = SourceTrust::untrusted;
    }

    part st077 : Statement {
        :>> id = "5196354e-02f9-4f40-a61f-caaa278b530d";
        :>> title = "GH#52 Stop-hook advisory: configurable summary (outstanding-decisions count + exec summary) instead of the [oversight] nag";
        :>> createdAt = "2026-09-03"; :>> createdBy = "claudeOpus5";
        :>> text = "## What\nThe exit-0 advisory that `keel hook stop` emits every turn (`[oversight] N item(s) are waiting on the HUMAN...` + bridge/deck instructions) reads as noise to the project owner. Requested replacement format (owner's words: 'a single number indicating how many decisions are outstanding followed by an exec summary'):\n\n```\n17 decisions outstanding (d9001..d9017) - accept from your terminal: keel accept dNNNN --by will. Covering: landscapeProcessCharter, designBasisSupplyFlow, ...\n```\n\n## Why an issue and not a local patch\nThe obvious local fix - pointing the Stop hook at a wrapper script that runs `keel hook stop`, passes through any non-zero exit verbatim, and rewrites only the exit-0 advisory - is REFUSED by `guard:claude-surface-drift` ('settings.json: keel-owned entries differ from this binary's generator'), and the in-loop gate then blocks the turn. That protection is correct (issue236 self-modification class), which makes the advisory's CONTENT an engine decision. So: feature request.\n\n## Proposal\nEither a flag the generator emits (`keel hook stop --advisory decisions`) or a key in a project contract (e.g. `activation.toml [oversight] advisory = ''decisions''`), with the blocking path unchanged. A working reference implementation of the summary (count of `DecisionStatus::proposed` in the project band, id range, accept hint, slug list truncated at whole slugs) is committed in the landscape_plan project at `.claude/hooks/stop-summary.sh`, chartered there as d9018.\n\nRequested by the project owner in landscape_plan (st048/us074).";
        :>> saidBy = "williamweatherholtz"; :>> saidAt = "2026-09-03"; :>> channel = StatementChannel::github;
        :>> sourceUrl = "https://github.com/williamweatherholtz/sysmlv2-ai-toolkit/issues/52";
        :>> sourceTrust = SourceTrust::untrusted;
    }

    part st078 : Statement {
        :>> id = "ee22e7f6-f18c-4670-a266-3d53527fdff0";
        :>> title = "GH#51 Two builds of the same version silently disagree on the .claude surface; drift report names no binary";
        :>> createdAt = "2026-09-03"; :>> createdBy = "claudeOpus5";
        :>> text = "## What happens\n\nTwo builds of the same keel version generate different `.claude/` enforcement surfaces, and nothing in the drift report or the surface stamp lets you tell that a second binary is the cause. The result is a gate that blocks on `claude-surface-drift` while the CLI you are verifying with reports the surface clean.\n\nObserved on one machine, both binaries reporting `keel 0.3.1`:\n\n| | project wrapper (`./keelw` → `.keel/bin/0.3.1/`) | `keel` on PATH |\n|---|---|---|\n| build commit | `cf985ec+dirty` | `6eafa86+dirty` |\n| `keel sync-claude . --check` | `keel-owned subset matches this binary's generator` | `DRIFT: settings.json: keel-owned entries differ from this binary's generator` |\n\nThe generated hooks resolve `K=''${KEEL_BIN:-}''; ... || K=$(command -v keel)`. With `KEEL_BIN` unset, the gate runs the PATH binary while the operator runs the wrapper. Each build considers the other's surface drifted, so `sync-claude` from one immediately drifts the other.\n\n`.claude/.keel-surface` contains only `0.3.1` — the version, not the build — so the stamp cannot distinguish the two, and `keel --version` reports `claude surface: 0.3.1 (generated from this binary)` for both.\n\n## Why it matters\n\nThis is not just a nuisance in a dev tree. The failure mode is that **verification is performed against a binary that is not the one enforcing**, and nothing says so. In this session every `keel guard` / `keel validate` read-back was run with the wrapper binary while the gate ran the PATH binary. The guard verdicts happened to agree; the surface check did not. There is no general reason to expect two builds from different commits to agree, and the operator has no signal that they are comparing two different programs.\n\nAnyone developing keel while also using it on a project is in exactly this configuration.\n\n## Repro\n\n1. Have two builds of the same version from different commits — e.g. a release cached in `.keel/bin/<version>/` and a `cargo build --release` in the toolkit tree that is on PATH.\n2. Leave `KEEL_BIN` unset.\n3. `./keelw sync-claude . --check` → matches. `keel sync-claude . --check` → DRIFT.\n4. `echo '{}' | keel hook stop` blocks on `claude-surface-drift`; the wrapper binary reports the tree clean.\n\n## Suggested fix\n\nAny one of these would have collapsed the investigation from many steps to one:\n\n- Stamp the **build commit** into `.claude/.keel-surface`, not just the version.\n- Have the drift message name the path of the binary whose generator it is comparing against — `differ from this binary's generator (<abs path>, <commit>)`.\n- Have `sync-claude --check` warn when the stamped surface was generated by a build whose commit differs from the running one, even if the version matches.\n";
        :>> saidBy = "williamweatherholtz"; :>> saidAt = "2026-09-02"; :>> channel = StatementChannel::github;
        :>> sourceUrl = "https://github.com/williamweatherholtz/sysmlv2-ai-toolkit/issues/51";
        :>> sourceTrust = SourceTrust::untrusted;
    }

    part st079 : Statement {
        :>> id = "da81207a-f7fb-44f0-9b65-156a1be7a25c";
        :>> title = "GH#50 red-yield obligation truncates its captured diagnostic at a fixed 726 chars, mid-token";
        :>> createdAt = "2026-09-03"; :>> createdBy = "claudeOpus5";
        :>> text = "## What happens\n\nThe red-yield obligation auto-recorded by the Stop hook truncates its `description` at a fixed width, cutting the captured gate output mid-token. The field exists to preserve ''first problem at yield'', and it loses it.\n\nThree obligations recorded in one session, each **exactly 726 characters** in `description`:\n\n```\nred-yield-276a9da5.sysml: description chars = 726\nred-yield-53e2a772.sysml: description chars = 726\nred-yield-9486ed0b.sysml: description chars = 726\n```\n\nEach cuts mid-word, then appends the fixed `. Discharge:` tail:\n\n- `... [viewpoint-renderer] critique-policy: renderer . Discharge: make the tree green ...`\n- `... [viewpoint-renderer] decisions: renderer names. Discharge: make the tree green ...`\n\nIn both cases the diagnostic ends in the middle of the sentence that was about to say what was actually wrong.\n\n## Why it matters\n\nThe obligation is the only durable record of a gate state that has since changed. When the gate later goes green, the obligation is what a triage pass reads to decide whether the condition was real. A truncated capture makes that judgment impossible: in this session five `viewpoint-renderer` complaints were recorded, and the record cannot say what the fifth one was.\n\nIt also silently degrades the guard's own advice. The description ends with ''make the tree green'', but the reader cannot see the full list of what was red.\n\n## Repro\n\n1. Let the Stop hook go red and yield twice (loop avoidance) so an obligation is auto-recorded.\n2. `grep -o 'description = ''[^'']*''' .tracking/obligations/red-yield-*.sysml | wc -c` → 726 every time.\n\n## Suggested fix\n\nEither raise the cap well above realistic gate output, or truncate on a token boundary and mark it (`… [truncated, N more]`) so a reader knows content is missing rather than inferring a sentence ended.\n";
        :>> saidBy = "williamweatherholtz"; :>> saidAt = "2026-09-02"; :>> channel = StatementChannel::github;
        :>> sourceUrl = "https://github.com/williamweatherholtz/sysmlv2-ai-toolkit/issues/50";
        :>> sourceTrust = SourceTrust::untrusted;
    }

    part st080 : Statement {
        :>> id = "4eed05ce-2b1c-47b5-bd11-34615caf144a";
        :>> title = "GH#49 Deactivating a process turns off its guard but still deploys its SKILL, so an agent is advertised a channel the project switched off";
        :>> createdAt = "2026-09-03"; :>> createdBy = "claudeOpus5";
        :>> text = "Downstream project (Penumbra) on the released `v0.3.1` (`c4d5dbf`). Reported with thanks: **#183's refusal is fixed at this vintage** — `keel deactivate knowledge-graph-memory` now succeeds where 0.3.0 said the process asserts no guard. This is the residual one level along.\n\n## What happens\n\n```\n$ keel deactivate knowledge-graph-memory\ndeactivated `knowledge-graph-memory`. ...\n\n$ keel activation\n  [INACTIVE] knowledge-graph-memory  (1 guard(s))\n```\n\nThe process is off and its guard is off. But:\n\n```\n$ keel sync-claude . --check\nclaude-surface: keel-owned subset matches this binary's generator (41 registry skill(s))\n\n$ ls .claude/skills/knowledge-graph-memory/\nSKILL.md\n```\n\nThe skill is still deployed. `sync-claude` builds the surface from the skills **registry** and consults activation state nowhere.\n\n## Why this matters more than it looks\n\nGuards bind the *tool*. For an AI-operated project, the skill list is what actually steers the *agent* — it is the closest thing the model has to a set of instructions about what it may do. So after a deactivation:\n\n- an operator reading `keel activation` concludes the channel is closed;\n- an agent reading its own skill list concludes it is open, and has no way to learn otherwise, because a skill entry carries no activation state.\n\nThe disable is honest at the enforcement layer and misleading at the surface layer, and the surface layer is the one that changes agent behaviour.\n\n## Why a downstream project cannot patch around it\n\n- Deleting the deployed copy: undone by the next `sync-claude`.\n- Removing the registry entry: undone by the next `keel migrate` (it resyncs the registry from the binary — see #44).\n\nSo there is no durable local expression of ''this process is off, stop advertising it''.\n\n## Direction (yours)\n\nEither:\n\n- **Skip inactive processes' skills** when generating the surface — the state is already known to `sync-claude`'s own binary; or\n- **Deploy them stated** — keep the file but have the generated skill's description begin with its inactive state, so a model reading the list learns it before acting.\n\nThe second is probably safer: silently removing a skill file could look like drift to anything comparing the surface against the registry, and `guard:claude-surface-drift` currently byte-compares that surface (#46).\n\nSame family as #183: activation governs guards, and the question each time is what *else* it ought to govern.";
        :>> saidBy = "williamweatherholtz"; :>> saidAt = "2026-09-02"; :>> channel = StatementChannel::github;
        :>> sourceUrl = "https://github.com/williamweatherholtz/sysmlv2-ai-toolkit/issues/49";
        :>> sourceTrust = SourceTrust::untrusted;
    }

    part st081 : Statement {
        :>> id = "6ac1816a-0a99-4bdd-a9f6-1fbfedd12146";
        :>> title = "GH#48 keel append-result inserts the TestResult INSIDE a multi-line verification block, and the error it causes points at the wrong thing";
        :>> createdAt = "2026-09-03"; :>> createdBy = "claudeOpus5";
        :>> text = "Found on a downstream project (Penumbra) with the released `v0.3.1` (`c4d5dbf`).\n\n## What happens\n\n`keel append-result --file X --task T` inserts the new `TestResult` immediately after the line matching `verification <T>DoD : Test {`. That is correct when the DoD is a **one-liner** — which is what `keel add-task` writes, so most results land fine. Against a **multi-line** verification block it lands *inside* the block:\n\n```\n        verification shareThePacerBudgetDoD : Test {\n        part shareThePacerBudgetDoDR1 : TestResult { :>> id = ''...''; :>> outcome = VerdictKind::pass; ... }\n            :>> id = ''cf4328a0-5155-4488-ab1d-540323d98f7c'';\n            :>> method = VerificationMethod::test;\n            :>> procedureText = ''...'';\n        }\n```\n\nThe verification's own `:>> id` now sits *after* a nested part, so it is no longer read as the verification's identity.\n\n## Why it costs more than a bad edit\n\nThe diagnostic points somewhere else entirely:\n\n```\nERROR .tracking/backlog.sysml:34: shareThePacerBudgetDoD : Test carries NO `:>> id` —\nidentity is an immutable UUID (section 1.3); an item without one cannot be referenced,\nsuperseded or attested against\n```\n\nThe block plainly *has* an id, three lines down. So the reader goes looking for a missing UUID that is not missing, in a file the tool just edited, with no indication that the tool's own write caused it. `keel validate` also reports **clean** — the file parses; only the guard notices, and it names the wrong defect.\n\nIt is silent in the other direction too: 10 unrelated warnings disappeared while the item was malformed and returned when it was repaired, so the warning count moved for a reason nothing explained.\n\n## Repro\n\nAny project, with a multi-line DoD (hand-authored ones usually are):\n\n```\nverification fooDoD : Test {\n    :>> id = ''...'';\n    :>> method = VerificationMethod::test;\n    :>> procedureText = ''...'';\n}\n```\n\nthen `keel append-result --file <that file> --task foo --sha <sha> --verdict pass`.\n\n## Direction\n\nInsert after the verification block's **closing brace**, not after its opening line — the block end is findable by brace depth, counting only braces **outside string literals** (a `procedureText` containing `{` is common; that detail bit the downstream detector written for this, so it is worth stating).\n\nA cheaper interim guard: refuse to append when the matched `verification` line does not also close on that line, naming why, rather than writing into the middle of a block.\n\n## Workaround downstream\n\nMove the result (and any `// RAN:` receipt) out by hand, and a local test now fails whenever any `TestResult` sits inside a verification block, so the corruption is caught by a machine on the next commit rather than by someone reading a misleading diagnostic.";
        :>> saidBy = "williamweatherholtz"; :>> saidAt = "2026-09-01"; :>> channel = StatementChannel::github;
        :>> sourceUrl = "https://github.com/williamweatherholtz/sysmlv2-ai-toolkit/issues/48";
        :>> sourceTrust = SourceTrust::untrusted;
    }

    part st082 : Statement {
        :>> id = "c7d5b721-0a16-4262-99cf-387e927045a2";
        :>> title = "GH#47 A forward-only rule ships upstream's adoption date as a literal, so it is RETROACTIVE for every downstream project that migrates into it";
        :>> createdAt = "2026-09-03"; :>> createdBy = "claudeOpus5";
        :>> text = "Found on a downstream project (Penumbra) migrating 0.3.0 → 0.3.1 with the released `v0.3.1` (`c4d5dbf`, 54 guards). This is the general form of a specific bug, and the general form is the one worth fixing.\n\n## The mechanism\n\nTwo rules in `.engine/rules/rules.sysml` take their forward-only boundary as a predicate argument:\n\n```\ndelegatedAcceptanceSubstanceRule    predicate = ''acceptQuotesDelegatedWords(2026-08-22)''\ndelegatedConfirmationSubstanceRule  predicate = ''confirmationQuotesOrAttested(2026-08-23)''\n```\n\n`keel-cli/src/view/checks.rs:137` returns `Some(true)` for anything judged before the date, and both rules' comments say **''Forward-only (issue068)''**. The implementation is correct and the intent is right.\n\nThe problem is the *value*. Those two dates are **this engine's own** adoption dates — the days its author delegated recording (D0192) and granted standing consent (D0207). `keel migrate` installs them into a downstream project verbatim.\n\nSo a rule that is forward-only **for upstream** becomes **retroactive for every adopter**: it judges records the project made months before it adopted anything. Measured here:\n\n| cutoff | `guard:confirmation-authenticity` |\n|---|---|\n| the shipped dates | **73** violations of 90 scanned |\n| the adopting project's own adoption date | **0** of 90 |\n\nSame corpus, same binary. 73 records that assert a human judged something, failed for lacking evidence of a delegation that did not exist when they were made.\n\n## Why this is worse than a wrong default\n\nThe only honest ways out are both bad:\n\n- **Retro-quote the old acceptances.** This engine already forbids that, in the same file: `guards.rs:80`'s `LEGACY_ACTOR_CUTOFF` handling says pre-convention records are *''immutable history, NOT dischargeable (rewriting a judgedBy would falsify provenance)''*. Exactly right — and exactly the reason retro-evidencing an acceptance is falsification, not repair.\n- **Edit the shipped rule.** Which `migrate` then rewrites (`update rules/rules.sysml`), so the fix is undone by the next migration and the 73 failures return without warning.\n\nAn AI agent hitting this concludes, reasonably and wrongly, that the update cannot land without fabricating its human's words. That is the shape of the failure: the guard is right, the mechanism is right, and the shipped constant makes both of them say something false about a project that has adopted nothing yet.\n\n## Direction (yours)\n\nThe adopting project's adoption date is already knowable to the engine — `attestation-policy.toml` is where the delegation is *declared*, and `installed-units.toml` / the activation state record when a unit arrived. Any of:\n\n- **Derive the cutoff** from when *this* project's `attestation-policy` first declared `delegatedRecording` / `standingConsent`, rather than from a literal in the rule.\n- **Stamp it on adoption** — have `migrate` (or `process import`) write the *adopting* date into the rule when it installs the delegation, so the shipped file carries a placeholder rather than upstream's calendar.\n- **Treat pre-cutoff records the way `LEGACY_ACTOR_CUTOFF` already does** — counted warnings, explicitly not dischargeable — which would make the retroactive case harmless even when the date is wrong.\n\nThe first is the smallest true fix; the third is the safest fallback.\n\n## Workaround downstream, and its cost\n\nSet both cutoffs to the adopting project's own adoption date after every migration. Because `migrate` rewrites the file, that project now ships a detector (seven tests that fail by name when any pin resets) and an idempotent repair script — roughly 400 lines of machinery to hold one date in place. Two other payloads need the same treatment for #44's reasons, so it is three hand-repairs owed after every migration.\n\nRelated: #36 and #44 are also cases where migrate's treatment of a downstream project's own state differs from what the tool reports.";
        :>> saidBy = "williamweatherholtz"; :>> saidAt = "2026-09-01"; :>> channel = StatementChannel::github;
        :>> sourceUrl = "https://github.com/williamweatherholtz/sysmlv2-ai-toolkit/issues/47";
        :>> sourceTrust = SourceTrust::untrusted;
    }

    part st083 : Statement {
        :>> id = "79d065e5-5944-49cb-9152-565620dcba9d";
        :>> title = "GH#46 guard:claude-surface-drift byte-compares output-styles/keel.md against an embedded literal, so every fresh clone on Windows fails it";
        :>> createdAt = "2026-09-03"; :>> createdBy = "claudeOpus5";
        :>> text = "Found on a downstream project (Penumbra) during the fresh-worktree verify of a 0.3.0 → 0.3.1 migration, with the released `v0.3.1` build (`c4d5dbf`).\n\n## What happens\n\n`keel sync-claude` writes `.claude/output-styles/keel.md` with **LF**. `guard:claude-surface-drift` then byte-compares that file against the contract literal embedded in the binary. On Windows, git checks the file out with **CRLF** (no `.gitattributes` to say otherwise), so the bytes differ:\n\n```\nworking tree, just after sync-claude:  4100 b  (LF)\nfresh checkout of the same commit:     4173 b  (CRLF)\n```\n\n```\nERROR output-styles/keel.md differs from the embedded response contract\n[guard:claude-surface-drift] FAIL — 43 scanned, 0 warning(s), 1 violation(s)\n```\n\n## Why it's more than cosmetic\n\nThe failure is **invisible to the person who caused it and unavoidable for everyone else**:\n\n- The tree where `sync-claude` just ran **passes**. The same commit checked out fresh **fails**.\n- So a contributor lands a green commit, and every clone of it fails the gate — including CI and any fresh worktree.\n- The only apparent remedy is running `sync-claude` locally, which git re-dirties on the next checkout. That teaches contributors the guard is noise.\n- `sync-claude --check` reports `DRIFT` for a file whose *content* is byte-identical modulo line endings, so the message points at the response contract when nothing about the contract changed.\n\nWe hit it twice: once as `2 skill(s) missing or stale` (two `.engine`/`.claude` SKILL.md pairs that had drifted apart by exactly their line counts — 43 and 80 bytes on 43- and 80-line files), and once as the output-style violation above.\n\n## Repro\n\nOn Windows with default `core.autocrlf`, in any keel project:\n\n```\nkeel sync-claude .          # writes LF, guard passes\ngit add -A && git commit    # git stores LF\ngit worktree add ../fresh HEAD\ncd ../fresh && keel guard . # FAILS on output-styles/keel.md\n```\n\n## Direction (yours)\n\nAny of these closes it; the first is smallest:\n\n- **Compare normalised** — strip `/r` on both sides before the byte comparison, for the output style and for the `.engine`↔`.claude` skill pairs. Line endings are not part of the contract.\n- **Ship a `.gitattributes`** from `keel init` pinning `eol=lf` on the keel-owned surface, so what git materialises is what the binary embeds.\n- **Write platform-native** — have `sync-claude` write CRLF on Windows; weakest option, since it makes the stored bytes host-dependent.\n\nWorked around downstream with a local `.gitattributes` (`.claude/output-styles/*.md text eol=lf`), which took a fresh checkout from FAIL to ALL PASS. Same family as #36 and #44: a check whose precision differs from what it reports.";
        :>> saidBy = "williamweatherholtz"; :>> saidAt = "2026-09-01"; :>> channel = StatementChannel::github;
        :>> sourceUrl = "https://github.com/williamweatherholtz/sysmlv2-ai-toolkit/issues/46";
        :>> sourceTrust = SourceTrust::untrusted;
    }

    part st084 : Statement {
        :>> id = "871c0c47-fb57-4bc1-9fc8-6bfc595806b3";
        :>> title = "GH#45 adoption-check reports FAIL for every unit, and the reason it prints is a guard PASS line";
        :>> createdAt = "2026-09-03"; :>> createdBy = "claudeOpus5";
        :>> text = "`keel adoption-check` reports **FAIL for every unit, including known-good ones**, and the reason it prints is a guard **PASS** line relabelled as a failure.\n\nFound on `se-templates` with keel 0.3.1 (build `7c12f13+dirty`).\n\n## What it prints\n\n```\n  [1/1] asi-templates\nUNIT                WITHOUT it (never adopted)      WITH it (freshly imported)\nasi-templates       FAIL nothing was removed — ...  FAIL guard: [guard:control-map-reconciled] PASS — 0 scanned, 0 warning(s),\n\nadoption-check: 1 of 1 unit(s) FAILED.\n```\n\nThe `WITH it` reason is literally `FAIL guard: [guard:control-map-reconciled] PASS — 0 scanned, 0 warning(s),` — a guard **PASS** line captured and labelled FAIL.\n\n## The tree underneath is fine\n\nThe kept fixture (`--keep`) — a fresh foreign project that freshly imported the unit — is clean:\n\n- `keel validate <fixture>` → clean\n- `keel guard <fixture>` → **`[guard] ALL PASS`**, exit 0, no failing guard\n- `[guard:control-map-reconciled]` in the fixture → **PASS**, 0 violations\n- `[guard:manifest-key-portability]` → PASS across all 39 files\n- all 36 declared payload paths present\n\nSo the unit *is* transferable and the checker is wrong, not the tree.\n\n## Not unit-specific — control run\n\nRunning the same command against **`library-stewardship`** — engine-shipped, already published, known-good — fails the `WITH it` column with the **identical** message:\n\n```\nlibrary-stewardship   clean                           FAIL guard: [guard:control-map-reconciled] PASS — 0 scanned, 0 warning(s),\n```\n\nThat control run is what separates ''my unit is broken'' from ''the checker is broken''. Without it the honest report would have been the former, and it is false.\n\n## Second, separate defect\n\nFor a **project-authored** unit the `WITHOUT it` column also fails, reporting `nothing was removed — the fixture never carried this unit's files`. That is a true statement about the *fixture*, not about the unit: the scaffold ships only engine units, so removal cannot be exercised for a unit it never had. It should read **N/A**, not FAIL. (`library-stewardship` reads `clean` there precisely because the scaffold does carry it.)\n\n## Why this matters beyond cosmetics\n\n`adoption-check` is the **only** control that answers *''does this unit actually travel''*, and issue264 exists precisely because that question is invisible from inside the publishing repository. A control that returns FAIL for every unit — good or bad — carries no signal and trains its reader to skip it. That is the D0261 blindness mechanism, in the one place a publisher most needs a trustworthy answer.\n\n## Repro\n\n```\nkeel process publish <any-unit>\nkeel adoption-check . --unit <any-unit>          # FAIL, reason is a PASS line\nkeel adoption-check . --unit library-stewardship # same FAIL, known-good unit\nkeel adoption-check . --unit <any-unit> --keep   # then gate the fixture: ALL PASS, exit 0\n```\n\n---\n\nTracked downstream as `issue008` (Medium) in `asirobots/se-templates`, with resolver\n`adoptionCheckTrusted`, whose DoD requires the check be shown able to **fail** on a deliberately\nbroken unit — not merely to stop failing on good ones.\n";
        :>> saidBy = "williamweatherholtz"; :>> saidAt = "2026-08-31"; :>> channel = StatementChannel::github;
        :>> sourceUrl = "https://github.com/williamweatherholtz/sysmlv2-ai-toolkit/issues/45";
        :>> sourceTrust = SourceTrust::untrusted;
    }

    part st085 : Statement {
        :>> id = "5b03ebd7-9631-4b84-aa43-7f1aad440fc0";
        :>> title = "GH#44 keel migrate silently deletes project-authored sections in engine-shipped contract files (a published unit lost its declared payload)";
        :>> createdAt = "2026-09-03"; :>> createdBy = "claudeOpus5";
        :>> text = "`keel migrate` rewrites engine-shipped `.engine/contracts/` files wholesale, which **silently deletes project-authored sections in them**. A published unit lost its declared payload this way and nothing reported it.\n\nFound on `se-templates` migrating 0.3.0 → 0.3.1 with keel 0.3.1 (build `7c12f13+dirty`).\n\n## What happened\n\nThe project had authored an `[exec-summary]` section in `.engine/contracts/unit-extras.toml`:\n\n```toml\n[exec-summary]\nfiles = [\n  ''templates/exec-summary/exec-summary.html'',\n  ''tests/exec_summary/test_exec_summary.py'',\n]\n```\n\n`exec-summary v1` was published to the library carrying exactly those extras — confirmed in the library clone's `exec-summary/unit.toml`:\n\n```toml\nextras = [''templates/exec-summary/exec-summary.html'', ''tests/exec_summary/test_exec_summary.py'']\n```\n\nAfter `keel migrate .`, that section was **gone**. Verified:\n\n```\ngit diff <pre-migration-sha> <migration-sha> -- .engine/contracts/unit-extras.toml\n```\n\n```diff\n-[exec-summary]\n-files = [\n-  ''templates/exec-summary/exec-summary.html'',\n-  ''tests/exec_summary/test_exec_summary.py'',\n-]\n```\n\n## Why it was silent\n\nThree separate things had to fail to notice, and all three did:\n\n1. **The dry-run gave no signal.** `keel migrate . --dry-run` reported the file as\n   `.engine/contracts/unit-extras.toml (1 edit(s)) / update contracts/unit-extras.toml` — one\n   unnamed edit, indistinguishable from a routine content refresh.\n2. **The PRESERVED note does not cover this case.** The plan warns about files *the binary does not\n   ship* (it correctly listed two such files and preserved them). It says nothing about authored\n   content *inside* a file the binary does ship — which is the case that loses data.\n3. **Nothing reconciled before against after.** `0 blocker(s)`, and every gate passed afterwards.\n   `keel validate`, `keel guard`, `keel check-engine` were all clean with the section destroyed.\n\n## Consequence if unnoticed\n\n`keel process show exec-summary` then reports a unit carrying three files, and the next\n`keel process publish` ships a unit **stripped of its template and test suite** — the receiving\nproject gets the discipline with the machinery gone. That is the D0219 ''teeth stay behind'' failure\nthat `unit-extras.toml` exists to prevent, reintroduced by the upgrade rather than by an author.\n\nIt was caught only because the publish output was reconciled by hand afterwards (39 exported vs 36\ndeclared + 3 definition files).\n\n## Class\n\nThis is the silent-miss class the project's own `migration` process names — *counts catch misses,\nhashes catch corruption* — and neither control is applied to authored content in engine-shipped\ncontract files.\n\n## Affects\n\nAny project that declares its own sections in an engine-shipped `.engine/contracts/` file.\n`unit-extras.toml` is the one with teeth, but the same overwrite applies to every shipped contract.\n\n## Suggested fix\n\nGive `migrate` the refusal shape it **already has** for removed types: rather than overwriting,\neither reconcile authored sections into the new file, or refuse and list exactly what it would\ndiscard. Minimum viable improvement: make the dry-run name authored sections it is about to remove,\nso ''1 edit'' cannot hide a deletion.\n\n---\n\nTracked downstream as `issue007` (High) in `asirobots/se-templates`, with resolver\n`unitExtrasSurviveMigrate` — a project-side detection built because the loss lands in the project\nregardless of when this is fixed upstream.\n";
        :>> saidBy = "williamweatherholtz"; :>> saidAt = "2026-08-31"; :>> channel = StatementChannel::github;
        :>> sourceUrl = "https://github.com/williamweatherholtz/sysmlv2-ai-toolkit/issues/44";
        :>> sourceTrust = SourceTrust::untrusted;
    }

    part st086 : Statement {
        :>> id = "641f0517-7c3e-4ed7-8154-ef863f7cd550";
        :>> title = "GH#43 The generated hooks resolve keel from PATH, so a project's turns can run a different (and uncommitted) engine vintage than its gates";
        :>> createdAt = "2026-09-03"; :>> createdBy = "claudeOpus5";
        :>> text = "Found in a downstream project pinned to 0.3.0 on purpose.\n\n## The shipped resolution\n\nEvery hook `claude_surface` generates opens with:\n\n```sh\nK=''${KEEL_BIN:-}''; { [ -n ''$K'' ] && [ -x ''$K'' ]; } || K=$(command -v keel 2>/dev/null);\n[ -n ''$K'' ] || { echo '[keel] keel binary NOT FOUND - this gate did not run. ...' >&2\n```\n\n`KEEL_BIN` if set, otherwise whatever is on PATH. Reasonable in isolation — but on a machine that also *develops* keel, PATH finds the development build.\n\n## What that produced here\n\nThat project pins 0.3.0 deliberately (a migrate blocker keeps it there) and resolves the pinned binary first in its own pre-commit gate. But `KEEL_BIN` was unset, so:\n\n| path | binary | version |\n|---|---|---|\n| pre-commit gates | project-pinned | **0.3.0**, 55 guards |\n| `UserPromptSubmit` / `PreToolUse` / `Stop` hooks | PATH | **0.3.1, build `7c12f13+dirty`**, 56 guards |\n\nSo two engine vintages participate in a single turn, and the prompt-path one is **another session's uncommitted work-in-progress**, rebuilt while that session works. The guard counts already differ (56 vs 55).\n\n## How it surfaced, which is the part worth noting\n\nThe project decided to turn recall off. Its pinned binary contains neither the string `KEEL_RECALL` nor `keel recall` — the feature does not exist in that vintage at all. Yet recall had been injecting facts into every prompt. The feature was arriving entirely from the PATH binary. Nobody had chosen that; nothing reported it.\n\nA pin that covers the gates and not the prompt is a pin the project believes it has and does not.\n\n## Suggested direction\n\n- Have the generated hooks prefer a **project-local** binary when one exists (the same PINNED-FIRST order the pre-commit gate already uses), before falling back to PATH.\n- Or have `keel version` / `keel guard` report the resolved path and version *per hook family*, so a mismatch is visible rather than inferred from a missing string in a binary.\n- At minimum: the ''keel binary NOT FOUND'' message tells the reader to set `KEEL_BIN`; the silent success case never says which binary won, and that is the case that misleads.\n\nMedium severity downstream: it is not a wrong answer, it is an unknown provenance for every hook-mediated behaviour, including gates.";
        :>> saidBy = "williamweatherholtz"; :>> saidAt = "2026-08-31"; :>> channel = StatementChannel::github;
        :>> sourceUrl = "https://github.com/williamweatherholtz/sysmlv2-ai-toolkit/issues/43";
        :>> sourceTrust = SourceTrust::untrusted;
    }

    part st087 : Statement {
        :>> id = "02a4b9fd-b87e-480c-8600-aa735f47cd12";
        :>> title = "GH#42 The documented off-switch for a guardless process refuses, leaving only the switch the same docs say is not a project decision";
        :>> createdAt = "2026-09-03"; :>> createdBy = "claudeOpus5";
        :>> text = "Verified against 0.3.1 (build 7c12f13) and against a scratch-built 0.3.0.\n\n## What the source promises\n\n`recalled_facts` in `keel-cli/src/main.rs` documents three ways to turn recall off and names the first as the one to use:\n\n> 1. `keel deactivate knowledge-graph-memory` — the DECLARED off. The process is a deactivatable unit (D0138), so the switch is committed, auditable, and travels with the project. **This is the one to use: a project that turned recall off has DECLARED it, rather than having it quietly not work.**\n> 2. `KEEL_RECALL=off` — the immediate, machine-local off … **Deliberately env-based so it cannot be mistaken for a project decision.**\n\n## What happens\n\n```\n$ keel deactivate knowledge-graph-memory\nerror: `knowledge-graph-memory` is a declared process but asserts no guard, so there is\nnothing for deactivate to switch. Activation governs GUARDS (D0138). To stop running this\nprocess, remove the facts it authors -- a process whose inputs are absent produces nothing.\n```\n\nSo option 1 — the one the docs single out precisely *because* it is declared rather than machine-local — cannot run for this process. `keel activation` shows why: `[always] knowledge-graph-memory (asserts no guard — nothing to switch off)`.\n\nThat leaves only option 2, which the same paragraph says must not be mistaken for a project decision. A project that has genuinely decided to turn recall off has no declared way to say so.\n\n## Why the suggested alternative isn't one\n\n''Remove the facts it authors'' would have us delete authored content in order to silence an input channel. Those are different acts with different consequences — and for a corpus-derived store (D0243) the facts in question are the project's own `.tracking` model, which exists for other reasons entirely.\n\n## What we did instead\n\nDeclared `KEEL_RECALL=off` in the project's committed `.claude/settings.json` `env` block, which gives the env mechanism option 1's auditability — it travels with the project and is visible in review. That works, but it is a workaround for a documented path that refuses.\n\n## Suggested direction\n\nEither let activation govern a guardless process's **participation** as well as its guards, so `deactivate` means what the docs promise; or, if that conflicts with D0138's scope, correct the documentation so it stops recommending a command that cannot run — and say plainly that the env var is the only switch, in which case its ''cannot be mistaken for a project decision'' framing needs rethinking too.\n\nLow severity: there is a working path. Filed because the docs and the behaviour disagree, and the docs are the more persuasive of the two.";
        :>> saidBy = "williamweatherholtz"; :>> saidAt = "2026-08-31"; :>> channel = StatementChannel::github;
        :>> sourceUrl = "https://github.com/williamweatherholtz/sysmlv2-ai-toolkit/issues/42";
        :>> sourceTrust = SourceTrust::untrusted;
    }

    part st088 : Statement {
        :>> id = "2b0e67d5-d977-42de-827f-6fbe0a02de9f";
        :>> title = "Disconnect the GitHub decision channel - no issue notifications";
        :>> createdAt = "2026-09-03"; :>> createdBy = "claudeOpus5";
        :>> text = "i don't want github issue notifications. disconnect that pipeline.  it wasn't really doing anything anyway, no?";
        :>> saidBy = "wweatherholtz"; :>> saidAt = "2026-09-03"; :>> channel = StatementChannel::chat;
    }

    part us078 : UserStory {
        :>> id = "d10e7434-12d1-4e75-be55-d8d2cbb20d7e";
        :>> title = "GH#42: deactivating a guardless process refuses";
        :>> createdAt = "2026-09-03"; :>> createdBy = "claudeOpus5";
        :>> asA = "a downstream keel project (reporter: williamweatherholtz)";
        :>> iWant = "keel deactivate to work for a process that asserts no guard";
        :>> soThat = "the documented, committed off-switch is the one that works";
        :>> implication = ImplicationKind::bug;
        :>> triageNote = "UNTRUSTED (public repo): plan only. Per GH#49 (same reporter) this refusal is FIXED at v0.3.1 - deactivate knowledge-graph-memory succeeds. RECOMMEND: verify on a scaffold, close #42 as resolved-at-0.3.1 with the commit named.";
    }
    #DerivedFrom dependency from us078 to st087;

    part us079 : UserStory {
        :>> id = "755892ee-6c9a-4d66-9522-d38c7fe8865e";
        :>> title = "GH#43: hooks resolve keel from PATH, so turns can run a different vintage than gates";
        :>> createdAt = "2026-09-03"; :>> createdBy = "claudeOpus5";
        :>> asA = "a downstream keel project (reporter: williamweatherholtz)";
        :>> iWant = "the generated hooks to resolve the PINNED binary (.keel/bin) before PATH, as the git hooks already do";
        :>> soThat = "a project's turns and gates run the same engine";
        :>> implication = ImplicationKind::bug;
        :>> triageNote = "UNTRUSTED: plan only. Real and precise: the pre-commit hook resolves .keel/bin first (D0230) while claude_surface's hooks resolve PATH first - two resolution orders for one pin. RECOMMEND: fix in claude_surface.rs (one line per hook template) + a test; High, because a turn gated by a different binary than the commit is the D0251 skew the pin exists to prevent.";
    }
    #DerivedFrom dependency from us079 to st086;

    part us080 : UserStory {
        :>> id = "0866fb6f-a480-41c3-a5f8-31c5d2772c90";
        :>> title = "GH#44: migrate deletes project-authored sections in engine-shipped contract files";
        :>> createdAt = "2026-09-03"; :>> createdBy = "claudeOpus5";
        :>> asA = "a downstream keel project (reporter: williamweatherholtz)";
        :>> iWant = "keel migrate to preserve or refuse over project-authored sections in .engine/contracts files it resyncs";
        :>> soThat = "a published unit does not lose its declared payload silently";
        :>> implication = ImplicationKind::bug;
        :>> triageNote = "UNTRUSTED: plan only. Adjacent to issue314 (project-owned contracts survive resync) - unit-extras.toml is partly engine, partly project. RECOMMEND: treat sections keyed by a project's own unit as project-owned in is_project_owned_contract, or refuse with the section named; High (data loss, silent).";
    }
    #DerivedFrom dependency from us080 to st085;

    part us081 : UserStory {
        :>> id = "d6bacb6f-5a08-49af-92ef-d9477b820ac3";
        :>> title = "GH#45: adoption-check FAILs every unit and cites a guard PASS line as the reason";
        :>> createdAt = "2026-09-03"; :>> createdBy = "claudeOpus5";
        :>> asA = "a downstream keel project (reporter: williamweatherholtz)";
        :>> iWant = "adoption-check to report the actual failing check, and PASS when the foreign gate is green";
        :>> soThat = "a green unit is not reported red";
        :>> implication = ImplicationKind::bug;
        :>> triageNote = "UNTRUSTED: plan only. Likely the issue329 class (a substring test on guard output) in adoption_check.rs. RECOMMEND: parse the verdict line, not its text; a fixture with a green unit must report PASS; High (a gate that is always red is routed around, D0214).";
    }
    #DerivedFrom dependency from us081 to st084;

    part us082 : UserStory {
        :>> id = "9b50a77c-d726-4497-9c76-9d2eeaefa346";
        :>> title = "GH#46: claude-surface-drift byte-compares keel.md, so every fresh Windows clone fails it";
        :>> createdAt = "2026-09-03"; :>> createdBy = "claudeOpus5";
        :>> asA = "a downstream keel project (reporter: williamweatherholtz)";
        :>> iWant = "the drift check to compare line-ending-normalised content, or sync-claude to write what git will check out";
        :>> soThat = "a Windows clone is not red on arrival";
        :>> implication = ImplicationKind::bug;
        :>> triageNote = "UNTRUSTED: plan only. CRLF vs LF on the embedded literal. RECOMMEND: normalise line endings on both sides of the comparison in guards.rs claude_surface_drift; Medium-High (every Windows adopter hits it first).";
    }
    #DerivedFrom dependency from us082 to st083;

    part us083 : UserStory {
        :>> id = "57de4d22-2854-4beb-8ec8-0f15d515d7d5";
        :>> title = "GH#47: a forward-only rule ships upstream's adoption date, so it is retroactive downstream";
        :>> createdAt = "2026-09-03"; :>> createdBy = "claudeOpus5";
        :>> asA = "a downstream keel project (reporter: williamweatherholtz)";
        :>> iWant = "forward-only cutoffs to be the ADOPTING project's date, not the engine's";
        :>> soThat = "a downstream project is not retro-failed on the day it migrates";
        :>> implication = ImplicationKind::bug;
        :>> triageNote = "UNTRUSTED: plan only. The general form of issue068: predicate = acceptQuotesDelegatedWords(2026-08-22) is this repo's date baked into a shipped rule. RECOMMEND: the cutoff comes from the project's own adoption record (activation date of the rule or the migration date), with the literal kept only as this repo's value; touches rules.sysml (keystone) and checks.rs; High.";
    }
    #DerivedFrom dependency from us083 to st082;

    part us084 : UserStory {
        :>> id = "034f13e3-cc0a-4f9e-8f26-50868050a4b8";
        :>> title = "GH#48: append-result inserts the TestResult inside a multi-line verification block";
        :>> createdAt = "2026-09-03"; :>> createdBy = "claudeOpus5";
        :>> asA = "a downstream keel project (reporter: williamweatherholtz)";
        :>> iWant = "append-result to insert after the block's closing brace, whether the DoD is one line or many";
        :>> soThat = "a result recorded by the API never breaks the file it is recorded into";
        :>> implication = ImplicationKind::bug;
        :>> triageNote = "UNTRUSTED: plan only. write.rs inserts after the line matching verification <T>DoD : Test { - correct only for one-liners. RECOMMEND: find the matching close brace; test with a multi-line DoD; High (the write API corrupting a file is the issue325 class).";
    }
    #DerivedFrom dependency from us084 to st081;

    part us085 : UserStory {
        :>> id = "70262bf8-78e4-4e90-a235-f00f1ceb7558";
        :>> title = "GH#49: deactivating a process leaves its SKILL deployed";
        :>> createdAt = "2026-09-03"; :>> createdBy = "claudeOpus5";
        :>> asA = "a downstream keel project (reporter: williamweatherholtz)";
        :>> iWant = "sync-claude to skip or mark the skills of deactivated processes";
        :>> soThat = "an agent is not advertised a channel the project switched off";
        :>> implication = ImplicationKind::designChange;
        :>> triageNote = "UNTRUSTED: plan only, and a FORK the reporter themselves frames: (A) skip inactive processes' skills, (B) deploy them with the inactive state written into the description. RECOMMEND (B), as the reporter leans: removal would read as drift to claude-surface-drift (GH#46) and a stated inactive skill teaches the model the state; Medium.";
    }
    #DerivedFrom dependency from us085 to st080;

    part us086 : UserStory {
        :>> id = "62aec0d1-ca9f-4a56-86d4-823af7c77083";
        :>> title = "GH#50: the red-yield obligation truncates its diagnostic at 726 chars mid-token";
        :>> createdAt = "2026-09-03"; :>> createdBy = "claudeOpus5";
        :>> asA = "a downstream keel project (reporter: williamweatherholtz)";
        :>> iWant = "the captured gate output preserved whole, or truncated at a line boundary with the truncation stated";
        :>> soThat = "the first problem at yield is actually preserved";
        :>> implication = ImplicationKind::bug;
        :>> triageNote = "UNTRUSTED: plan only. A fixed-width cut in the Stop hook's obligation writer. RECOMMEND: cut at a line boundary with a '... (N more lines)' marker, or no cut with the field allowed to be long; Low-Medium.";
    }
    #DerivedFrom dependency from us086 to st079;

    part us087 : UserStory {
        :>> id = "90f5987b-e48b-4502-a0f2-0d61aaa3893e";
        :>> title = "GH#51: two builds of the same version disagree on the .claude surface; the drift report names no binary";
        :>> createdAt = "2026-09-03"; :>> createdBy = "claudeOpus5";
        :>> asA = "a downstream keel project (reporter: williamweatherholtz)";
        :>> iWant = "the surface stamp and the drift report to carry the build commit, and the drift message to name both binaries";
        :>> soThat = "a second binary on the machine is diagnosable from the report";
        :>> implication = ImplicationKind::bug;
        :>> triageNote = "UNTRUSTED: plan only. Two 0.3.1 builds (cf985ec+dirty vs 6eafa86+dirty) generated different surfaces; version alone is not identity for a dirty build. RECOMMEND: stamp build commit into .keel-surface and print it in the drift message; Medium.";
    }
    #DerivedFrom dependency from us087 to st078;

    part us088 : UserStory {
        :>> id = "44cea2b6-3388-431f-855a-08f5d13198fb";
        :>> title = "GH#52: the Stop-hook advisory reads as noise; wanted a configurable one-line summary";
        :>> createdAt = "2026-09-03"; :>> createdBy = "claudeOpus5";
        :>> asA = "a downstream keel project (reporter: williamweatherholtz)";
        :>> iWant = "the exit-0 advisory replaced by a short configurable summary: outstanding decisions and how to accept";
        :>> soThat = "the turn-boundary message is read instead of skimmed past";
        :>> implication = ImplicationKind::designChange;
        :>> triageNote = "UNTRUSTED: plan only. The reporter quotes the owner's wanted format. Partly moot after D0291 (record-time consent leaves far fewer outstanding decisions) and D0289 (accept by quoted word). RECOMMEND: one line - N decisions outstanding, names, and 'accept with your word or keel accept' - with the console nag dropped; Low.";
    }
    #DerivedFrom dependency from us088 to st077;

    part us089 : UserStory {
        :>> id = "1e98d48f-85d9-45e3-876c-3b54c5521761";
        :>> title = "GH#53: keel accept from a TTY writes the note bare, so the human's own command lands red";
        :>> createdAt = "2026-09-03"; :>> createdBy = "claudeOpus5";
        :>> asA = "a downstream keel project (reporter: williamweatherholtz)";
        :>> iWant = "a TTY-run accept to satisfy the substance rule by construction - the TTY IS the human gesture";
        :>> soThat = "the one command only a human may run does not fail the gate it exists to pass";
        :>> implication = ImplicationKind::bug;
        :>> triageNote = "UNTRUSTED: plan only, but this is the mirror of D0289: the rule wants a quoted span or a cited gesture, and a human typing at their own terminal supplied the gesture without the word. RECOMMEND: when stdin is a TTY, cmd_accept records the note with the gesture cited (TTY) so the rule is satisfied; High (six red acceptances on a downstream project, from the one path the docs told them to use).";
    }
    #DerivedFrom dependency from us089 to st076;

    part st089 : Statement {
        :>> id = "4affcaed-fa34-4908-ad37-c5acd0232c5b";
        :>> title = "Route all twelve intake issues as recommended - they are the owner's own reports";
        :>> createdAt = "2026-09-03"; :>> createdBy = "claudeOpus5";
        :>> text = "all work. these are essentially from me";
        :>> saidBy = "wweatherholtz"; :>> saidAt = "2026-09-03"; :>> channel = StatementChannel::chat;
    }
    // Routing of the twelve downstream issues on the owner's word (D0292): story -> Issue, story -> the accepting Decision.
    #Implicates dependency from us079 to issue348;
    #Implicates dependency from us079 to d0292;
    #Implicates dependency from us080 to issue349;
    #Implicates dependency from us080 to d0292;
    #Implicates dependency from us081 to issue350;
    #Implicates dependency from us081 to d0292;
    #Implicates dependency from us082 to issue351;
    #Implicates dependency from us082 to d0292;
    #Implicates dependency from us083 to issue352;
    #Implicates dependency from us083 to d0292;
    #Implicates dependency from us084 to issue353;
    #Implicates dependency from us084 to d0292;
    #Implicates dependency from us085 to issue355;
    #Implicates dependency from us085 to d0292;
    #Implicates dependency from us086 to issue356;
    #Implicates dependency from us086 to d0292;
    #Implicates dependency from us087 to issue357;
    #Implicates dependency from us087 to d0292;
    #Implicates dependency from us088 to issue358;
    #Implicates dependency from us088 to d0292;
    #Implicates dependency from us089 to issue359;
    #Implicates dependency from us089 to d0292;
    // GH#42 (us078): verified fixed at this vintage on a fresh scaffold - deactivate succeeds, activation reads INACTIVE; closed without an Issue.
    #Implicates dependency from us078 to d0292;
    #Implicates dependency from us090 to dcHooksOutsideTheAgentsWritePath;

    part st090 : Statement {
        :>> id = "0aff12e2-6161-405b-a8eb-8f0c2ad5639f";
        :>> title = "Would keel work better as an extension with forced pre/post hooks";
        :>> createdAt = "2026-09-03"; :>> createdBy = "claudeOpus5";
        :>> text = "would keel work better as an extension? forced pre post hooks?";
        :>> saidBy = "williamWeatherholtz"; :>> saidAt = "2026-09-03"; :>> channel = StatementChannel::chat;
    }

    part us090 : UserStory {
        :>> id = "16096387-01a8-4571-8140-4c8f174617d8";
        :>> title = "Host the keel hooks where the agent cannot rewrite them";
        :>> createdAt = "2026-09-03"; :>> createdBy = "claudeOpus5";
        :>> asA = "human directing an agent through keel";
        :>> iWant = "the pre/post hooks that gate the agent to be forced - hosted where the agent they gate cannot edit or silence them";
        :>> soThat = "the in-loop tier is a control, not a convention the controlled party maintains";
        :>> implication = ImplicationKind::architecture;
        :>> triageNote = "st090 asks whether keel would work better as an extension with forced pre/post hooks. Routed as ARCHITECTURE, plan-only: a spike ranks the hosts (repo settings, plugin, plugin+self-guarding deny hook, managed settings) by who can write them; the concrete gap found while checking - disableAllHooks from any scope, unseen by the drift guard - is issue365 with its own resolver.";
    }
    #DerivedFrom dependency from us090 to st090;

    part st091 : Statement {
        :>> id = "3eca90dd-54c2-431d-81b0-70a10c7765ed";
        :>> title = "Pull the hook-hosting spike forward and run it";
        :>> createdAt = "2026-09-03"; :>> createdBy = "claudeOpus5";
        :>> text = "we do. go";
        :>> saidBy = "williamWeatherholtz"; :>> saidAt = "2026-09-03"; :>> channel = StatementChannel::chat;
    }
}
