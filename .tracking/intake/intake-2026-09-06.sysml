// Intake for 2026-09-06 — their words, my translation, the triage verdict (D0166/D0216).
// Written by `keel record statement` / `keel record story` (D0236): a Statement's text is
// VERBATIM, so it is escaped for the literal and otherwise untouched.
package ProjectIntake20260906 {
    private import EngineElement::*;
    private import EngineIntake::*;
    private import EngineRelationships::*;

    part st092 : Statement {
        :>> id = "a1189fc6-aa2d-4182-90f0-dac6b6d60364";
        :>> title = "GH#59 keel migrate: a removed type NAMED IN PROSE blocks migration - the scanner reads string literals, and Rust's :: satisfies its typed-as test";
        :>> createdAt = "2026-09-06"; :>> createdBy = "githubRecorder";
        :>> text = "`keel migrate` refuses a healthy project because a removed type is **named in prose** inside an authored `description`. The scanner reads string literals as if they were schema, and Rust's path separator `::` satisfies its ''typed as'' test.\n\n## Repro\n\nAn authored issue in a downstream project records a critic's finding that quotes Rust:\n\n```sysml\npart i : Issue {\n    :>> description = ''get() uses a concrete ureq::Agent with no injection point, so the\n                       429-decrement, 503+Retry-After, reauth-429 and give-up arms have\n                       no executing test.'';\n}\n```\n\n`keel migrate . --dry-run` then reports:\n\n```\n  → [removed-types] Instances of REMOVED engine types (no mechanical transform)\n      BLOCKED .tracking/issues.sysml:1187 — `Agent` no longer exists in the engine schema:\n              :>> description = ''tS7_2's procedure promises a fabricated-response walk...\n              advice: removed as dead schema (D0142). An AI actor is `Actor` with\n                      `kind = ActorKind::ai` (D0129).\n\n  totals: 419 file(s), 419 edit(s), 1 blocker(s)\n\nkeel migrate: REFUSING — 1 item(s) have no mechanical transform (listed above).\n```\n\nThere is no `part x : Agent` anywhere in the tree — `grep -nE '': *Agent/b''` matches only that one description string.\n\n## Root cause\n\n`types_as` (`keel-cli/src/migrate.rs:267`) decides a line ''types as'' a name when the text before the match, trimmed, ends with `:` or `:>`, and the identifier boundaries hold on both sides.\n\nFor `ureq::Agent` every condition is satisfied:\n\n- text before the match is `... uses a concrete ureq::`, which trims to something ending in `:` → `before_ok`\n- the character immediately before `Agent` is `:`, not an identifier char → `left_ok`\n- the character after is a space → `after_ok`\n\nSo a Rust path separator is indistinguishable from a SysML typing colon to this matcher. `step_removed_types` (`migrate.rs:587`) then scans **every line in full**, including quoted string literals, so authored prose is parsed as a declaration. `REMOVED_ENUMS` in the same loop has the same exposure via `line.contains(''{en}::'')`.\n\n## Why this is worth fixing rather than working around\n\nThe three available workarounds are all bad:\n\n1. **Edit the description** to remove the word — falsifies a recorded finding. The text is a critic's own words about a real defect; rewriting it to appease a scanner corrupts the record the project exists to keep.\n2. **Re-add `part def Agent`** in the project's own `.engine/schema/`, which the advice suggests — adds a dead type to the schema purely to silence a false positive.\n3. **Skip migrate** — leaves the project unable to move vintage at all.\n\nThere is no `--force`, no per-item override, and no allowlist: `keel migrate [--dry-run] [ROOT]` is the whole surface. So one quoted word in one description permanently blocks migration.\n\nThe blast radius is wider than `Agent`. Any authored prose quoting a foreign symbol whose last path segment matches `REMOVED_TYPES` hits this — `Assumption`, `Risk`, `Mitigation`, `Task`, `Epic`, `Role`, `DesignElement`, `ComponentRequirement`. `Task` and `Risk` in particular are ordinary words that appear constantly in descriptions, and `std::task`, `tokio::task` or any `foo::Task` in a quoted code reference would block just as this did.\n\n## Suggested fix\n\nBlank double-quoted string literals before scanning, in `step_removed_types` only. A SysML type annotation never appears inside a string literal, so this is precise: a **qualified reference outside quotes still matches**, and prose stops being read as a declaration.\n\n```rust\n/// Blank out double-quoted string literals, preserving structure.\n///\n/// The removed-type and removed-enum scanners must read SCHEMA, not PROSE.\nfn without_string_literals(line: &str) -> String { /* ... */ }\n```\n\nthen in `step_removed_types`:\n\n```rust\nlet scan = without_string_literals(line);\nlet scan = scan.as_str();\nfor (ty, advice) in REMOVED_TYPES {\n    if types_as(scan, ty) { /* ... */ }\n}\nfor (en, advice) in REMOVED_ENUMS {\n    if scan.contains(&format!(''{en}::'')) { /* ... */ }\n}\n```\n\n## Verification\n\nImplemented and tested locally against `origin/main` at `d82c512`.\n\n- `cargo test --lib` — **344 passed, 0 failed**. The existing `old_vintage_tree_migrates_then_is_a_noop` arms still hold: the `Task` annotation still blocks, and the `RiskLevel::high` enum value still blocks.\n- Added a regression test, `a_removed_type_named_inside_a_string_literal_is_prose_not_schema`, with both arms — a removed type named in prose must not block, and the same type as a real `: Agent` annotation outside quotes must still block, so the fix cannot pass by simply never matching.\n- **Falsified**: making `without_string_literals` a passthrough makes that test fail with exactly the reason it names —\n\n  ```\n  a removed type NAMED IN PROSE must not block:\n    [''`Agent` no longer exists in the engine schema: part i : Issue { :>> description = /''get() uses a concrete ureq::Agent he...'']\n  ```\n\n- With the fix in place, `keel migrate . --dry-run` on the affected project proceeds past the blocker.\n\nHappy to open a PR with the fix plus the regression test if that is useful.\n\nFound while building `origin/main` (`d82c512`) to pick up D0269, so the report is against main rather than the v0.3.1 tag.\n";
        :>> saidBy = "williamweatherholtz"; :>> saidAt = "2026-09-04"; :>> channel = StatementChannel::github;
        :>> sourceUrl = "https://github.com/williamweatherholtz/sysmlv2-ai-toolkit/issues/59";
        :>> sourceTrust = SourceTrust::untrusted;
    }

    part st093 : Statement {
        :>> id = "b60c0671-bab5-4ce8-8a4e-b0c969287a35";
        :>> title = "GH#58 decision-issue.yml never bootstraps the keel-standing label the script requires, so the channel's first run in a new repo dies on gh issue create";
        :>> createdAt = "2026-09-06"; :>> createdBy = "githubRecorder";
        :>> text = "`open_decision_issues.py` opens its standing-consent thread with the label `keel-standing`, but `decision-issue.yml` only bootstraps `blocks-work` and `decision`. GitHub refuses an issue carrying an undeclared label, so `gh issue create` exits 1 and takes the whole step down.\n\n## The mismatch\n\n`.github/workflows/decision-issue.yml` creates two labels:\n\n```sh\ngh label create blocks-work --force --color B60205 --description ''...'' || true\ngh label create decision    --force --color 4C5FD7 --description ''...'' || true\n```\n\n`.github/scripts/open_decision_issues.py` needs a third:\n\n```python\nSTANDING_LABEL = ''keel-standing''\n...\ncreated = gh([''issue'', ''create'', ''--title'', STANDING_TITLE, ''--body-file'', ''body.md'',\n              ''--label'', ''decision'', ''--label'', STANDING_LABEL], check=True)\n```\n\n`check=True`, so the whole run dies:\n\n```\nsubprocess.CalledProcessError: Command '['gh', 'issue', 'create', '--title',\n'keel: decisions auto-accepted under standing consent', '--body-file', 'body.md',\n'--label', 'decision', '--label', 'keel-standing']' returned non-zero exit status 1\n```\n\nConfirmed by listing labels on the repo after the failure: `blocks-work` and `decision` present, `keel-standing` absent.\n\n## Why it is easy to miss\n\nIt only fires on a repo where the label does not already exist — i.e. the channel's **first ever successful run** in a new project. In the origin repo the label has existed since D0227, so nothing there reproduces it. It is also masked by the two earlier blockers: under an org Actions allowlist the run `startup_failure`s before any step (#38), and in a consuming project the `cargo build -p keel-cli` step fails before the label is reached (see the comment on #38). This is the third failure in the same chain, and each one hides the next.\n\nThe error is also unhelpful: `CalledProcessError` names the command but not the cause, so the reader sees a failed `gh issue create` with no indication that a label is missing.\n\n## Reproduce\n\n1. A repo with no `keel-standing` label and Actions able to run the channel.\n2. Trigger `decision-issue` with at least one proposed Decision present.\n3. Step `open an issue per proposed decision` fails at `standing_thread()`.\n\n## Fix\n\nOne line beside the other two:\n\n```sh\ngh label create keel-standing --force --color 0E8A16 /\n  --description ''keel standing-consent thread (D0207)'' || true\n```\n\nApplied locally and the step then went green, opening the thread as issue #1 with both labels.\n\nWorth considering more generally: the bootstrap and the script hold the label set in two places, so they can drift again. Deriving the labels the workflow creates from the script's own constants — or asserting at start-up that every label the script will use exists — would close the class rather than this instance.\n";
        :>> saidBy = "williamweatherholtz"; :>> saidAt = "2026-09-04"; :>> channel = StatementChannel::github;
        :>> sourceUrl = "https://github.com/williamweatherholtz/sysmlv2-ai-toolkit/issues/58";
        :>> sourceTrust = SourceTrust::untrusted;
    }

    part st094 : Statement {
        :>> id = "23251363-cbe9-475d-a376-fb3756417994";
        :>> title = "GH#57 decision-channel auto-accept records the acceptance as a hardcoded actor, quoting another project's human's standing words verbatim";
        :>> createdAt = "2026-09-06"; :>> createdBy = "githubRecorder";
        :>> text = "`decision-channel`'s auto-accept path records a human acceptance with **a hardcoded actor id** and **a hardcoded quotation of one specific human's standing consent**. Any project that imports the unit and runs the channel will record acceptances attributed to `wweatherholtz`, citing standing words that project's own supervisor never gave.\n\nThis is the class `guard:confirmation-authenticity` and D0106 exist to prevent — a fabricated attestation — arriving through the channel's own script.\n\n## The line\n\n`.github/scripts/record_decision.sh`, AUTO mode (read in the pristine library copy at `~/.keel/library/decision-channel/`, not in an adopting project, so this is upstream content and not local drift):\n\n```sh\nnote=''AUTO-ACCEPTED under standing consent (D0207). Their standing words, verbatim:\n'issues raised are automatically accepted. they can be customizedly changed post-fact.'\nNot individually reviewed; override anytime by replying 'reject <why>' on ${ISSUE_URL}.''\n''$KEEL'' accept ''$AUTO_DECISION'' --note ''$note'' --by wweatherholtz --date ''$today''\n```\n\nTwo independent problems in one statement:\n\n1. **`--by wweatherholtz` is hardcoded.** The project declares its deciders in `.engine/contracts/github-actors.toml`, and `keel github-decider <login>` resolves them — the script does not consult either. `keel process show decision-channel` even tells the receiving project to declare its own deciders, and then the accept path ignores them.\n2. **The quoted ''standing words, verbatim'' belong to a different project's human.** For any adopter, the record will contain a verbatim quotation of a consent that was never given in that project. A `--note` that quotes words the named person did not say is worse than an unattributed one, because it reads as evidence.\n\n## There is no consent gate, and no exemption for process changes\n\n`open_decision_issues.py` queues a Decision for auto-accept when it has no options:\n\n```python\nif not c[''options''] and standing_has(c[''cid'']):\n    print(f''{c['cid']} already on the standing thread'')\n    continue\n```\n\n`standing_has()` is **idempotency only** — its own docstring says so (''Idempotency for a re-run or the sweeper''). It asks whether the decision is already posted, never whether consent was granted. The standing thread's body states the model outright:\n\n> nothing here needs you … To reverse one, reply `reject dNNNN <why>` naming the decision.\n\nSo D0207 is opt-out by construction, and nothing distinguishes a `#ProspectiveChange` Decision from an ordinary one. In the project that found this, the three Decisions queued for auto-accept were:\n\n- `d0001` — the project's **process charter**\n- `d0002`, `d0003` — both **enforcement-surface** changes carrying the `#ProspectiveChange` marker\n\ni.e. exactly the class the keystone lock refuses to let an AI change unsigned would have been signed, by CI, in the supervisor's name, quoting someone else's consent.\n\n## What actually stopped it\n\nNothing that was a control. The first dispatch reached the auto-accept step and died on an unrelated `keel guard` failure (failing closed — that part is correct). After that failure was fixed, the only remaining obstacle was that push events do not trigger workflows in that repo — a bug, not a safeguard. Once either is resolved, the acceptances land.\n\n## Reproduce\n\n1. Import `decision-channel` into a project whose keel actor is not `wweatherholtz`.\n2. Declare a decider in `github-actors.toml` (any login → any local actor).\n3. Record a proposed Decision with no options: `keel record decision --from d.md`.\n4. Push it and let `decision-issue` run to the auto-accept step.\n5. The recorded acceptance names `wweatherholtz`, not the declared decider, and quotes standing words from another project.\n\n## Direction (yours)\n\n- Read the actor from `github-actors.toml` via `keel github-decider`, and refuse rather than default when it does not resolve — the same discipline the channel already applies to an unmapped commenter login (issue182).\n- Make the standing words **project-local data**, not a string in a portable script: recorded once by the human in their own words (the standing thread itself is the obvious home), and quoted from there or not at all.\n- Consider excluding marker-carrying Decisions (`#ProspectiveChange` / `#SafetyChange`) from standing consent. A project that hard-locks its enforcement surface against unsigned AI change is making a statement that auto-accept currently overrides.\n";
        :>> saidBy = "williamweatherholtz"; :>> saidAt = "2026-09-04"; :>> channel = StatementChannel::github;
        :>> sourceUrl = "https://github.com/williamweatherholtz/sysmlv2-ai-toolkit/issues/57";
        :>> sourceTrust = SourceTrust::untrusted;
    }

    part st095 : Statement {
        :>> id = "de82cf7d-1f73-4df5-b896-fadd89780fad";
        :>> title = "GH#56 keel migrate overwrites a project's chartered activation.toml with the engine's own, leaving charteredBy pointing at a Decision the project does not hold";
        :>> createdAt = "2026-09-06"; :>> createdBy = "githubRecorder";
        :>> text = "`keel migrate` overwrites `.engine/contracts/activation.toml` with the **engine's own** activation set. A project that has chartered its process set loses that charter, and `keel onboard` then reports the set as CHARTERED by a Decision the project does not contain.\n\nThis is the most damaging of the migrate side-effects because it is **silent and destructive**: it discards a recorded human decision about which controls apply, and nothing in the migrate output names it.\n\n## Measured\n\nProject `jama-rereviewer`, whose charter `d0001` adopted 8 processes and deliberately declined `deploy` and `distributed-collaboration`, each with a named adoption trigger.\n\nBefore `keel migrate .`:\n\n```toml\n[processes]\ncharteredBy = ''d0001''\nactive = [''actor-enrollment'', ''agile-workflow'', ''decision-channel'', ''doc-sync'',\n          ''element-critique'', ''issue-resolution'', ''knowledge-graph-memory'', ''render'']\n```\n\nAfter (untouched by hand, this is migrate's output):\n\n```toml\n[processes]\ncharteredBy = ''d0226''\nactive = [''actor-enrollment'', ''agile-workflow'', ''decision-authoring'', ''decision-channel'',\n          ''deploy'', ''distributed-collaboration'', ''doc-sync'', ''element-critique'',\n          ''issue-resolution'', ''knowledge-graph-memory'', ''render'']\n```\n\n`keel onboard .` → `process set: CHARTERED by d0226`.\n\n**`d0226` does not exist in that project.** Its `.engine/decisions/` holds `0001`–`0004`. So `onboard` asserts a charter that cannot be read — a dangling provenance claim, and a false one, on the command whose entire job is to answer *on what basis were these processes chosen*.\n\n## The knock-on that made it visible\n\nThe two re-added processes were the two the project argued against. Re-arming `distributed-collaboration` re-armed `guard:ownership`, which then failed on the very files migrate had just rewritten:\n\n```\nVIOLATION ownership: .engine/views/viewpoint-registry.sysml: 'authorityQueueVP' is owned by\n'claudeOpus5' and its fields were edited by 'ai' — D0108: a non-owner ADDS items and typed\nedges or SUPERSEDES, never overwrites in place.\n```\n\nThat is the only reason it was caught. **A project that had declined a control for a reason would simply find it back on**, with a green gate, and no line of output saying so.\n\n(Separately worth noting: the engine-shipped `viewpoint-registry.sysml` carries owner ids from the *toolkit's* own actor registry — `claudeOpus5`, `wweatherholtz` — so an adopting project's migrate edits are attributed to its own actor against owners it has never heard of.)\n\n## What survived, for scope\n\n`github-actors.toml`, `installed-units.toml` and the project's own `.engine/decisions/*.sysml` all survived intact. The damage was confined to `activation.toml`.\n\n## Reproduce\n\n1. In a keel project, charter a process set (`keel deactivate <something>`, then set `charteredBy` — or run the `project-onboarding` skill).\n2. `keel onboard .` → CHARTERED by your Decision.\n3. `keel migrate .`\n4. `keel onboard .` → CHARTERED by `d0226`, and your `active` list is the engine's.\n\n## Prior art in the field\n\nThe Penumbra project already hit this class and carries a post-migrate repair script (`tools/after_migrate.py`), with its CLAUDE.md warning: *''Migrate rewrites engine-shipped files, and four pins that make this project's vintage usable live inside them.''* So the workaround exists in the wild; the defect does not appear to be recorded.\n\n## Direction (yours)\n\n`activation.toml` is instance data by the same argument `.engine/contracts/github-actors.toml` already wins — the D0219 note says outright that shipping one project's deciders into another is the defect that file's exclusion exists to fix. A project's chartered activation set is the same kind of fact: it records a human decision, it is not engine vintage. Candidates: exclude it from migrate's rewrite set; or three-way merge it the way unit imports already do; or, at minimum, refuse to write a `charteredBy` that does not resolve in the target project, which would have turned this from silent data loss into a loud refusal.\n";
        :>> saidBy = "williamweatherholtz"; :>> saidAt = "2026-09-04"; :>> channel = StatementChannel::github;
        :>> sourceUrl = "https://github.com/williamweatherholtz/sysmlv2-ai-toolkit/issues/56";
        :>> sourceTrust = SourceTrust::untrusted;
    }

    part st096 : Statement {
        :>> id = "d20eb322-825a-4505-b805-f465d29928b6";
        :>> title = "GH#55 The pre-commit hook, keelw and the Claude hooks each resolve the keel binary differently - two of the three fall back to PATH silently";
        :>> createdAt = "2026-09-06"; :>> createdBy = "githubRecorder";
        :>> text = "`keelw` and `keel init` write the binary cache at `.keel/bin/<version>/<asset-name>`. The scaffolded `.githooks/pre-commit` looks for `.keel/bin/keel` or `.keel/bin/keel.exe` — **unversioned** — and when it misses, falls through to `command -v keel`.\n\nThe two layouts do not know about each other. So on a freshly initialised project the hook never finds the cache init just wrote, and **gates every commit with whatever keel is on PATH** — which is precisely the fallback `keelw`'s own header calls out:\n\n> instructions, never a fallback to whatever keel is on PATH — the PATH fallback is exactly the defect the pin ends.\n\n## The relevant lines\n\n`.githooks/pre-commit`:\n\n```sh\n[ -z ''$KEEL'' ] && [ -x .keel/bin/keel ]     && KEEL=./.keel/bin/keel\n[ -z ''$KEEL'' ] && [ -x .keel/bin/keel.exe ] && KEEL=./.keel/bin/keel.exe\nKEEL=''${KEEL:-keel}''\n```\n\n`keelw`:\n\n```sh\nCACHE_DIR=''.keel/bin/$VERSION''\nCACHED=''$CACHE_DIR/$ASSET''\n```\n\n`keel init` seeds the second shape. The hook only reads the first.\n\n## Measured\n\nSame tree, same commit, on a project whose PATH keel was a `+dirty` build while `.keel/bin/0.3.1/` held the pinned release:\n\n- `./keelw guard .` → **ALL PASS**, 0 violations\n- the pre-commit hook's `keel gate --workspace .` → **FAILED**, `viewpoint-renderer` 14 violations\n\nThe hook printed that it ran and the commit was refused for a reason that is not true of the tree the project pins. The mirror case is worse and is the one that bit first: with the *dev* build in the cache and the *release* nowhere, the hook passed a tree the release rejects.\n\nPlacing the release at `.keel/bin/keel.exe` — the path the hook's own comment sanctions (''drops a RELEASED binary at `.keel/bin/keel` … and it wins over PATH'') — made hook and wrapper agree.\n\n## The same defect on a third surface\n\n`.claude/settings.json`, generated by `keel sync-claude`, has every hook resolve `''${KEEL_BIN:-}''` first and then `command -v keel`. With `KEEL_BIN` unset that is the same silent PATH fallback, so the **turn gate** also gated with the dev build: it reported 14 `viewpoint-renderer` violations and a `claude-surface-drift` on a tree the pinned binary passes clean. Setting `KEEL_BIN` to the pinned binary resolved it.\n\nSo three surfaces are meant to enforce one pin and each resolves the binary differently: `keelw` (versioned cache, no PATH fallback), the commit hook (unversioned cache, PATH fallback), the Claude hooks (`KEEL_BIN`, PATH fallback).\n\n## Why it matters\n\nA gate that silently runs the wrong engine is worse than an absent one — the hook's own K2 comment says an absent gate must not pass silently, and this one does exactly that in the direction that produces a false green. It also means ''the pin is binding'' (D0251) holds for `keelw` and for CI but not for the two surfaces a contributor actually goes through on every commit and every turn.\n\n## Direction (yours)\n\nOne resolution shared by all three surfaces, rather than three. Candidates: have the hooks call `./keelw` (which already owns pin resolution and has no PATH fallback); or have `keel init` additionally place/symlink the pinned asset at `.keel/bin/keel[.exe]` so the existing hook finds it; or drop the PATH fallback and refuse loudly, which the wrapper already does and the hooks do not.\n\nWhichever way, the fallback deserves to be loud: today nothing prints which binary gated the commit, so the skew is undetectable from the output.\n";
        :>> saidBy = "williamweatherholtz"; :>> saidAt = "2026-09-04"; :>> channel = StatementChannel::github;
        :>> sourceUrl = "https://github.com/williamweatherholtz/sysmlv2-ai-toolkit/issues/55";
        :>> sourceTrust = SourceTrust::untrusted;
    }

    part st097 : Statement {
        :>> id = "642d5cea-397a-4044-b33c-6876f952fd32";
        :>> title = "GH#54 keel init seeds the wrapper cache with whatever binary ran it, under the pin's name - and keelw never verifies a cache hit";
        :>> createdAt = "2026-09-06"; :>> createdBy = "githubRecorder";
        :>> text = "`keel init` writes the engine pin, then seeds the wrapper cache with **whatever binary ran init** — labelled as that pin. If init was run by an unreleased build, that build silently becomes ''the pinned version'' for the project's whole life, and `keelw` will never notice, because it verifies a **download** but not a **cache hit**.\n\n## Measured\n\nA project initialised 2026-09-03 by a local dev build. Two different binaries, both answering `keel version` with `0.3.1`:\n\n| | SHA-256 | bytes | build commit |\n|---|---|---|---|\n| `.keel/bin/0.3.1/keel-windows-x86_64.exe` (seeded by init) | `21aea1ef…` | 11,429,888 | `4674965+dirty` |\n| published `v0.3.1` release asset | `76714047…` | 10,536,960 | `c4d5dbf` |\n\n`76714047…` is the checksum **already committed in that project's own `keel-wrapper.toml`**, and a fresh download of the asset matches it exactly. So the tree carried the correct expected hash the whole time and nothing ever compared the cached file against it.\n\nThe ~900 KB gap is real capability, not build noise. The dev build spells the lenses `keel show <lens>`; the release spells them `keel <lens>`. That single difference is enough to invert a gate:\n\n```\n# same tree, same commit, two binaries\nkeel   guard .   (4674965+dirty)  ->  viewpoint-renderer FAIL 14 violations,  claude-surface-drift FAIL 1\nkeelw  guard .   (c4d5dbf)        ->  viewpoint-renderer PASS  0 violations,  claude-surface-drift PASS 0\n```\n\n## Why it matters\n\nD0251 makes `engine-version.toml` **binding** — validate and guard are supposed to *refuse* under skew. Here the mismatched binary did not refuse; it gated, and it reported clean. Every local `gate clean` in that project's first day was produced by a binary the project does not pin, and the project's own CI (which downloads the release asset by tag) was the only honest signal. It said FAILED, and it was right.\n\nThe failure direction is the bad one: **a false green**. Nobody investigates a passing gate.\n\n## Reproduce\n\n1. Build keel from an uncommitted working tree (any `+dirty` build).\n2. `keel init someproject` with that binary.\n3. `sha256sum someproject/.keel/bin/<pin>/<asset>` and compare with the entry for that version in `someproject/keel-wrapper.toml`. They differ.\n4. `keelw guard .` passes — the cache hit is execed without verification (`keelw` line: *''cache hit: exec, touching nothing else''*).\n\n## Direction (yours)\n\nTwo candidates, not exclusive:\n\n- **Verify the cache hit**, at least when `keel-wrapper.toml` has an entry for that version. `keelw` already refuses a *download* whose checksum mismatches; the same comparison on a cache hit would have caught this at the first invocation. The wrapper's own header says trust-on-first-use is no verification at all — a seeded cache is trust-on-first-use by another route.\n- **Refuse to seed from an unreleased build.** An unreleased binary is reproducible by nobody: no other machine and no CI runner can obtain `21aea1ef…`, so pinning to it names a version that does not exist as an artifact. Seeding could be skipped (leaving `keelw` to fetch the real asset on first use) or recorded as provisional.\n\nRelated but distinct, filed separately: the pre-commit hook looks for a *different* cache path than the one init seeds, and falls back to PATH when it misses.\n";
        :>> saidBy = "williamweatherholtz"; :>> saidAt = "2026-09-04"; :>> channel = StatementChannel::github;
        :>> sourceUrl = "https://github.com/williamweatherholtz/sysmlv2-ai-toolkit/issues/54";
        :>> sourceTrust = SourceTrust::untrusted;
    }

    part us091 : UserStory {
        :>> id = "f8025e8c-6863-4c50-9067-120acf20bd44";
        :>> title = "GH#59: migrate reads a removed type named in prose as a declaration, and Rust :: satisfies its typing test";
        :>> createdAt = "2026-09-06"; :>> createdBy = "claudeOpus5";
        :>> asA = "a downstream keel project (reporter: williamweatherholtz)";
        :>> iWant = "the removed-type and removed-enum scanners to read SCHEMA, not the text inside string literals";
        :>> soThat = "a quoted foreign symbol (ureq::Agent, std::task) in an authored description cannot block migration of a healthy project";
        :>> implication = ImplicationKind::bug;
        :>> triageNote = "UNTRUSTED tier, decider-filed (D0314). VERIFIED against main: types_as (migrate.rs) accepts text ending in : before the name, so a Rust path separator passes, and step_removed_types scans whole lines including quoted prose; REMOVED_ENUMS uses line.contains. The three workarounds the reporter lists all corrupt the record or the schema. RECOMMEND: blank double-quoted literals before scanning in step_removed_types only, regression test with both arms (prose must not block; a real : Agent annotation still must). High - one quoted word permanently blocks a project from moving vintage, with no override surface.";
    }
    #DerivedFrom dependency from us091 to st092;

    part us092 : UserStory {
        :>> id = "fb6e8f19-dfde-4cf2-b790-2b800f244a58";
        :>> title = "GH#58: the published decision-channel unit never bootstraps the keel-standing label its script requires";
        :>> createdAt = "2026-09-06"; :>> createdBy = "claudeOpus5";
        :>> asA = "a project importing decision-channel from the library (reporter: williamweatherholtz)";
        :>> iWant = "the channel workflow to create every label its script uses, or refuse at start-up naming the missing one";
        :>> soThat = "the first run in a new repository does not die inside gh issue create with a CalledProcessError that names no cause";
        :>> implication = ImplicationKind::bug;
        :>> triageNote = "UNTRUSTED tier, decider-filed (D0314). VERIFIED: keel-lib origin/main decision-channel v6 ships .github/workflows/decision-issue.yml and .github/scripts/open_decision_issues.py; this repository deleted both in sprint 527 (D0291 - the channel is disconnected upstream) so the unit cannot be republished from a landed tree (library-stewardship rule 1). The defect is real and third in a chain each of which masks the next. RECOMMEND: route with GH#57 - the unit is RETIRED in the library with its reason and replacement (record-time standing consent in the binary, D0291) rather than patched, because the same unit carries a fabricated-attestation path. Medium on its own.";
    }
    #DerivedFrom dependency from us092 to st093;

    part us093 : UserStory {
        :>> id = "94773ce1-4690-447f-817d-f08a3ea4d204";
        :>> title = "GH#57: standing-consent auto-accept quotes one specific human and names one hardcoded actor, in any project that runs it";
        :>> createdAt = "2026-09-06"; :>> createdBy = "claudeOpus5";
        :>> asA = "a project whose own supervisor declared its deciders (reporter: williamweatherholtz)";
        :>> iWant = "an auto-acceptance to name the projects declared decider and quote standing words that decider actually gave, or stay proposed";
        :>> soThat = "no acceptance is recorded in a humans name citing consent they never gave - the guard:confirmation-authenticity / D0106 class arriving through the tool itself";
        :>> implication = ImplicationKind::bug;
        :>> triageNote = "UNTRUSTED tier, decider-filed (D0314). VERIFIED WIDER THAN FILED: the library unit script hardcodes --by wweatherholtz and the quote (keel-lib decision-channel v6, record_decision.sh), AND the binary has the same class at record time - main.rs cmd_record decision builds the AUTO-ACCEPTED note from a string literal of this repositorys humans words, while init ships attestation-policy.toml verbatim with standingConsent = d0207 and migrate resyncs it (not in PROJECT_OWNED). So a fresh project with one declared decider auto-accepts every non-fork Decision in that deciders name quoting words they never said. The reporters third candidate (marker Decisions outside consent) is already D0337. RECOMMEND: the standing words are project-local data - a standingWords line beside standingConsent, quoted from there or the Decision stays proposed saying why; init resets the two grant lines; migrate treats attestation-policy.toml as project-owned; the library unit is retired. CRITICAL - a fabricated attestation produced by the engine.";
    }
    #DerivedFrom dependency from us093 to st094;

    part us094 : UserStory {
        :>> id = "ec9c4185-645d-4eeb-a3b7-4dd76b3cf73f";
        :>> title = "GH#56: migrate overwrote a chartered activation.toml with the engines, and onboard then cited a Decision the project does not hold";
        :>> createdAt = "2026-09-06"; :>> createdBy = "claudeOpus5";
        :>> asA = "a project that chartered its process set (reporter: williamweatherholtz)";
        :>> iWant = "migrate to leave my activation set alone, and onboard to refuse a charteredBy that does not resolve in my tree";
        :>> soThat = "a recorded human decision about which controls apply is never silently discarded, and a dangling provenance claim is never printed as fact";
        :>> implication = ImplicationKind::bug;
        :>> triageNote = "UNTRUSTED tier, decider-filed (D0314). PARTLY FIXED ON MAIN, UNRELEASED: activation.toml has been in migrates PROJECT_OWNED set since 6583e08 (2026-08-30, issue314), which is NOT an ancestor of v0.3.1 (c4d5dbf, 2026-08-29) - so every adopter on the release still has the defect until a release ships it. RESIDUAL, real on main: nothing checks that charteredBy resolves, so onboard asserts a charter it cannot read; and attestation-policy.toml is still resynced wholesale (routed under GH#57). RECOMMEND: a guard/onboard refusal for a dangling charteredBy, and a release carrying the issue314 fix. High.";
    }
    #DerivedFrom dependency from us094 to st095;

    part us095 : UserStory {
        :>> id = "dc0ca7ea-b752-4f72-a69f-a8a132e26997";
        :>> title = "GH#55: pre-commit, keelw and the Claude hooks resolve the binary three different ways, two falling back to PATH silently";
        :>> createdAt = "2026-09-06"; :>> createdBy = "claudeOpus5";
        :>> asA = "a contributor on a pinned project (reporter: williamweatherholtz)";
        :>> iWant = "every gating surface to find the same pinned binary, and to print which binary gated";
        :>> soThat = "a commit or a turn is never gated by a build the project does not pin, and a skew is visible in the output when it happens";
        :>> implication = ImplicationKind::bug;
        :>> triageNote = "UNTRUSTED tier, decider-filed (D0314). VERIFIED: keelw and init write .keel/bin/<version>/<asset>; PRECOMMIT_HOOK (lib.rs) and claude_surface RESOLUTION_ORDER (D0316, this week) probe .keel/bin/keel(.exe) - a path nothing writes - then PATH. D0316 fixed the ORDER and left the mismatch: both hooks probe a file init never creates. RECOMMEND: one probe list in one place shared by the hook text and the Claude hooks - KEEL_BIN, .keel/bin/keel(.exe), the pins cache .keel/bin/<pin>/<asset> read from engine-version.toml, then PATH - and every surface prints the binary it gated with and its build commit, so the fallback is loud. High - a false green from the wrong engine on the two surfaces every commit and turn go through.";
    }
    #DerivedFrom dependency from us095 to st096;

    part us096 : UserStory {
        :>> id = "b6c5351f-cb94-44cb-9a04-477676fc2370";
        :>> title = "GH#54: init seeds the wrapper cache with whatever binary ran it, under the pins name, and keelw never verifies a cache hit";
        :>> createdAt = "2026-09-06"; :>> createdBy = "claudeOpus5";
        :>> asA = "a project initialised by a local build (reporter: williamweatherholtz)";
        :>> iWant = "keelw to verify a cache hit against the committed checksum when one exists, and init never to seed from an unreleased build";
        :>> soThat = "the pin names an artifact another machine can obtain, and a seeded binary cannot pass as the release for the projects whole life";
        :>> implication = ImplicationKind::bug;
        :>> triageNote = "UNTRUSTED tier, decider-filed (D0314). VERIFIED: init_wrapper (main.rs) copies current_exe into .keel/bin/<CARGO_PKG_VERSION>/<asset> unconditionally; keelw execs a cache hit without comparing it to keel-wrapper.toml. build.rs bakes KEEL_BUILD_COMMIT with +dirty for a modified tree, so init can tell. RECOMMEND: keelw checks a cache hits SHA-256 against the committed entry when one exists and refuses on mismatch naming both hashes; init seeds only from a clean (non-dirty) build and prints what it did either way, never writing a hash it made up. High - a false green in the direction nobody investigates.";
    }
    #DerivedFrom dependency from us096 to st097;

    // Routing of the six downstream issues on the decider's own report (D0339, D0314): story -> Issue, story -> the routing Decision.
    #Implicates dependency from us091 to issue377;
    #Implicates dependency from us091 to d0339;
    #Implicates dependency from us092 to issue381;
    #Implicates dependency from us092 to d0339;
    #Implicates dependency from us093 to issue376;
    #Implicates dependency from us093 to d0339;
    #Implicates dependency from us094 to issue380;
    #Implicates dependency from us094 to d0339;
    #Implicates dependency from us095 to issue378;
    #Implicates dependency from us095 to d0339;
    #Implicates dependency from us096 to issue379;
    #Implicates dependency from us096 to d0339;

    part st098 : Statement {
        :>> id = "7ccf0041-fad6-4304-9001-e2b9346ea2cc";
        :>> title = "Use the ASI template skill for the standing executive summary";
        :>> createdAt = "2026-09-06"; :>> createdBy = "claudeOpus5";
        :>> text = "use the asi template skill for this standing executive summary process.";
        :>> saidBy = "wweatherholtz"; :>> saidAt = "2026-09-06"; :>> channel = StatementChannel::chat;
    }

    part us097 : UserStory {
        :>> id = "8821d868-e4e5-40ac-a151-ed906723da05";
        :>> title = "The standing executive summary is rendered from the ASI exec-summary surface, not hand-authored HTML";
        :>> createdAt = "2026-09-06"; :>> createdBy = "claudeOpus5";
        :>> asA = "the human reading what waits on them";
        :>> iWant = "the standing summary built by the asi-templates skill - tabs, steel-manned choices, the reasoning chain, Copy-for-AI";
        :>> soThat = "every ask arrives in the format I asked for, and the page can be argued with rather than deferred to";
        :>> implication = ImplicationKind::process;
        :>> triageNote = "TRUSTED: the human's own direction in chat (D0314), so it is acted on under the ordinary process. The unit is in the library and not installed here; importing it is a process-surface change, so it carries a Decision with a process-change marker, accepted on these words under the D0192/D0289 delegation with the read-back naming the process. RECOMMEND: import asi-templates v3, render the queue from templates/exec-summary/exec-summary.html, wire the contract checker into pre-commit (the unit declares no guard), publish to the standing URL.";
    }
    #DerivedFrom dependency from us097 to st098;

    // The human directed the surface (st098); the Decision adopts it and the task delivers it.
    #Implicates dependency from us097 to d0354;
    #Implicates dependency from us097 to dcStandingSummaryUsesTheKit;

    part st099 : Statement {
        :>> id = "9575dd8a-d741-4039-ac91-ce7a241bf57f";
        :>> title = "The decision report is administrative justification, not implications; the diagrams are weak";
        :>> createdAt = "2026-09-06"; :>> createdBy = "claudeOpus5";
        :>> text = "context is very lacking. these decisions aren't grappling strongly enough with the implications of these decisions, mostly just administrative justification for the decision. I think the skill needs to be reworked - a decision isn't really to accept A decision or B decision - i need to understand the implications and real technical changes much better. and the diagrams are so weak today. I want the main logical reasons for the proposed changes. we have needs, use cases, etc. calling for different directions and I want better insight";
        :>> saidBy = "wweatherholtz"; :>> saidAt = "2026-09-06"; :>> channel = StatementChannel::chat;
    }

    part st100 : Statement {
        :>> id = "dcd9ebcc-824b-48a3-8228-53592caff694";
        :>> title = "Not a citing issue - a logical clarity issue; too many references already";
        :>> createdAt = "2026-09-06"; :>> createdBy = "claudeOpus5";
        :>> text = "it's not a citing issue - it's a logical clarity issue. there are already too many things that are referenced";
        :>> saidBy = "wweatherholtz"; :>> saidAt = "2026-09-06"; :>> channel = StatementChannel::chat;
    }

    // The owner directed the rework and then corrected the diagnosis; the Decision carries both.
    #DerivedFrom dependency from d0355 to st100;
}
