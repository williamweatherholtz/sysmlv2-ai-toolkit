// Intake for 2026-09-09 — their words, my translation, the triage verdict (D0166/D0216).
// Written by `keel record statement` / `keel record story` (D0236): a Statement's text is
// VERBATIM, so it is escaped for the literal and otherwise untouched.
package ProjectIntake20260909 {
    private import EngineElement::*;
    private import EngineIntake::*;
    private import EngineRelationships::*;

    part st113 : Statement {
        :>> id = "28be6e7c-f558-4c66-9e68-abeaa17b3179";
        :>> title = "GH#69 append-result cannot address a standalone verification - the write API misses the shape the RED-first rule produces";
        :>> createdAt = "2026-09-09"; :>> createdBy = "githubRecorder";
        :>> text = "`keel append-result` cannot address a standalone `verification … : Test`. Given one, it answers `error: task not found`. It only resolves a `--task` that is an `action` inside an `action def` with a sibling `<task>DoD` verification.\n\n## Why this matters more than it looks\n\nThe TDD discipline the engine asks for — author the test RED first, before implementation — produces exactly the shape the API cannot reach: a standalone verification with no action beside it. In one downstream project that is every RED test file (`verification-wave5.sysml`, `verification-reviewhistory.sysml`, `verification-reviewcorpus.sysml`). So the moment a RED test goes green, its passing result has to be hand-appended into the `.sysml` — the one write the write API exists to make unnecessary, and the one place where a hand-written `TestResult` skips the API's UUID minting and append-only guarantees. The pre-write hook only advises on these files.\n\n## Repro\n\n```sysml\npackage X {\n    private import EngineElement::*;\n    private import EngineVerification::*;\n    verification tFoo : Test {\n        :>> id = ''…''; :>> title = ''RED - …''; :>> createdAt = ''2026-09-08''; :>> createdBy = ''ai'';\n        :>> method = VerificationMethod::test;\n        :>> procedureText = ''…'';\n    }\n}\n```\n\n```\n$ keel append-result --file .tracking/x.sysml --task tFoo --sha 0f5a1d1 --verdict pass --judged-by ai --judged-at 2026-09-08\nerror: task not found: tFoo\n```\n\nThe same command against an `action tFoo;` + `verification tFooDoD : Test {…}` pair succeeds.\n\n## Suggested fix\n\nEither resolve `--task` to a standalone verification by name when no action of that name exists in the file (the result part name would be `<name>R<n>`, matching the idiom hand-appended records already use), or add an explicit `--verification NAME`. Either keeps the API's minting and append-only semantics on the path the TDD rule makes most common.\n\nFound closing a downstream sprint where two wave-5 RED verifications went green and both had to be hand-appended, as two before them had been on 2026-08-21.\n";
        :>> saidBy = "williamweatherholtz"; :>> saidAt = "2026-09-08"; :>> channel = StatementChannel::github;
        :>> sourceUrl = "https://github.com/williamweatherholtz/sysmlv2-ai-toolkit/issues/69";
        :>> sourceTrust = SourceTrust::untrusted;
    }

    part st114 : Statement {
        :>> id = "037a0ac1-c70d-4f89-8654-328437543064";
        :>> title = "GH#68 migrate: verified-or-reverted makes a project overlay unreachable, and an engine resync reads as a non-owner overwrite of computed-owned items";
        :>> createdAt = "2026-09-09"; :>> createdBy = "githubRecorder";
        :>> text = "Two defects found moving a downstream project (penumbra) from v0.3.1 to v0.4.1. Both are in the migrate path, both are structural rather than incidental, and neither is caught by a test. Reporting together because they were hit in the same run and the second only becomes visible after working around the first.\n\n## 1. Verified-or-reverted (D0336) forbids a project overlay from ever being applied\n\n`keel migrate` applies, gates under the new binary, and reverts `.engine/` + `.tracking/` on any red. This project must run `python tools/after_migrate.py` **after** migrate, because migrate rewrites engine-shipped files and four pins that make its adopted vintage usable live inside them. The two rules cannot both hold: the apply resets the pins, the gate runs before any repair can, and the revert lands before the repair could ever be applied.\n\n**Measured, not reasoned.** The first verified run reported ~87 failing lines and rolled back 484 files. Running the overlay afterwards proved every one of those failures was an artefact of the apply:\n\n| Repaired by the overlay | Was |\n|---|---|\n| `acceptQuotesDelegatedWords` | `2026-08-22` → project adoption date `2026-09-01` |\n| `confirmationQuotesOrAttested` | `2026-08-23` → `2026-09-01` |\n| critique-policy D1028 override | 3 armed tiers → 6 (the apply had **loosened** the gate) |\n| registry entries | 2 restored — these were the two `process-skill` ''inert process'' violations |\n\nThe cutoff resets are the retroactive-cutoff failure the project's own overlay script documents: reset to the engine's adoption date, 73 of 90 acceptance records fail at once. The engine ships **upstream's** adoption date, so installed verbatim downstream a forward-only rule becomes retroactive.\n\nSo the gate was reporting its own apply, and the revert guaranteed the fix could never run.\n\n**The only exit is `--no-verify`,** which the `project-migration` skill says never to use — on the sound general ground that it disables every other check to get past one that is usually correct. Here the one being got past was not correct. That skill also calls this the least-tested surface in the system, seven defects deep with four untested, which is exactly why a downstream author cannot tell a real red from a reset one.\n\n**Suggested fixes, in preference order:**\n\n1. A post-apply hook migrate runs *before* it gates — the project declares its overlay command in a contract, migrate runs it, then gates. This makes verified-or-reverted correct for projects with overlays instead of unreachable.\n2. Treat the cutoff-bearing rule files as project-owned, the way `attestation-policy.toml` already is under D0340 (''an adopter's grants survive a resync byte-identically''). The cutoffs are the same kind of fact: a value the engine cannot supply.\n3. Failing either, document the overlay contract so `--no-verify` is a named step rather than a violation of a skill's explicit instruction.\n\n## 2. Migrate overwrites items whose ownership is COMPUTED, so an engine resync reads as a non-owner edit\n\nAfter working around (1), `guard:ownership` refuses the tree with 16 violations:\n\n```\n.engine/views/viewpoint-registry.sysml: 'decisionsVP' is owned by 'wweatherholtz'\n  and its fields were edited by 'ai' — D0108: a non-owner ADDS items and typed edges\n  or SUPERSEDES, never overwrites in place.\n```\n\nFourteen owned by the human, two by `claudeOpus5`.\n\n**The guard is right about what happened, and the content change is still correct and necessary.** v0.4.1 moved read views under a `show` subcommand, so every `renderer` string had to change — `keel decisions` → `keel show decisions`, `keel suspect` → `keel show suspect`, sixteen in all. Left unchanged they name commands that no longer exist, which is precisely what `guard:viewpoint-renderer` fails on before the apply. The tree cannot be honest either way: keep the old strings and the renderers name nothing; take the new ones and a non-owner has overwritten owned items.\n\n**The root is that ownership here is not authored.** There is no `owner =` field anywhere in that file — `grep -c ''owner = ''` returns 0 before and after. Ownership is computed from provenance, so the acting actor at write time becomes the editor, and the bound actor running migrate is `ai`.\n\nThat makes it structural: **any migrate touching any engine-shipped file whose lines a human last authored reproduces this, on every project.** Not specific to viewpoints, not specific to this project.\n\nD0108's own escapes do not fit. Superseding sixteen viewpoints to rename a command is a workaround wearing a supersession's clothes. ''Have the owner make the change'' means a human hand-editing sixteen strings the engine already knows the correct value of. Disarming the guard is what `control-propriety` exists to refuse.\n\n**Suggested fixes:** `guard:ownership` learns that an engine resync is not an authorship claim (migrate could stamp the resync as engine-authored rather than as the invoking actor); or engine-shipped view registries stop carrying computed project ownership; or migrate reports owned-item overwrites as a distinct, dispositionable class rather than as a generic ownership violation.\n\n## State this left behind\n\nThe migration is applied and the tree is green on `keel validate .`, `keel check-engine .`, and the project's full 614-test suite. `guard:ownership` is the only violation and it blocks the commit — so the tree is neither fully migrated nor byte-identical to its preflight commit, which is the third state the `project-migration` process says must not exist.\n\nAlso worth noting, minor: migrate's rollback restored `.engine/` and `.tracking/` but **not** `.claude/`, so the new binary's surface stamp survived a revert that reported the tree was ''as it was before this run''.\n\nTracked downstream as issue218 and issue219. Happy to open PRs for either fix.\n";
        :>> saidBy = "williamweatherholtz"; :>> saidAt = "2026-09-08"; :>> channel = StatementChannel::github;
        :>> sourceUrl = "https://github.com/williamweatherholtz/sysmlv2-ai-toolkit/issues/68";
        :>> sourceTrust = SourceTrust::untrusted;
    }
}
