// Intake for 2026-08-31 — their words, my translation, the triage verdict (D0166/D0216).
// Written by `keel record statement` / `keel record story` (D0236): a Statement's text is
// VERBATIM, so it is escaped for the literal and otherwise untouched.
package ProjectIntake20260831 {
    private import EngineElement::*;
    private import EngineIntake::*;
    private import EngineRelationships::*;

    part st050 : Statement {
        :>> id = "d3e8f425-8ade-43cc-b676-4391324017ca";
        :>> title = "GH#41 guard:resolver-kind rejects an action resolver while naming 'action' as valid";
        :>> createdAt = "2026-08-31"; :>> createdBy = "claudeOpus5";
        :>> text = "`#Resolves` pointing at an `action` declared inside a project `action def` is rejected, and the rejection message names the resolver's kind as exactly the kind it says is required.\n\n**Observed**\n\n```\nERROR aimQuantization: #Resolves comes from layoutControl, which is a action — a resolver\nmust be a declared action (work that closes it) or a Decision (which moots it); ...(issue136)\n```\n\n**Repro** — in a `.tracking/` package:\n\n```\naction def MyBacklog {\n    action layoutControl;\n    verification layoutControlDoD : Test { ... }\n    part layoutControlR1 : TestResult { ... outcome = VerdictKind::pass; }\n}\n#Resolves dependency from layoutControl to someIssue;\n```\n\n`keel validate` is clean; `guard:resolver-kind` errors as above.\n\n**Neither placement works.** Moving the edge *inside* the `action def` silences `resolver-kind` — but only because it no longer sees the edge at all: `guard:issues` then reports `untriaged — no #Resolves edge`. So the two guards disagree about where the edge must live, and one of the two always fires. Qualifying the reference (`MyBacklog::layoutControl`) is a parse error: `expected To, got ColonColon`.\n\n**Workaround used:** point `#Resolves` at a Decision instead, keeping the action as the work record. That loses the action/Decision distinction the rule exists to preserve — a Decision *moots* an Issue, an action *closes* it, and here the work genuinely closed them.\n\nguards.md notes this predicate is deliberately bespoke because `objectType` filters by declared item TYPE and an action is not a typed element, so it must recognise actions some other way; that recognition appears not to reach actions declared in a project `action def`, or the message misreports the kind it found.";
        :>> saidBy = "williamweatherholtz"; :>> saidAt = "2026-08-31"; :>> channel = StatementChannel::github;
        :>> sourceUrl = "https://github.com/williamweatherholtz/sysmlv2-ai-toolkit/issues/41";
        :>> sourceTrust = SourceTrust::untrusted;
    }

    part st051 : Statement {
        :>> id = "0028bfc4-1ee2-406e-ac6f-888b11fac181";
        :>> title = "GH#40 A strict-profile project cannot make its INITIAL commit: the keystone lock counts all 128 scaffolded files as a process change, and init emits no #ProspectiveChange Decision";
        :>> createdAt = "2026-08-31"; :>> createdBy = "claudeOpus5";
        :>> text = "## Summary\n\nA strict-profile project cannot make its **initial commit**. The keystone hard-lock counts every scaffolded file as a process-definition change — because a root commit has no parent to diff against — and `keel init` does not emit the `#ProspectiveChange` Decision the guard demands. The scaffold the tool produces is rejected by the gate the tool installs.\n\nSecond, smaller defect in the same flow: consuming a `keel override` writes an obligation file that **does not validate**, so the sanctioned escape hatch also leaves the tree red.\n\n## Repro — the initial commit\n\n1. `keel init myproject --profile strict`\n2. `cd myproject && git init && git config core.hooksPath .githooks`\n3. Author anything, `git add -A`, `git commit`\n\n## Observed\n\n```\nERROR locked file(s) changed (.engine/contracts/activation.toml, ... 128 paths ...,\n.githooks/pre-commit, .github/workflows/keel-gate.yml) with NO co-committed process-change\nDecision (a #ProspectiveChange/#SafetyChange-marked .engine/decisions/*.sysml). HARD LOCK: ...\n[guard:process-change] FAIL — 128 scanned, 0 warning(s), 1 violation(s)\npre-commit: keel guard FAILED — commit aborted\n```\n\nAll 128 are files `keel init` itself wrote moments earlier — every process definition, every skill, the contracts, the pre-commit hook, the CI workflow.\n\nThe guard's premise is right: an enforcement surface may not change without a human signing for it, and that holds on the commit that *introduces* the surface no less than on one that edits it. The defect is that `keel init` leaves the project unable to satisfy it.\n\n## Workaround\n\nAuthor a `#ProspectiveChange` Decision adopting the scaffold, and **co-commit it**:\n\n```\nkeel record decision --from DRAFT.md --process-change\ngit add -A          # the Decision must be in the SAME changeset\nkeel guard .        # exit 0\n```\n\nNote the ordering trap: staging before recording the Decision leaves the guard still failing, because it looks for the Decision in the same changeset. That is correct behaviour, but it is easy to hit and the error message does not mention it.\n\n## Expected\n\nEither:\n\n1. `keel init` emits the adoption Decision as part of the scaffold — it knows exactly which surface it wrote; or\n2. the keystone guard recognises a **root commit** (no parent) and reports the scaffold adoption as an obligation to sign rather than a violation; or\n3. `keel init` prints the required next step, so the operator is not left deducing it from a 128-path error.\n\n(1) is the cleanest — the Decision's content is fully determined by what init just wrote, including the binary version and build commit that produced it, which is exactly the provenance a human should be signing for.\n\n## Second defect: the override obligation does not validate\n\n`keel override <path> --reason ''...''` then writing through the unlocked path records an obligation at `.tracking/obligations/override-<hash>.sysml`. The generated file declares:\n\n```sysml\npackage Obligation7c7fff9e {\n    private import EngineElement::*;\n\n    part obligation7c7fff9e : Issue {\n        ...\n        :>> severity = Severity::Low;\n```\n\n`Issue` and `Severity` are defined in **`EngineWork`** (`.engine/schema/core/work.sysml:70`), which is not imported. The result:\n\n```\nERROR .tracking/obligations/override-7c7fff9e.sysml:7 — unresolved type reference `Issue`\n```\n\nSo the sanctioned override path leaves the model broken and the operator must hand-repair keel's own generated output by adding `private import EngineWork::*;`.\n\nCombined with the initial-commit lock above, both the primary path and its escape hatch are currently red out of the box.\n\n## Environment\n\n```\nkeel 0.3.0\nbuild commit: c444ca5\nguards: 51 (42 hard-blocking, 9 warning-only)\n```\nBoth reproduced on Windows 11 with a project scaffolded 2026-08-29 via `keel init . --profile strict`. The obligation defect was re-confirmed on 0.3.1.\n";
        :>> saidBy = "williamweatherholtz"; :>> saidAt = "2026-08-31"; :>> channel = StatementChannel::github;
        :>> sourceUrl = "https://github.com/williamweatherholtz/sysmlv2-ai-toolkit/issues/40";
        :>> sourceTrust = SourceTrust::untrusted;
    }

    part st052 : Statement {
        :>> id = "010d36c0-03e8-471f-9171-5b858f711c84";
        :>> title = "GH#39 keel migrate OVERWRITES a downstream project's chartered process set with the engine's own (charteredBy d9001 -> d0226, declined processes silently re-enabled)";
        :>> createdAt = "2026-08-31"; :>> createdBy = "claudeOpus5";
        :>> text = "## Summary\n\n`keel migrate` overwrites `.engine/contracts/activation.toml`, replacing a downstream project's **chartered process set** with the **engine's own**. A human-signed governance choice is silently replaced by the engine author's choices during a routine version upgrade. No blocker, no prompt, no mention in the migration summary.\n\nThis is the most serious of the findings from this session, because the overwritten file is precisely the artifact D0225 exists to produce.\n\n## Observed\n\nProject `landscape_plan`, chartered via the `project-onboarding` skill, then upgraded 0.3.0 -> 0.3.1.\n\n**Before `keel migrate`:**\n\n```toml\n[processes]\ncharteredBy = ''d9001''\nactive = [''actor-enrollment'', ''agile-workflow'', ''deploy'', ''doc-sync'',\n          ''element-critique'', ''issue-resolution'', ''render'']\n```\n\n**After `keel migrate`:**\n\n```toml\n[processes]\ncharteredBy = ''d0226''\nactive = [''actor-enrollment'', ''agile-workflow'', ''decision-authoring'', ''decision-channel'',\n          ''deploy'', ''distributed-collaboration'', ''doc-sync'', ''element-critique'',\n          ''issue-resolution'', ''knowledge-graph-memory'', ''render'']\n```\n\n`d0226` is **keel's own charter Decision** — `keelChartersItsOwnSet`, from this repository. It does not exist in the downstream project's tree at all.\n\nAll three processes the project had **deliberately declined** were silently re-enabled: `decision-channel`, `distributed-collaboration`, `knowledge-graph-memory`. Each was declined with recorded reasoning in the project's charter Decision, and one of those (`knowledge-graph-memory`) was declined by the human author personally, against a condition that was arguably met, on cost grounds.\n\nThe migration summary reported only:\n\n```\ntotals: 275 file(s), 275 edit(s), 0 blocker(s)\nwrote 275 file(s). Re-plan is empty: the migration is complete and idempotent.\n```\n\n`activation.toml` appeared in the dry-run plan as a bare `update contracts/activation.toml`, indistinguishable from the other 274 entries.\n\n## Why it is worse than a lost edit\n\nHad it not been caught, the project would have:\n\n1. silently resumed enforcing three processes its charter argues against;\n2. reported `keel onboard` -> `CHARTERED by d0226` — a Decision that **does not exist in that tree**, so the charter link dangles while still reading as chartered.\n\nThe second is the honest-state failure: `keel onboard` would assert a charter, name a Decision, and that Decision would be unresolvable. A project that ''knows what it chose not to do'' is D0225's stated purpose, and after migration it does not.\n\nIt was caught only because the file was backed up beforehand on suspicion, having been noticed in the dry-run plan. Nothing in the tool surfaced it.\n\n## Expected\n\n`.engine/contracts/activation.toml` is **project-owned data living in an engine-shipped path**. Migrate should either:\n\n1. **never overwrite it** — treat it the way the docs already describe for files the engine does not ship; or\n2. **merge** — take new engine keys, preserve `charteredBy` and the project's `active` list; or\n3. **refuse and list it as a blocker**, the way migrate already refuses when the engine has removed a type, so the operator resolves it deliberately.\n\n(3) is most consistent with the existing design — migrate already knows how to stop and name what it cannot safely change.\n\nMore generally: any file under `.engine/contracts/` that a project is *invited to edit* (this one says `Edit by hand, or use keel activate / keel deactivate`) needs the same protection. A file the tool tells you to edit and then silently overwrites is a trap.\n\n## Related\n\n`keel sync-claude` gets this right for a comparable case — it reports `settings.json merged (keel-owned entries only)`. The same discipline applied to `activation.toml` would fix this.\n\n## Environment\n\n```\nfrom: keel 0.3.0 (build c444ca5)\nto:   keel 0.3.1 (build c4d5dbf), sha256 verified against the release digest\n```\nWindows 11. Project scaffolded 2026-08-29 via `keel init . --profile strict`, chartered 2026-08-30 via the `project-onboarding` skill.\n";
        :>> saidBy = "williamweatherholtz"; :>> saidAt = "2026-08-31"; :>> channel = StatementChannel::github;
        :>> sourceUrl = "https://github.com/williamweatherholtz/sysmlv2-ai-toolkit/issues/39";
        :>> sourceTrust = SourceTrust::untrusted;
    }

    part st053 : Statement {
        :>> id = "f6319c95-ce74-4572-82b9-2859f0e8673d";
        :>> title = "GH#33 guard:scaffold-placeholder misses placeholder ACTORS - a Person named 'Your Name' survives a fully green run";
        :>> createdAt = "2026-08-31"; :>> createdBy = "claudeOpus5";
        :>> text = "## Summary\n\n`guard:scaffold-placeholder` passes while the shipped placeholder actors — including a `Person` named `''Your Name''` — are still registered in `.tracking/actors.sysml`. `keel enroll` appends real actors beside them without removing or flagging them, so a scaffolded project can run fully green with an unowned human identity in its actor registry.\n\n## Repro\n\n1. `keel init myproject --profile strict`\n2. `keel enroll --actor will --name ''William Weatherholtz'' --kind human --role supervisor --email ... .`\n3. `keel enroll --actor claudeOpus5 --name ''...'' --kind ai --role contributor .`\n4. `keel guard .`\n\n## Observed\n\n`.tracking/actors.sysml` after both enrollments:\n\n```sysml\npackage ProjectActors {\n    private import EngineElement::*;\n\n    part you : Person { :>> name = ''Your Name''; :>> email = ''you@example.com''; }\n    part ai : Actor { :>> name = ''AI assistant''; :>> kind = ActorKind::ai; }\n    part will : Person { :>> name = ''William Weatherholtz''; ... :>> role = ''supervisor''; }\n    part claudeOpus5 : Actor { :>> name = ''Claude Opus 5 (Claude Code)''; ... }\n}\n```\n\nGuard output:\n\n```\n[guard:scaffold-placeholder] PASS — 326 scanned, 0 warning(s), 0 violation(s)\n[guard:actors]               PASS — 3 scanned, 0 warning(s), 0 violation(s)\n[guard] ALL PASS\n```\n\nBoth placeholders survive a full green run. (Side observation: `guard:actors` reports **3 scanned** against **4** declared parts — possibly unrelated, but the count does not match the file.)\n\n## Why it matters\n\n`you` is a registered `Person`, and `Person` is the type that gates human-only authority. Per D0106 and the enroll output itself, accepting a Decision, dispositioning a >= Medium finding and adjudicating a contributor conflict all require a human actor — `keel enroll --kind ai` explicitly refuses them. A placeholder `Person` is therefore a registered human identity that nobody owns.\n\nThe scaffold comment does say `EDIT to your real actors`, but that is a reminder, and D0047 is explicit that manual vigilance is not a control.\n\n## NOT tested\n\nI did **not** run `keel accept <decision> --by you` to see whether an attestation attributed to the placeholder would be accepted, because doing so would record a real acceptance in a real project. This is reported as an untested exposure, not a demonstrated exploit.\n\n## Expected\n\nEither:\n\n1. `guard:scaffold-placeholder` flags placeholder actors the way it flags other scaffold residue — the strings are fixed and known (`Your Name`, `you@example.com`, `AI assistant`); or\n2. `keel enroll` removes or supersedes the placeholders on the first real enrollment, since that is the moment the project stops needing them.\n\n(1) is the control; (2) removes the occasion. Both would be better than either.\n\nNote that the workaround is itself awkward: removing them by hand is blocked by the fact-surface write guard (`[keel] in-place sed over a fact surface`), so a user following the scaffold's own advice to ''EDIT to your real actors'' hits a gate telling them to use a write API that has no actor-removal verb.\n\n## Environment\n\n```\nkeel 0.3.0\nbuild commit: c444ca5\napi contract: 2.0.0 (derived)\nguards: 51 (42 hard-blocking, 9 warning-only)\n```\nWindows 11. Project scaffolded 2026-08-29 via `keel init . --profile strict`.\n";
        :>> saidBy = "williamweatherholtz"; :>> saidAt = "2026-08-30"; :>> channel = StatementChannel::github;
        :>> sourceUrl = "https://github.com/williamweatherholtz/sysmlv2-ai-toolkit/issues/33";
        :>> sourceTrust = SourceTrust::untrusted;
    }

    part st054 : Statement {
        :>> id = "c670588d-f9ea-4c89-a0c5-04491bd269d8";
        :>> title = "GH#32 Protected-path enforcement is tool-bound, not path-bound: a shell redirect and rm write .engine/decisions/ ungated, and the override obligation never fires";
        :>> createdAt = "2026-08-31"; :>> createdBy = "claudeOpus5";
        :>> text = "## Summary\n\nProtected-path enforcement is bound to the **tool** that writes, not to the **path** being written. A shell redirect and `rm` reach `.engine/decisions/` — a governance surface — completely ungated, and because the write never touches the gate, `keel override`'s obligation record never fires either.\n\n## Observed\n\nUnder the strict profile, an in-place `sed` over a fact surface IS blocked:\n\n```\n$ sed -i '/part you : Person/d' .tracking/actors.sysml\n[keel] in-place sed over a fact surface - use the keel write API (D0176; blocking under the strict profile)\n```\n\nGood. But in the same session, against a path that appears in the PreToolUse protected list (`.engine/decisions/`):\n\n```\n$ sed -e 's/package Decision0001 {/package Decision0230 {/' /\n      .engine/decisions/0001-landscapeProcessCharter.sysml /\n      > .engine/decisions/0230-landscapeProcessCharter.sysml      # succeeded, ungated\n\n$ rm .engine/decisions/0001-landscapeProcessCharter.sysml          # succeeded, ungated\n```\n\nBoth went through with no gate, no prompt, no record.\n\n## The obligation never fired\n\nBefore the write I armed the sanctioned unlock:\n\n```\n$ keel override .engine/decisions/0230-landscapeProcessCharter.sysml --reason ''...''\noverride armed for `.engine/decisions/0230-landscapeProcessCharter.sysml` - SINGLE USE,\nexpires in 900s; consumption records an obligation (D0176/K7).\n```\n\nAfter the write:\n\n```\n$ keel enforcement-report .\n  ''overrideLedgerEvents'': 0,\n  ''overrideObligationsUnsynced'': 0,\n  ''overrideObligationsTracked'': 0,\n```\n\nThe override was armed and never consumed, because the write bypassed the mechanism that would have consumed it. D0176's guarantee that *''consumption records an obligation''* holds only for writes that arrive through Write/Edit.\n\n## Why it matters\n\n`.engine/decisions/` holds accepted Decisions and their acceptance events. The pre-write hook lists it as protected precisely because it is a governance surface. A path that can be written by redirect is a path where a Decision's `status`, or an acceptance `TestResult`'s `judgedBy`, can be altered with no gate and no obligation trail.\n\nThe pre-bash hook already demonstrates the right instinct — it pattern-matches `sed -i` on fact surfaces. It just does not cover `>` redirect, `tee`, `cp`, or `rm` to the same paths.\n\n## Expected\n\nEither:\n\n1. **path-bound enforcement** — any write to a protected path is gated regardless of mechanism; or\n2. **widen the pre-bash matcher** to cover redirect / `cp` / `mv` / `tee` / `rm` targeting protected paths, the way it already covers `sed -i`.\n\n(1) is the durable fix; (2) closes the observed hole. Either way `keel override` should be the only way through, so the obligation ledger stays honest.\n\n## Related\n\nSibling finding in the same session: `guard:scaffold-placeholder` passes with a placeholder `Person` still registered in `.tracking/actors.sysml`. Filed separately. Together — an ungated write path to `.engine/decisions/` plus an unowned registered `Person` — they are the two halves of a fabricated-acceptance path. **I did not test that end to end** and am not claiming it; each is reported as the individual defect it is.\n\n## Environment\n\n```\nkeel 0.3.0\nbuild commit: c444ca5\napi contract: 2.0.0 (derived)\nguards: 51 (42 hard-blocking, 9 warning-only)\n```\nWindows 11, Git Bash. Project scaffolded 2026-08-29 via `keel init . --profile strict`.\n";
        :>> saidBy = "williamweatherholtz"; :>> saidAt = "2026-08-30"; :>> channel = StatementChannel::github;
        :>> sourceUrl = "https://github.com/williamweatherholtz/sysmlv2-ai-toolkit/issues/32";
        :>> sourceTrust = SourceTrust::untrusted;
    }

    part st055 : Statement {
        :>> id = "351b130c-e33c-4a58-8e20-c2d7248a5949";
        :>> title = "GH#31 No item type for a design INPUT - a value the design consumes but does not decide";
        :>> createdAt = "2026-08-31"; :>> createdBy = "claudeOpus5";
        :>> text = "## Summary\n\nThere is no item type for **a value the design consumes but does not decide** — a design input. Frost depth, static pressure, soil infiltration rate, available supply flow, mature plant size. Every existing type is something you *decide*, something you *require*, something you *watch without gating*, or something someone *uttered*.\n\nThis surfaced on a real project (residential landscape/irrigation) whose author said, verbatim: *''I'll be providing more facts to serve as basis for calculations.''* There is nowhere correct to put them.\n\n## Walking the type list\n\n| Type | Why it does not fit |\n|---|---|\n| `Decision` | implies someone *chose* it, with a rationale and a supersession path. `FROST = 30 in` is not a choice anyone made. |\n| `SystemRequirement` / `Requirement` | a *shall*, not an *is*. A design input constrains the design; it is not a contract the system must meet. |\n| `Indicator` + `Measurement` | closest — `Measurement` already carries `value` / `measuredAt` / `source`. But `Indicator` is invariant-7 **''MONITORED with no enforced threshold — never gated''**, and a design input *is* gated: zone sizing must not exceed available GPM. Using it would mis-signal the semantics. |\n| `Statement` | what someone *said*, not what is true. Correct for the utterance, wrong for the value. |\n| `Claim` | a work-claim (who is working an item). Unrelated despite the name. |\n| `Brief` / `Persona` / `Component` | not values. |\n\n## What I did instead, and why it only half-works\n\nFor an assumed supply floor I recorded a `Decision`:\n\n```\nd0231 — Design to a supply floor of 7 GPM at the point of connection, pending measurement\n```\n\nThat is *defensible here*, because choosing to design to a floor pending measurement genuinely **is** a decision, with a real rationale and a real supersession path (the bucket test).\n\nIt breaks on the very next fact. `FROST = 30 in` recorded as a `Decision` would fabricate an author, a rationale and a supersession path for a fact about the world. The workaround does not generalise.\n\n## What is NOT being asked for\n\nNot an `Assumption` type. issue105 is right that assumption-ness must be **computed** (unverified + depended-upon) rather than authored, and that should not change. This asks for the **carrier** the computation runs over — today there isn't one, so the computed lens has nothing to point at.\n\nConcretely, in this project `keel assumptions` returns `count: 0` while the design demonstrably rests on an unmeasured GPM figure. It returns 0 correctly, because nothing depends on `d0231` yet — but the reason there is no natural dependent is that there is no type for the values that would depend on it either.\n\n## Sketch of a fit (not prescriptive)\n\nA part def carrying `value` / `unit` / `source` / `asOf`, which:\n\n- participates in the `#DependsOn` propagation set, so dependents go suspect when the value moves;\n- is verifiable by a `Test`, so **measured vs assumed is computed** from whether a passing result exists, rather than declared in a field that can disagree with reality;\n- is *gateable*, unlike `Indicator`.\n\nThat last point is the whole difference from `Indicator`, and it is what makes this a separate type rather than a relaxation of that one.\n\n## Environment\n\n```\nkeel 0.3.0\nbuild commit: c444ca5\napi contract: 2.0.0 (derived)\nguards: 51 (42 hard-blocking, 9 warning-only)\n```\nWindows 11. Project scaffolded 2026-08-29 via `keel init . --profile strict`.\n";
        :>> saidBy = "williamweatherholtz"; :>> saidAt = "2026-08-30"; :>> channel = StatementChannel::github;
        :>> sourceUrl = "https://github.com/williamweatherholtz/sysmlv2-ai-toolkit/issues/31";
        :>> sourceTrust = SourceTrust::untrusted;
    }

    part st056 : Statement {
        :>> id = "d6d5bf4d-600b-414c-9cc7-329b21549d10";
        :>> title = "GH#30 Project decision numbering collides with .engine/reference decisions (first record decision lands a red tree; any renumber dodge collides on the next engine release)";
        :>> createdAt = "2026-08-31"; :>> createdBy = "claudeOpus5";
        :>> text = "## Summary\n\nA freshly scaffolded project's first `keel record decision` allocates **D0001**, which collides with the engine's own shipped reference decision (`.engine/reference/decisions/0001-text-files-are-truth.sysml`) because the registry and the `duplicate-identity` guard scan `.engine/reference/` into the same identity namespace as the project's `.engine/decisions/`. The allocator and the guard disagree about what the namespace contains, so the sanctioned write path produces a tree the gate rejects.\n\n**Author position (wweatherholtz):** D0001 **is the right allocation** — a project's decisions should number monotonically from d0001 within that project. The engine's reference set is the *engine's* history, not the project's; it should not share the project's identity namespace (exclude it from duplicate-identity scope, or namespace its packages/parts distinctly, e.g. `EngineDecision0001`).\n\n## Environment\n\n```\nkeel 0.3.0\nbuild commit: c84671a+dirty\napi contract: 2.0.0\n```\nWindows 11, project scaffolded with `keel init` on 2026-08-25.\n\n## Repro\n\n1. `keel init myproject` (empty `.engine/decisions/`)\n2. Write any valid draft file and run `keel record decision --from DRAFT.md`\n   → `recorded D0001 (proposed) -> .engine/decisions/0001-<slug>.sysml`\n3. `keel guard .`\n\n## Observed\n\n```\nERROR .engine/reference/decisions/0001-text-files-are-truth.sysml:1: duplicate package name `Decision0001` (also declared at .engine/decisions/0001-process-set-charter.sysml:4) — the registry SILENTLY MERGES same-named packages, so this corruption would land green (issue074)\nERROR .engine/reference/decisions/0001-text-files-are-truth.sysml:6: duplicate declared name `d0001` in package `Decision0001` (also at .engine/decisions/0001-process-set-charter.sysml:10) — concurrent allocation produces no git conflict, so nothing else would warn\n[guard:duplicate-identity] FAIL — 327 scanned, 0 warning(s), 2 violation(s)\n```\n\n## Why renumbering is not a workaround\n\nWe renumbered the project decision to D0232 (one past the shipped reference range 0001–0231) to get the gate green. That collides **on the very next engine release**: when the engine records its own decision 0232 and a project runs `keel migrate`, the upgraded `.engine/reference/` lands D0232 into a tree that already declares `Decision0232`/`d0232` — the same two duplicate-identity violations, now caused by an upgrade the project cannot refuse. Any numbering dodge loses this race eventually. Allocating above the reference range also breaks the author-intended semantics (project decisions starting at d0001).\n\n## Expected\n\nEither of:\n- `.engine/reference/**` is excluded from the project identity namespace (registry and duplicate-identity guard treat it as read-only engine history, not project instances), so a project's `Decision0001` is legal; or\n- the engine's reference decisions are namespaced distinctly (package/part prefix) so they can never collide with `DecisionNNNN`/`dNNNN` in any project, at any number.\n\nAdditionally the allocator and the registry should agree on one namespace definition — `record decision` scanning only `.engine/decisions/` while the guard scans reference too is the mechanism that lets the sanctioned write path emit a red tree.\n\n## Impact\n\nEvery keel project that records at least one decision hits this on its first `keel record decision` + `keel guard` cycle. Discovered during project-onboarding of a real project (se-templates); the project is currently carrying D0232/D0233 as a stopgap and intends to renumber to d0001-based once this is fixed.\n";
        :>> saidBy = "williamweatherholtz"; :>> saidAt = "2026-08-25"; :>> channel = StatementChannel::github;
        :>> sourceUrl = "https://github.com/williamweatherholtz/sysmlv2-ai-toolkit/issues/30";
        :>> sourceTrust = SourceTrust::untrusted;
    }

    part st057 : Statement {
        :>> id = "b2faa6a8-1c4f-43e2-a049-e939950f9068";
        :>> title = "GH#29 keel: decisions auto-accepted under standing consent";
        :>> createdAt = "2026-08-31"; :>> createdBy = "claudeOpus5";
        :>> text = "<!-- keel-standing-thread -->\n\nEvery Decision auto-accepted under your standing consent (D0207) is posted here as a comment rather than as its own issue, so this thread is the override surface for all of them and **nothing here needs you**.\n\nTo reverse one, reply `reject dNNNN <why>` naming the decision.\n\nNobody is assigned, so you can mute this thread. A decision that genuinely needs you is a FORK: it opens its own issue and assigns you, which notifies through a mute.";
        :>> saidBy = "github-actions[bot]"; :>> saidAt = "2026-08-25"; :>> channel = StatementChannel::github;
        :>> sourceUrl = "https://github.com/williamweatherholtz/sysmlv2-ai-toolkit/issues/29";
        :>> sourceTrust = SourceTrust::untrusted;
    }

    part st058 : Statement {
        :>> id = "84e823cb-e70b-4a4f-b38e-08f675ec2f2a";
        :>> title = "GH#14 An unrecognized --flag silently becomes the ROOT argument - keel guard --read gated a phantom directory";
        :>> createdAt = "2026-08-31"; :>> createdBy = "claudeOpus5";
        :>> text = "keel 0.2.3 (build 1546d19). `keel guard --read .` is parsed with '--read' as ROOT: the guard suite runs against a nonexistent directory named '--read', producing 0-scanned rows, absence warnings (declared rule not present), and exit 1 - while plain `keel guard` on the real tree exits 0.\n\n**Cost in the field:** a session read the phantom run's FAILED as a broken warning-read-ledger, concluded commits were hard-blocked for the whole team, escalated to peers, and told the human - all downstream of one silently-swallowed flag. A second session lost `guard --help` to the same trap.\n\n**Suggested control:** refuse any argument starting with '-' that is not a recognized flag, naming it ('unknown flag --read; ROOT must be a directory') - never bind it as a path. A cheap invariant at every subcommand's arg parse.\n\nTwo-session repro: run `keel guard --read .` on any project; compare with `keel guard .`.";
        :>> saidBy = "williamweatherholtz"; :>> saidAt = "2026-08-24"; :>> channel = StatementChannel::github;
        :>> sourceUrl = "https://github.com/williamweatherholtz/sysmlv2-ai-toolkit/issues/14";
        :>> sourceTrust = SourceTrust::untrusted;
    }

    part st059 : Statement {
        :>> id = "7b4e60b2-2b2b-4303-819d-6e94a450e248";
        :>> title = "GH#9 keel land can report 'landed' while just-authored facts never reach the pushed commit";
        :>> createdAt = "2026-08-31"; :>> createdBy = "claudeOpus5";
        :>> text = "Found in Penumbra (recorded there as issue125), keel 0.2.3+.\n\n**What happened:** a session authored three Claim records via hand-edit of .tracking/claims/<actor>.sysml, ran `keel land`, and got 'keel land: landed.' Three days later, git ancestry showed those additions first reached a commit that day - the claims never existed in any pushed tree, so the exclusion they assert was phantom for three days. guard:claim-ancestry caught it at the eventual commit (good control), but only then.\n\n**Root:** on a shared checkout with branch churn, land can push while the working tree's just-authored facts are uncommitted - and still print 'landed'.\n\n**Suggested control:** land should either (a) commit-then-push what the write API just authored, or (b) refuse with 'authored but uncommitted: <files>' - never print 'landed' over a working-tree-only write. A cheap invariant: after land, `git status --porcelain .tracking/` must be empty or land names what it left behind.";
        :>> saidBy = "williamweatherholtz"; :>> saidAt = "2026-08-24"; :>> channel = StatementChannel::github;
        :>> sourceUrl = "https://github.com/williamweatherholtz/sysmlv2-ai-toolkit/issues/9";
        :>> sourceTrust = SourceTrust::untrusted;
    }

    part st060 : Statement {
        :>> id = "e5fbfbfb-195c-45ec-9ba3-1fdc0f317ab4";
        :>> title = "Ingest the GitHub issues and fix them";
        :>> createdAt = "2026-08-31"; :>> createdBy = "claudeOpus5";
        :>> text = "ingest github issues and fix";
        :>> saidBy = "wweatherholtz"; :>> saidAt = "2026-08-31"; :>> channel = StatementChannel::chat;
    }

    part us062 : UserStory {
        :>> id = "29514f9d-14cb-43d7-b810-51e1e24d61b4";
        :>> title = "Decision numbering no longer collides with the engine's reference decisions";
        :>> createdAt = "2026-08-31"; :>> createdBy = "claudeOpus5";
        :>> asA = "downstream maintainer";
        :>> iWant = "my project's first decision to record without a red tree";
        :>> soThat = "I can author decisions from day one";
        :>> implication = ImplicationKind::bug;
        :>> triageNote = "bug and ALREADY RESOLVED: verified empirically today on a fresh strict project - d0001 recorded alongside 261 ReferenceDecisionNNNN packages, validate clean, duplicate-identity 368 scanned 0 violations. D0139/issue291's disjoint-prefix rename is what fixed it. Triaged as bug rather than none because it WAS a defect; the resolution is evidence, not a dismissal.";
    }
    #DerivedFrom dependency from us062 to st056;

    part us063 : UserStory {
        :>> id = "5f8bc4a6-7a47-4344-bcec-63ba5301d382";
        :>> title = "keel migrate no longer overwrites a downstream project's chartered process set";
        :>> createdAt = "2026-08-31"; :>> createdBy = "claudeOpus5";
        :>> asA = "downstream maintainer";
        :>> iWant = "my adoption choices to survive an engine upgrade";
        :>> soThat = "an upgrade does not silently revert decisions nobody revisited";
        :>> implication = ImplicationKind::bug;
        :>> triageNote = "bug and ALREADY RESOLVED: this is issue314, found by the federation suite and fixed today - project-owned contracts (activation, adoption-profile, pin, install record, github-actors, parser baseline) are ADDED by resync and never overwritten. Verified: a project chartered by d9001 keeps it across a migration.";
    }
    #DerivedFrom dependency from us063 to st052;

    part us064 : UserStory {
        :>> id = "1d11589f-dddc-4362-9dc5-4ed45eb63bd8";
        :>> title = "An unrecognised flag must be refused, not silently taken as the ROOT";
        :>> createdAt = "2026-08-31"; :>> createdBy = "claudeOpus5";
        :>> asA = "any operator";
        :>> iWant = "a mistyped flag to fail loudly";
        :>> soThat = "a typo cannot produce a green run over a directory that does not exist";
        :>> implication = ImplicationKind::bug;
        :>> triageNote = "bug and the worst kind: TWO defects compounding - silent argument mis-parsing plus pass-at-zero - so keel guard --read gated a phantom directory and reported every guard PASS with 0 scanned, which is indistinguishable from a clean tree. I hit the same class building github-ingest, where a trailing --at value became the root.";
    }
    #DerivedFrom dependency from us064 to st058;

    // Routed under D0268 (the owner's instruction is the acceptance untrusted input requires).
    #Implicates dependency from us062 to d0268;
    #Implicates dependency from us063 to d0268;
    #Implicates dependency from us064 to d0268;
    #Implicates dependency from us064 to issue319;

    part st061 : Statement {
        :>> id = "c7fee024-d357-469f-bfec-ac0437bc7806";
        :>> title = "A process: pending decisions always come with a link to the exec-summary artifact, never buried";
        :>> createdAt = "2026-08-31"; :>> createdBy = "claudeOpus5";
        :>> text = "create a new process - if there are decisions for me to make, always give me a link to the executive summary artifact.  Do not bury it under past messages.  do that now please";
        :>> saidBy = "wweatherholtz"; :>> saidAt = "2026-08-31"; :>> channel = StatementChannel::chat;
    }

    part st062 : Statement {
        :>> id = "e4fb6930-2f9e-4333-a48b-ea8f576bf625";
        :>> title = "Adjudication: one Need, drift first but widened to a full status command, async CI, repo-level trust unchanged";
        :>> createdAt = "2026-08-31"; :>> createdBy = "claudeOpus5";
        :>> text = "[x] Keep ONE Need - trust and update-consent are the same predicate - RECOMMENDED\n[x] Drift report first - RECOMMENDED\nNote: I really want a full status output for state of everything including versioning, library update new processes, etc. a command I can run to check all bases\n[x] Asynchronous - land records the SHA, the next keel command surfaces a failure - RECOMMENDED\n[x] Keep repo-level trust exactly as written; --trust overrides case by case - RECOMMENDED";
        :>> saidBy = "wweatherholtz"; :>> saidAt = "2026-08-31"; :>> channel = StatementChannel::chat;
    }

    part us065 : UserStory {
        :>> id = "ceb03e9b-203a-4bed-a1be-6fb894d185f5";
        :>> title = "A single status command that checks all bases: versions, library drift, new units, work, CI";
        :>> createdAt = "2026-08-31"; :>> createdBy = "claudeOpus5";
        :>> asA = "supervisor";
        :>> iWant = "one command that reports the state of everything - engine version, library units available and behind, and what is waiting";
        :>> soThat = "I can check all bases without running five commands and comparing their output by hand";
        :>> implication = ImplicationKind::verifiedRequirement;
        :>> triageNote = "verifiedRequirement and not priority: their tab-2 SELECTION was a priority (drift first), but the NOTE widens what that task must deliver - from a unit-drift report to a full state readout including new processes available in the library. The widening is a contract change, so it routes as a requirement rather than as ordering. Recorded separately from the four acceptances because it is the one thing in the digest that is not an answer to a question I asked.";
    }
    #DerivedFrom dependency from us065 to st062;
}
