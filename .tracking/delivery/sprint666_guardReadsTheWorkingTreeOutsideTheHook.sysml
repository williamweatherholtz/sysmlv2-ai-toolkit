// ProjectDeliveryS666 — Sprint 666: The five diff-reading guards read the working tree outside a git hook and the staged index inside one, and say which (D0440, resolving issue464). On 2026-09-10 the D0425 verifier ran keel guard --no-receipt over a tree whose sprint edits were not yet staged and reported ALL PASS; the pre-commit hook then refused the same edits on process-change once git add had run. The guards read git diff --cached, so outside a hook they judged an empty index and called it a clean tree - every verifier verdict was blind to a locked-file edit until the moment it was staged.. EXECUTE. 3 pts.
package ProjectDeliveryS666 {
    private import EngineElement::*;
    private import EngineWork::*;
    private import EngineVerification::*;
    private import EngineRelationships::*;

    #CharteredBy dependency from guardReadsTheWorkingTreeOutsideTheHookStory to d0440;
    #CharteredBy dependency from guardReadsTheWorkingTreeOutsideTheHookStory to d0441;

    part guardReadsTheWorkingTreeOutsideTheHookStory : Story {
        :>> id = "9dd96e52-2900-40e5-a9a3-55719016c606";
        :>> title = "Sprint 666: The five diff-reading guards read the working tree outside a git hook and the staged index inside one, and say which (D0440, resolving issue464). On 2026-09-10 the D0425 verifier ran keel guard --no-receipt over a tree whose sprint edits were not yet staged and reported ALL PASS; the pre-commit hook then refused the same edits on process-change once git add had run. The guards read git diff --cached, so outside a hook they judged an empty index and called it a clean tree - every verifier verdict was blind to a locked-file edit until the moment it was staged. (3 pts)";
        :>> createdAt = "2026-09-11"; :>> createdBy = "claudeOpus5"; :>> kind = WorkKind::code; :>> priority = WorkPriority::p0; :>> owner = "claudeOpus5"; :>> estimatedPoints = 5;
    }

    action def DeliveryRunS666 {
        action storyGuardReadsTheWorkingTreeOutsideTheHook;
        verification storyGuardReadsTheWorkingTreeOutsideTheHookDoD : Test { :>> id = "6405912c-e871-4963-9e68-82f4bfec4d7c"; :>> method = VerificationMethod::test; :>> procedureText = "Outside a git hook (neither GIT_INDEX_FILE, which git sets for every hook, nor KEEL_HOOK is set) process-change, doc-sync, decision-amends-process, retro-backlog and ownership read the working tree against HEAD - git diff HEAD --name-status -M with the same filters, every untracked file as an addition, a file's text from disk - and inside a hook they read the staged index exactly as before; each names its read in the summary line as (read: working tree) or (read: index), the note is neither an actionable warning nor counted history and status/serve do not count it, and the guard receipt's key carries the mode so a green terminal run never answers for a hook's index read. D0388 pair: tests/guard_reads_the_working_tree.rs - known-positive: a fixture repo with an unstaged edit to .engine/processes/x.sysml and no Decision fails process-change at the terminal naming the file (today it passes); known-negative: the same tree with an unstaged marked Decision beside it passes; the hook shape with KEEL_HOOK set passes the unstaged edit and fails it once staged; a clean tree passes under both. guards::change_read_tests (3) on the note's classification. Every child process in the test pins GIT_INDEX_FILE and KEEL_HOOK itself, because the land's touched run executes inside a post-commit hook where GIT_INDEX_FILE is inherited. DEVIATION from the backlog DoD, stated: it names 'the D0308 acceptance-binds-to-text staged read' as an index reader; acceptance_binds_to_text reads the working tree through corpus already and was not touched - the seven staged_* call sites (five guards, the workspace gate's marked-Decision probe, retro-backlog's added-item scan) are the set. SECOND ITEM, D0441 / issue475 (dcResyncIsNotASelfModification), delivered here because the two cannot land apart: the working-tree read made process-change refuse keel migrate's own resync inside its D0336 gate and revert the update (six migration_fixture_is_realistic tests red on the first touched run). process-change drops a locked path under .engine/ whose text is what the resync would write - the embedded file, or the sectioned-contract merge over HEAD (migrate::resync_text) - and says so in one warning line; inert in the self-build and for a deleted file. D0388 pair: tests/resync_is_not_a_self_modification.rs - known-positive: a stale locked skill overwritten with the embedded text passes with no Decision, the line naming it; known-negative: one appended line fails naming the file; the self-build case fails the same way. migration_fixture_is_realistic passes 6 of 6 again."; }
        // RAN: keel suite --touched: 719 passed 0 failed 845 s, stems embedded guards migrate receipt serve status + lib, at 1789107167 > launch 1789106314, head c88feb2; probe pairs: guard_reads_the_working_tree 4 passed, resync_is_not_a_self_modification 3 passed, lib change_read_tests 3 passed; clippy -D warnings pass; sync-claude --check clean
        part storyGuardReadsTheWorkingTreeOutsideTheHookDoDR1 : TestResult { :>> id = "6012a92c-28ea-4294-b9b9-df0e058b8643"; :>> outcome = VerdictKind::pass; :>> judgedAgainst = "c88feb2"; :>> judgedAt = "2026-09-11"; :>> judgedBy = "claudeOpus5"; }
    }

    verification guardReadsTheWorkingTreeOutsideTheHookRefineGate : Test { :>> id = "dff322ce-1047-4253-ac7b-b0a6e72ecc01"; :>> title = "Sprint 666 refine gate (DoR)"; :>> createdAt = "2026-09-11"; :>> createdBy = "claudeOpus5"; :>> method = VerificationMethod::inspect; :>> procedureText = "Chartered by D0440 (proposed, process-change: guard source is the enforcement surface under D0209 clause 2, so the commit carries the marked Decision and the human's word is what accepts it). Sized 5 points after the first touched run: the read (3) plus the resync exemption it forced (2 - one predicate, one shared writer/guard function, the embedded engine moved into the library, three tests). One read-mode enum and two readers replacing staged_changes/staged_files and the added-item scan across seven call sites, a READ note the printer folds into the summary line with its exclusions in actionable(), status.rs and serve.rs, one hash in the receipt key, the unit and end-to-end probe pair, and the catalogue paragraph. Ready: issue464 names the shape exactly, and the hook environment was probed in a scratch repository before the design was fixed - GIT_INDEX_FILE is present in pre-commit (plain and -a) and post-commit and absent in a plain shell."; }
    // RAN: keel validate . 760 tracking file(s) validated clean; keel check-engine . .engine instance files validated clean (kernel-free; D0112 phase 2)
    part guardReadsTheWorkingTreeOutsideTheHookRefineGateR1 : TestResult { :>> id = "11b8a4e5-9497-4397-89f1-4da5accf7768"; :>> outcome = VerdictKind::proposed; :>> judgedAgainst = "c88feb2"; :>> judgedAt = "2026-09-11"; :>> judgedBy = "claudeOpus5"; }
    verification guardReadsTheWorkingTreeOutsideTheHookStandupGate : Test { :>> id = "0276d28e-e1d6-4ced-a4d9-5856929de8e3"; :>> title = "Sprint 666 standup gate"; :>> createdAt = "2026-09-11"; :>> createdBy = "claudeOpus5"; :>> method = VerificationMethod::inspect; :>> procedureText = "Order: probe the hook environment first so the detector is a fact and not a guess (GIT_INDEX_FILE set by git in every hook; KEEL_HOOK reserved for a caller that is the gate); write ChangeRead with current() and label(), READ_PREFIX/read_line/is_read beside the HISTORY pair, read_mode() on GuardReport, actionable() excluding the note and print() folding it into the summary line; changed_paths(root, filter, read) with the HEAD diff and the untracked ls-files as A entries when the filter admits additions, falling back to the index when HEAD does not resolve (the issue272 first-commit shape); changed_text reading the index blob or disk; added_items with the same two sources; the seven call sites through them, each report carrying read_line(read); status.rs and serve.rs excluding the note; the receipt key hashing the label; the integration test with every child's environment pinned; the guards.md preamble paragraph and the CLAUDE.md sec 5 line; record D0440 with the marker; then the verifier and recorder. After the first touched run went red: record issue475, dcResyncIsNotASelfModification and D0441 BEFORE the guard edit, move ENGINE_DIR into keel_cli::embedded, write is_engine_resync beside the lock predicates and migrate::resync_text beside the writer, the pair, the guards.md row, rebuild, rerun."; }
    // RAN: guard ALL PASS 43 guards, 65 actionable warning(s); [guard:process-change] 1 scanned (read: working tree), 0 warning, 0 violation; [guard:doc-sync] 0 scanned (read: working tree), 0 warning, 0 violation; [guard:decision-amends-process] 2 scanned (read: working tree), 1 warning, 0 violation; [guard:retro-backlog] 1 scanned (read: working tree), 0 warning, 0 violation; [guard:ownership] 1766 scanned (read: working tree), 0 warning, 0 violation
    part guardReadsTheWorkingTreeOutsideTheHookStandupGateR1 : TestResult { :>> id = "13f6044e-1eac-45bb-8242-1254f8c0274b"; :>> outcome = VerdictKind::proposed; :>> judgedAgainst = "c88feb2"; :>> judgedAt = "2026-09-11"; :>> judgedBy = "claudeOpus5"; }
    verification guardReadsTheWorkingTreeOutsideTheHookImplementGate : Test { :>> id = "7505d4e4-87a4-40fd-b204-70bdf1a52d87"; :>> title = "Sprint 666 implement gate"; :>> createdAt = "2026-09-11"; :>> createdBy = "claudeOpus5"; :>> method = VerificationMethod::test; :>> procedureText = "keel-cli/src/guards.rs: READ_PREFIX, read_line, is_read, ChangeRead { Index, WorkingTree } with current() and label(); GuardReport::read_mode, actionable() excludes the note, print() folds it into the summary line as (read: <mode>); changed_files / changed_paths / changed_text / added_items replace staged_files / staged_changes / staged_added_items; staged_marked_decision, process_change, decision_amends_process, doc_sync, retro_backlog, ownership read under ChangeRead::current() and carry read_line(read); mod change_read_tests (3). keel-cli/src/status.rs: the model section's warning count excludes the note. keel-cli/src/serve.rs: the gate JSON excludes the note from warnings and reports it as read. keel-cli/src/receipt.rs: key() hashes ChangeRead::current().label(). keel-cli/tests/guard_reads_the_working_tree.rs (4). .engine/docs/guards.md: one preamble paragraph naming the five guards and both reads; CLAUDE.md sec 5. keel-cli/src/embedded.rs (new): ENGINE_DIR and engine_text, borrowed by main.rs. keel-cli/src/migrate.rs: pub resync_text. keel-cli/src/guards.rs: is_engine_resync; process_change partitions its MDR set into resynced and judged, counts both as scanned, and announces the resynced paths. keel-cli/tests/resync_is_not_a_self_modification.rs (3). guards.md process-change row. Live on this tree before the verifier: process-change 1 scanned (read: working tree) PASS on the untracked marked D0440; with KEEL_HOOK set 0 scanned (read: index); guard ALL PASS 759 validated clean, check-engine clean, sync-claude --check clean, clippy -D warnings clean after one must_use lint on read_mode."; }
    // RAN: keel suite --touched: 719 passed 0 failed 845 s, stems embedded guards migrate receipt serve status + lib, at 1789107167 > launch 1789106314, head c88feb2; probe pairs: guard_reads_the_working_tree 4 passed, resync_is_not_a_self_modification 3 passed, lib change_read_tests 3 passed; clippy -D warnings pass; sync-claude --check clean
    part guardReadsTheWorkingTreeOutsideTheHookImplementGateR1 : TestResult { :>> id = "41dd0ee5-6b24-4375-b072-de8d49281adc"; :>> outcome = VerdictKind::pass; :>> judgedAgainst = "c88feb2"; :>> judgedAt = "2026-09-11"; :>> judgedBy = "claudeOpus5"; }
    verification guardReadsTheWorkingTreeOutsideTheHookReviewGate : Test { :>> id = "ded81895-0903-4b2d-aabb-bf6cf1377b85"; :>> title = "Sprint 666 review gate — three passes per D0172"; :>> createdAt = "2026-09-11"; :>> createdBy = "claudeOpus5"; :>> method = VerificationMethod::inspect; :>> procedureText = "Delivered: a guard run outside a hook judges the tree on disk, the hook's read is unchanged, and every report and receipt states which population it judged; and process-change tells the engine's own text arriving by keel migrate from a hand edit to a locked file, so a downstream project's resync is retained under its own gate and passes at its commit. Verified by the verifier's receipt only (D0425): validate, check-engine, guard --no-receipt with the five diff-readers naming (read: working tree), sync-claude --check, clippy, the D0388 pair, and the touched run (lib tests included, keel-cli/src moved) read from its receipt after exit. Held back: nothing. Not in scope: the partially staged file outside a hook is read from disk, which is the working tree's truth and not the commit's - the hook's read is the one that decides what lands, and the receipt key keeps the two verdicts apart."; }
    // RAN: guard ALL PASS 43 guards, 65 actionable warning(s) across 9 guard(s); clippy -D warnings pass; sync-claude --check claude-surface: keel-owned subset matches this binary's generator (46 registry skill(s))
    part guardReadsTheWorkingTreeOutsideTheHookReviewGateR1 : TestResult { :>> id = "ea97b9a8-7c23-4c0c-b8ea-3c8949945b1d"; :>> outcome = VerdictKind::proposed; :>> judgedAgainst = "c88feb2"; :>> judgedAt = "2026-09-11"; :>> judgedBy = "claudeOpus5"; }
    verification guardReadsTheWorkingTreeOutsideTheHookCloseOutGate : Test { :>> id = "183e2663-2133-4571-bff5-32d67166d44b"; :>> title = "Sprint 666 closeOut gate (autonomous, D0049)"; :>> createdAt = "2026-09-11"; :>> createdBy = "claudeOpus5"; :>> method = VerificationMethod::inspect; :>> procedureText = "Sprint 666 closes on the verifier's receipt only (D0425): validate, check-engine, guard --no-receipt (ALL PASS, the five diff-readers each naming their read), sync-claude --check clean, clippy clean, the D0388 pair - cargo test on change_read_tests and the guard_reads_the_working_tree binary (4 passed), resync_is_not_a_self_modification (3) and migration_fixture_is_realistic (6) with keystone_sees_renames still green (3) - and the touched receipt with outcome pass, at after the launch epoch and stems naming guards, receipt, serve, status. The recorder writes the six gates and the DoD from that receipt; the backlog items dcGuardReadsTheWorkingTreeOutsideTheHook and dcResyncIsNotASelfModification get their own DoD results and issue464 and issue475 resolve through the #Resolves edges already authored."; }
    // RAN: TOUCHED RECEIPT: outcome=pass passed=719 failed=0 seconds=845 at=1789107167 launch=1789106314; DISCREPANCIES: NONE
    part guardReadsTheWorkingTreeOutsideTheHookCloseOutGateR1 : TestResult { :>> id = "63e884b2-4bde-4314-8a1b-213429cac2fc"; :>> outcome = VerdictKind::proposed; :>> judgedAgainst = "c88feb2"; :>> judgedAt = "2026-09-11"; :>> judgedBy = "claudeOpus5"; }
    verification guardReadsTheWorkingTreeOutsideTheHookRetroGate : Test { :>> id = "484e143c-c5fa-48e3-be2e-9c3dc77ceaf6"; :>> title = "Sprint 666 retro gate (autonomous, D0049)"; :>> createdAt = "2026-09-11"; :>> createdBy = "claudeOpus5"; :>> method = VerificationMethod::analyze; :>> procedureText = "AVOIDABLE-ISSUE SCAN: two new items - issue474 with resolver dcSuiteNamesTheImageLockThatBlockedIt (FINDING 5) and issue475 with resolver dcResyncIsNotASelfModification, delivered in this sprint under d0441 (FINDING 6); FINDINGs 1-4 are carried by issue464 and d0440 already. FINDING 1: the backlog DoD named acceptance-binds-to-text as an index reader; reading guards.rs before designing showed it reads the working tree through corpus and always did - the DoD's inventory was written from memory of the incident, the code's inventory (seven staged_* call sites) was the real set. The deviation is stated in the DoD text rather than absorbed, and the lesson is the one D0388 already states: enumerate the call sites before writing the criterion that counts them. FINDING 2: the hook detector was probed empirically before it was written (a scratch repository's pre-commit and post-commit hooks printing their environment) - GIT_INDEX_FILE turned out to be set in every hook shape, so KEEL_HOOK became a reserved override rather than something the scaffolded hook must export; without the probe the design would have added an export to .githooks/pre-commit that the enforcement-surface lock makes expensive to change. FINDING 3: decision-amends-process warns on D0440 because its context names doc-sync as a guard and a process of that name exists - the known cite-not-amend noise class the guard's own row documents; read past, not silenced. FINDING 4: the working-tree read makes the stop hook's process-change guard fire on an unsigned guards.rs edit at the first turn boundary instead of at commit time - which is the point, and it means a sprint that edits guard source must record its marked Decision BEFORE its first edit lands or the turn boundary blocks; this sprint recorded D0440 first and never met the block - but the retro-backlog guard DID fire at the first turn boundary on this very retro's unstaged text (no item named), which before this sprint would have surfaced only at git commit. FINDING 5: the first verifier receipt was RED on the touched run - cargo could not relink target/release/keel.exe (Access is denied, os error 5) because the primary was running keel guard and keel validate FROM that image to clear the stop-hook block at the same moment; the receipt recorded 61 failing binaries where none ran. Tracked as issue474 (Medium) with dcSuiteNamesTheImageLockThatBlockedIt: the receipt says blocked and names the holder. The primary's rule from here is the console's (issue150/386): its own keel commands run from keel-serve.exe while a verifier's cargo runs. FINDING 6: the verifier's touched run (D0432, the lib and every integration test naming a moved module) went red in six migration_fixture_is_realistic tests that no local run of the sprint's own pair could have reached - keel migrate applies the resync unstaged and then runs the project's own gate, and under the new read process-change refused the engine's own skill file as an unsigned locked-file change and reverted the update. The refusal was not new: under the staged read it fell at a downstream project's post-migrate COMMIT, in the pre-commit hook, where no test had ever committed (guards.rs keystone_violations, code-read). The read moved the refusal to where a test stood. Tracked as issue475 (High) and fixed at the root in this sprint under d0441 - process-change decides by content whether a locked file is the engine arriving - rather than by running migrate's gate in the hook shape, which would have kept the fixture green and the downstream commit refused. The lesson is D0432's: the touched set is the set the land runs, and a pair that proves the change proves nothing about the callers of the changed function."; }
    // RAN: VERIFIER RECEIPT 2026-09-11 head=c88feb2 tree=12 dirty paths (11 modified, 5 untracked); OWED WRITES: NONE
    part guardReadsTheWorkingTreeOutsideTheHookRetroGateR1 : TestResult { :>> id = "059a6a08-abf9-4ca6-9a42-5dbaae5399dc"; :>> outcome = VerdictKind::proposed; :>> judgedAgainst = "c88feb2"; :>> judgedAt = "2026-09-11"; :>> judgedBy = "claudeOpus5"; }
}
