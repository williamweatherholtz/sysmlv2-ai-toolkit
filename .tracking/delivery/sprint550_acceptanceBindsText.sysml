// ProjectDeliveryS550 — Sprint 550: the text a human signed is the text the tree carries - acceptances bind to text, and seventeen editorial drifts are re-bound in the open. EXECUTE. 3 pts.
package ProjectDeliveryS550 {
    private import EngineElement::*;
    private import EngineWork::*;
    private import EngineVerification::*;
    private import EngineRelationships::*;

    #CharteredBy dependency from acceptanceBindsTextStory to d0308;

    part acceptanceBindsTextStory : Story {
        :>> id = "7d4ef889-5168-4fd2-bad0-c9ade5f7fca0";
        :>> title = "Sprint 550: the text a human signed is the text the tree carries - acceptances bind to text, and seventeen editorial drifts are re-bound in the open (3 pts)";
        :>> createdAt = "2026-09-05"; :>> createdBy = "claudeOpus5"; :>> kind = WorkKind::code; :>> priority = WorkPriority::p0; :>> owner = "claudeOpus5"; :>> estimatedPoints = 3;
    }

    action def DeliveryRunS550 {
        action storyAcceptanceBindsText;
        verification storyAcceptanceBindsTextDoD : Test { :>> id = "f473f68e-9959-4396-b654-e1e3373f6e4f"; :>> method = VerificationMethod::test; :>> procedureText = "DELIVERED BACKLOG ITEMS: dcAcceptanceBindsToTheText (resolves issue341 and issue371). DONE: guard 61 acceptance-binds-to-text, hard - for every accepted Decision, decision, rationale and consequences at HEAD equal their VALUES at the SHA the latest AcceptR result binds to (the file at judgedAgainst, else the commit that introduced the file), in one batched cat-file; a difference names the Decision, both SHAs, the fields and the remedy; keel accept --rebind appends AcceptR<n+1> against the current text with notes naming what changed, the first acceptance standing; governing-version still reads R1. MEASURED FIRST: 17 of 301 drifted, all editorial, recorded as issue371 and re-bound under standing consent with the changing commit in each note - none allowlisted. Also: decision-amends-process ignores a staged Decision whose prose is unchanged from HEAD (25 noise warnings on the first re-bind). VERIFY: integration test - accepted fixture green, signed field edited red naming both SHAs and the remedy, reverted green, edited-and-committed then --rebind writes AcceptR2 bound to the new SHA and the guard is green; live guard 302 scanned 0 violations after re-binding; the constraint-def identity test caught the new guard lacking one, added; suite and clippy in the RAN line."; }
        // RAN: cargo test --release --no-fail-fast 486 passed 0 failed; clippy 0; keel guard acceptance-binds-to-text . 302 scanned 0 violations after 17 re-binds; acceptance_binds_to_text 1/1
        part storyAcceptanceBindsTextDoDR1 : TestResult { :>> id = "fc37e0f4-bc55-4b30-b3cd-0c282c505163"; :>> outcome = VerdictKind::pass; :>> judgedAgainst = "eb0adcf"; :>> judgedAt = "2026-09-04"; :>> judgedBy = "claudeOpus5"; }
    }

    verification acceptanceBindsTextRefineGate : Test { :>> id = "ee56f777-9716-4b1e-b01f-926aa4b25ae3"; :>> title = "Sprint 550 refine gate (DoR)"; :>> createdAt = "2026-09-05"; :>> createdBy = "claudeOpus5"; :>> method = VerificationMethod::inspect; :>> procedureText = "READY once the census existed: 17 real drifts and their diffs read by hand before any code, so the guard's first live result (27) was recognisable as ten false positives plus the truth, not accepted as the truth."; }
    verification acceptanceBindsTextStandupGate : Test { :>> id = "5ab02057-f54e-48d8-a07c-1e8f4f73b9f2"; :>> title = "Sprint 550 standup gate"; :>> createdAt = "2026-09-05"; :>> createdBy = "claudeOpus5"; :>> method = VerificationMethod::inspect; :>> procedureText = "THREE CHOICES stated plainly. (1) The LATEST acceptance result is the binding, so a legitimate edit is re-bound with a new result rather than by editing history or living with a permanent violation. (2) Values not source: plus-joined segments are compared as one string - ten early Decisions differed only in indentation between segments. (3) The 17 are re-bound under standing consent rather than queued for the human, because each change is editorial and each note names the commit so the judgment can be checked and undone by their word; the DoD said record, not allowlist, and issue371 is the record."; }
    verification acceptanceBindsTextImplementGate : Test { :>> id = "5390b889-3cf4-458d-99f7-af4be88736b8"; :>> title = "Sprint 550 implement gate"; :>> createdAt = "2026-09-05"; :>> createdBy = "claudeOpus5"; :>> method = VerificationMethod::test; :>> procedureText = "RAN: four wrong results on the way, each a real fact about something else - a heredoc that wrote literal newlines into a Rust string (twice), a batch lookup that looked wrong and was right, whitespace between string segments read as drift; the DoD's suspect-view clause is NOT built and D0308 says so. Then the re-bind of seventeen through the real command, and the guard's first clean run."; }
    verification acceptanceBindsTextReviewGate : Test { :>> id = "2cc0c6aa-fc90-4b58-9de8-a41327c927a6"; :>> title = "Sprint 550 review gate — three passes per D0172"; :>> createdAt = "2026-09-05"; :>> createdBy = "claudeOpus5"; :>> method = VerificationMethod::inspect; :>> procedureText = "THREE PASSES. (1) CAN AN AGENT LAUNDER A SUBSTANTIVE EDIT AS EDITORIAL: yes, by re-binding with a false note - the D0192 limit; the note names the commit, so a reader can diff it, and the re-bind is a recorded acceptance result with recorder and judge stamped. (2) DOES governing-version MOVE: no - it reads R1, so when a Decision took effect is unchanged by re-binding. (3) WHAT IS NOT BUILT: acceptance drift in orient's suspect list; the guard is the hard control and D0308 states the gap."; }
    verification acceptanceBindsTextCloseOutGate : Test { :>> id = "561294ed-8213-4918-8914-24d0a29a56f9"; :>> title = "Sprint 550 closeOut gate (autonomous, D0049)"; :>> createdAt = "2026-09-05"; :>> createdBy = "claudeOpus5"; :>> method = VerificationMethod::inspect; :>> procedureText = "CLOSED. issue341 and issue371 resolve; guard count 61; the seventeen carry AcceptR2 results dated today."; }
    verification acceptanceBindsTextRetroGate : Test { :>> id = "f70905fb-4ad3-45ed-b165-1fca94d751f0"; :>> title = "Sprint 550 retro gate (autonomous, D0049)"; :>> createdAt = "2026-09-05"; :>> createdBy = "claudeOpus5"; :>> method = VerificationMethod::analyze; :>> procedureText = "no new item - already tracked: the suspect-view half is d0308's stated deferral, to be raised if the guard alone proves insufficient; the heredoc class is dcPreBashSeesHeredocSource, which this sprint fed twice more. The census-before-code habit paid for itself again - 27 would have been recorded as 27."; }
}
