// ProjectDeliveryS568 — Sprint 568: two console items built on 2026-08-26 and never recorded - verified against the served console today, armed with tests, and marked done. EXECUTE. 2 pts.
package ProjectDeliveryS568 {
    private import EngineElement::*;
    private import EngineWork::*;
    private import EngineVerification::*;
    private import EngineRelationships::*;

    #CharteredBy dependency from consoleRecordedStory to d0236;

    part consoleRecordedStory : Story {
        :>> id = "06b1f177-bc4e-4278-bac2-45e1ab174d57";
        :>> title = "Sprint 568: two console items built on 2026-08-26 and never recorded - verified against the served console today, armed with tests, and marked done (2 pts)";
        :>> createdAt = "2026-09-05"; :>> createdBy = "claudeOpus5"; :>> kind = WorkKind::code; :>> priority = WorkPriority::p0; :>> owner = "claudeOpus5"; :>> estimatedPoints = 2;
    }

    action def DeliveryRunS568 {
        action storyConsoleRecorded;
        verification storyConsoleRecordedDoD : Test { :>> id = "44e06a03-481b-4b36-bb60-999d27e52f02"; :>> method = VerificationMethod::test; :>> procedureText = "DELIVERED BACKLOG ITEMS: dcComputedViewsRenderAndLink (resolves issue286) and dcTabsFlagWhatNeedsTheHuman (resolves issue288, chartered by d0236). Both mechanisms have been in keel-cli/assets/console.html since commits e4e8ee8 and c3e35f9 (2026-08-26) with no DoD result, so the backlog served them as READY for ten days. DONE today: verified live on a served copy - /api/computed/open-issues returns a dict the generic panel renders as tables (renderComputed/renderRows), item names link through openItem, /api/item/notAnItemXyz answers found:false and the panel says so, the raw payload sits in a collapsed details block; /api/obligations returns four act classes (acceptancesPendingVP 1, authorityQueueVP 132, findingsAwaitingDispositionVP 131, sittingReviewVP 138, all countable) so the act tab badge reads 402 and the other five surfaces read nothing; the served page carries oblFlag, the ? branch for an uncountable class and the ? branch for a failed fetch. Two text-level tests over CONSOLE_HTML pin the mechanisms (D0160's ceiling stated)."; }
        // RAN: same suite receipt: 526/0 exit 0
        part storyConsoleRecordedDoDR1 : TestResult { :>> id = "133966e3-8ab9-46d6-bbee-ef6231d16f22"; :>> outcome = VerdictKind::pass; :>> judgedAgainst = "18270a81975f4de36c4a5f707b85babe8a4f0b9e"; :>> judgedAt = "2026-09-05"; :>> judgedBy = "claudeOpus5"; }
    }

    verification consoleRecordedRefineGate : Test { :>> id = "1b67ee39-6b61-4980-8214-df2b382a3419"; :>> title = "Sprint 568 refine gate (DoR)"; :>> createdAt = "2026-09-05"; :>> createdBy = "claudeOpus5"; :>> method = VerificationMethod::inspect; :>> procedureText = "READY once the premise was checked: both DoDs described work that already existed. The DoD's 2026-08-26 figures (act 140, three classes 50/50/40, acceptances-pending not countable) are a snapshot; today's are 402 over four countable classes, which the mechanism computes rather than the DoD."; }
    verification consoleRecordedStandupGate : Test { :>> id = "372fbe7a-d447-407e-8999-d3861bf67301"; :>> title = "Sprint 568 standup gate"; :>> createdAt = "2026-09-05"; :>> createdBy = "claudeOpus5"; :>> method = VerificationMethod::inspect; :>> procedureText = "THE FINDING IS THE GAP, NOT THE WORK: recording is part of the task, and two items were built without their result - the same shape recorded in memory as build-now-record-later. Neither had a sprint; this sprint is theirs."; }
    verification consoleRecordedImplementGate : Test { :>> id = "bda7d491-5787-4ba3-9d0c-8e3f32bf9139"; :>> title = "Sprint 568 implement gate"; :>> createdAt = "2026-09-05"; :>> createdBy = "claudeOpus5"; :>> method = VerificationMethod::test; :>> procedureText = "RAN: keel serve on a copied binary (port 7791): /api/obligations, /api/surfaces, /api/computed/open-issues, /api/item/issue283, /api/item/notAnItemXyz, GET / grepped for oblFlag / renderComputed / raw payload; cargo test --lib serve::tests 13 passed incl. the two new text-level tests; clippy -D warnings clean; the full suite in the background to completion (receipts on both DoD results)."; }
    verification consoleRecordedReviewGate : Test { :>> id = "187eb332-eefc-4b04-8510-7058040c64d1"; :>> title = "Sprint 568 review gate — three passes per D0172"; :>> createdAt = "2026-09-05"; :>> createdBy = "claudeOpus5"; :>> method = VerificationMethod::inspect; :>> procedureText = "THREE PASSES. (1) IS TEXT-LEVEL ENOUGH: no, and the tests say so (D0160) - they pin presence; the live serve check is the behaviour read-back, recorded in the receipts. (2) DO THE DOD NUMBERS MATTER: the DoD's counts were the day's values; the VERIFY clauses are about mechanism (badge, nothing at zero, ? never 0, ? on failure, tables, links, raw payload), all held. (3) WHY NO DECISION: a console rendering is neither schema nor process; d0236 chartered the tab."; }
    verification consoleRecordedCloseOutGate : Test { :>> id = "d4db3025-28fe-4f29-bc78-7b38f10c6915"; :>> title = "Sprint 568 closeOut gate (autonomous, D0049)"; :>> createdAt = "2026-09-05"; :>> createdBy = "claudeOpus5"; :>> method = VerificationMethod::inspect; :>> procedureText = "CLOSED. Two items done on evidence read today; issue286 and issue288 resolved by computation."; }
    verification consoleRecordedRetroGate : Test { :>> id = "466aa828-68e9-4b92-95cb-f7a5f4ad232d"; :>> title = "Sprint 568 retro gate (autonomous, D0049)"; :>> createdAt = "2026-09-05"; :>> createdBy = "claudeOpus5"; :>> method = VerificationMethod::analyze; :>> procedureText = "no new item - already tracked: the build-now-record-later shape these two items show is the standing feedback memory (recording is part of the task); the deeper control - a task whose code landed with no result - is what the untrusted-taint and stpa-currency work call an undeclared sink, and dcCommitDeltaView on the frontier is the lens that would show a commit touching a task's files with no result. The lesson: a DoD's example numbers date; its mechanism clauses are what to verify."; }
}
