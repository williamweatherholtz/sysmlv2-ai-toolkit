// ProjectDeliveryS311 — Sprint 311: clear the non-blocking burndown — and refuse the one item that
// should NOT be cleared. EXECUTE. 3 pts.
package ProjectDeliveryS311 {
    private import EngineElement::*;
    private import EngineWork::*;
    private import EngineVerification::*;
    private import EngineRelationships::*;

    #CharteredBy dependency from burndownStory to issue132;

    part burndownStory : Story {
        :>> id = "0d800320-0814-6320-9b3e-000000300320";
        :>> title = "Sprint 311: reverify drift, decompose N-8, and leave the orphan alone (3 pts)";
        :>> createdAt = "2026-08-15"; :>> createdBy = "claudeOpus5"; :>> kind = WorkKind::modeling; :>> priority = WorkPriority::p1; :>> owner = "claudeOpus5"; :>> estimatedPoints = 3;
    }

    action def DeliveryRunS311 {
        action storyBurndown;
        verification storyBurndownDoD : Test { :>> id = "0d800321-0814-6321-9b3e-000000300321"; :>> method = VerificationMethod::demo; :>> procedureText = "Human asked to proceed with the whole non-blocking burndown. THREE ITEMS, AND ONE OF THEM WAS REFUSED. (1) DRIFT CLEARED: `keel reverify --all-drift` re-ran the declared gate at HEAD and re-stamped all 9 suspect tasks pass (runtimeParser, rustS2Parser, rustS5CLI, rustS6Orient, rustS7QueryAlign, rustS8runtimeParser, rustS9writeApi, rustToolchainFix, writeApi); `suspect` is now []. (2) N-8 DECOMPOSED: nViewerPersistedViewpoints was the last undecomposed Need. D0115 KEEPS it — it routes N-7's saveable-viewpoint concern into N-8 explicitly while dropping auth/multi-user/per-user — so srViewerPersistedViewState decomposes the surviving scope: viewpoints, filters and view state persist as a DECLARED artifact in the repo and share by travelling in git, needing no account and no server-side per-user state. need_decomposed_pct 97% -> 100%. (3) THE ORPHAN STORY WAS NOT 'FIXED', deliberately. `postReleaseBurndownStory` reports as unrooted because sprint 283 REMOVED a #CharteredBy edge pointing at `postReleaseBurndown`, a backlog action never declared in any commit. Sprint 171's own file says why: 'inventing a charter target to satisfy a guard would fabricate provenance to pass a check — which is the one thing a charter must never do.' Adding a charter now would re-commit precisely that. orphan_stories stays 1 and that is the honest number. clippy clean; 221 tests; validate 336 clean; 33 guards green."; }
        part storyBurndownDoDR1 : TestResult { :>> id = "0d800322-0814-6322-9b3e-000000300322"; :>> outcome = VerdictKind::pass; :>> judgedAgainst = "f9d2495"; :>> judgedAt = "2026-08-15"; :>> judgedBy = "claudeOpus5"; }
    }

    verification bdRefineGate : Test { :>> id = "0d800323-0814-6323-9b3e-000000300323"; :>> title = "Sprint 311 refine gate (DoR)"; :>> createdAt = "2026-08-15"; :>> createdBy = "claudeOpus5"; :>> method = VerificationMethod::inspect; :>> procedureText = "DoR. 'Proceed with all' was taken as authorisation to clear the burndown, NOT as authorisation to make numbers go green. Each of the three was checked for whether clearing it would be truthful before any edit — which is what caught that one of them must not be cleared at all. estimatedPoints=3."; }
    part bdRefineGateR1 : TestResult { :>> id = "0d800324-0814-6324-9b3e-000000300324"; :>> outcome = VerdictKind::pass; :>> judgedAgainst = "f9d2495"; :>> judgedAt = "2026-08-15"; :>> judgedBy = "claudeOpus5"; }

    verification bdStandupGate : Test { :>> id = "0d800325-0814-6325-9b3e-000000300325"; :>> title = "Sprint 311 standup gate"; :>> createdAt = "2026-08-15"; :>> createdBy = "claudeOpus5"; :>> method = VerificationMethod::inspect; :>> procedureText = "Approach: read the history behind each burndown number before acting on it, because a number that has sat at the same value for many sprints usually has a recorded reason. No blockers."; }
    part bdStandupGateR1 : TestResult { :>> id = "0d800326-0814-6326-9b3e-000000300326"; :>> outcome = VerdictKind::pass; :>> judgedAgainst = "f9d2495"; :>> judgedAt = "2026-08-15"; :>> judgedBy = "claudeOpus5"; }

    verification bdImplementGate : Test { :>> id = "0d800327-0814-6327-9b3e-000000300327"; :>> title = "Sprint 311 implement gate"; :>> createdAt = "2026-08-15"; :>> createdBy = "claudeOpus5"; :>> method = VerificationMethod::test; :>> procedureText = "READING THE HISTORY IS WHAT MADE THIS SPRINT CORRECT RATHER THAN HARMFUL. The orphan story looked like a one-line fix; two prior sprints had already considered and REFUSED it, and sprint 171's file carries the reason inline. Sprint 294 had gone further and warned in writing that excluding superseded Needs from the gap set was necessary partly to stop a future contributor 'fixing' a gap by authoring requirements for work that was explicitly cut — which is exactly the move I would have made on N-8 had D0115 not kept it. N-8 SURVIVED that check and five of its siblings did not, so decomposing it is right and decomposing them would have been fabrication. A SEPARATE DEFECT FOUND BY HITTING IT (issue133): `keel reverify --judged-by claudeOpus5` failed with 'no acting actor', because the parser accepted only `--by` and its catch-all arm turned the unknown flag into a ROOT path — so the binding was sought in a directory named claudeOpus5. The actor error message itself advertises `--judged-by`. Fixed both halves: all three spellings accepted, and an unrecognised --flag now errors with the usage line instead of silently becoming a path. The same catch-all-as-root arm exists in other subcommand parsers, so the class is probably wider; that is recorded rather than swept blind."; }
    part bdImplementGateR1 : TestResult { :>> id = "0d800328-0814-6328-9b3e-000000300328"; :>> outcome = VerdictKind::pass; :>> judgedAgainst = "f9d2495"; :>> judgedAt = "2026-08-15"; :>> judgedBy = "claudeOpus5"; }

    verification bdReviewGate : Test { :>> id = "0d800329-0814-6329-9b3e-000000300329"; :>> title = "Sprint 311 review gate"; :>> createdAt = "2026-08-15"; :>> createdBy = "claudeOpus5"; :>> method = VerificationMethod::inspect; :>> procedureText = "Reviewed. srViewerPersistedViewState decomposes only the half of N-8 that D0115 left standing, and issue132 records the residual: N-8's statement still asserts 'shareable across users' and 'per-user view state', scope D0115 removed. The Need is owned by wweatherholtz and D0108 forbids a non-owner editing its fields, so the conflict is RECORDED rather than silently resolved by writing a requirement that contradicts the Need it decomposes. Sharing by ARTIFACT rather than by account is the design choice worth defending: a saved viewpoint in a database would be state the model cannot see, which is the dual truth §2.1 forbids, and an artifact in git is reviewable and diffable like every other authored fact."; }
    part bdReviewGateR1 : TestResult { :>> id = "0d80032a-0814-632a-9b3e-00000030032a"; :>> outcome = VerdictKind::pass; :>> judgedAgainst = "f9d2495"; :>> judgedAt = "2026-08-15"; :>> judgedBy = "claudeOpus5"; }

    verification bdCloseOutGate : Test { :>> id = "0d80032b-0814-632b-9b3e-00000030032b"; :>> title = "Sprint 311 closeOut gate (autonomous, D0049)"; :>> createdAt = "2026-08-15"; :>> createdBy = "claudeOpus5"; :>> method = VerificationMethod::inspect; :>> procedureText = "Autonomous closeOut (D0049). suspect [] ; need_decomposed_pct 100%; orphan_stories deliberately still 1. sr_verified_pct moved 84% -> 83% because a NEW requirement now exists that nothing verifies — the honest direction, and the human is reviewing the verification gap separately. clippy clean; 221 tests; validate 336 clean; check-engine clean; 33 guards green."; }
    part bdCloseOutGateR1 : TestResult { :>> id = "0d80032c-0814-632c-9b3e-00000030032c"; :>> outcome = VerdictKind::pass; :>> judgedAgainst = "f9d2495"; :>> judgedAt = "2026-08-15"; :>> judgedBy = "claudeOpus5"; }

    verification bdRetroGate : Test { :>> id = "0d80032d-0814-632d-9b3e-00000030032d"; :>> title = "Sprint 311 retro gate (autonomous, D0049)"; :>> createdAt = "2026-08-15"; :>> createdBy = "claudeOpus5"; :>> method = VerificationMethod::analyze; :>> procedureText = "Autonomous retro (D0049) under D0131's retroTrack. WELL: (1) 'proceed with all' was read as authorisation to clear the burndown truthfully, not to make numbers green, and the difference decided the sprint — one of the three items had to be refused and the refusal is recorded where the next reader will find it; (2) the history behind each stale number was read first, and it contained the answer in two of three cases, written by contributors who had already faced the same temptation; (3) the flag defect was FIXED at the point it bit rather than filed, and the wider class was named honestly instead of being swept blind. AVOIDABLE-ISSUE: I listed the orphan story to the human as outstanding work without first reading why it was outstanding, so the offer to fix it was made before the check that would have shown it must not be fixed. NO NEW ITEM: the remedy is the verify-before-asserting discipline already tracked several times today, and this instance is recorded here — but it is worth naming that the failure mode has now shifted from 'wrong facts in the model' to 'unverified claims in my summaries to the human', which the gates do not cover. Estimate 3 pts, delivered."; }
    part bdRetroGateR1 : TestResult { :>> id = "0d80032e-0814-632e-9b3e-00000030032e"; :>> outcome = VerdictKind::pass; :>> judgedAgainst = "f9d2495"; :>> judgedAt = "2026-08-15"; :>> judgedBy = "claudeOpus5"; }
}
