// ProjectDeliveryS316 — Sprint 316: obligations on arrival, and every view carries an explicit
// status. EXECUTE. 8 pts.
package ProjectDeliveryS316 {
    private import EngineElement::*;
    private import EngineWork::*;
    private import EngineVerification::*;
    private import EngineRelationships::*;

    #CharteredBy dependency from obligationsStory to d0152;

    part obligationsStory : Story {
        :>> id = "0d800370-0814-6370-9b3e-000000300370";
        :>> title = "Sprint 316: obligations on arrival + explicit view status (8 pts)";
        :>> createdAt = "2026-08-17"; :>> createdBy = "claudeOpus5"; :>> kind = WorkKind::code; :>> priority = WorkPriority::p0; :>> owner = "claudeOpus5"; :>> estimatedPoints = 8;
    }

    action def DeliveryRunS316 {
        action storyObligations;
        verification storyObligationsDoD : Test { :>> id = "0d800371-0814-6371-9b3e-000000300371"; :>> method = VerificationMethod::demo; :>> procedureText = "Builds srConsoleObligationsOnArrival (N-C1) and srConsoleViewStatusExplicit (N-C2). DELIVERED (1): `/api/obligations`, whose obligation CLASSES are derived from the viewpoints declaring surface=\"act\" rather than enumerated in code — declaring a viewpoint adds a class with no console change, which is what makes N-C1's 'without having been told a new class exists' achievable rather than aspirational. Each class's count is read from the view its own `renderer` names, so the existing computed view stays the authority and nothing is re-implemented. A class with no bound counter reports NOT COUNTABLE with the command named, never zero. The console renders the bar on ARRIVAL above whichever surface is active, so no navigation is required. VERIFIED LIVE: 4 classes derived, 0 uncountable, counts acceptances-pending 0 / authority-queue 4 / findings-awaiting-disposition 3 / sitting-review-due 311. DELIVERED (2): every cached response now passes through `with_status`, stamping viewStatus=computed|stale|failed — a CHOKE POINT, because the requirement says no render path may emit content without a status and only a single funnel can mean it. On a compute failure with a prior good value the response is STALE with its reason rather than an error page; with no prior value it is FAILED with the reason. The console reads the status and draws each distinctly. clippy clean; 224 tests; validate 343 clean; 33 guards green."; }
        part storyObligationsDoDR1 : TestResult { :>> id = "0d800372-0814-6372-9b3e-000000300372"; :>> outcome = VerdictKind::pass; :>> judgedAgainst = "faa366e"; :>> judgedAt = "2026-08-17"; :>> judgedBy = "claudeOpus5"; }
    }

    verification obRefineGate : Test { :>> id = "0d800373-0814-6373-9b3e-000000300373"; :>> title = "Sprint 316 refine gate (DoR)"; :>> createdAt = "2026-08-17"; :>> createdBy = "claudeOpus5"; :>> method = VerificationMethod::inspect; :>> procedureText = "DoR. These two were taken together because they are the same property from two sides: N-C1 asks that what is owed be discoverable, and N-C2 asks that a quiet surface be trustworthy — an obligation bar reading zero is worthless if zero and 'failed to compute' look alike. Building the bar without the status would have shipped the more dangerous half. srConsoleNavigationDerived (sprint 315) is their declared #DependsOn predecessor and was already in place. estimatedPoints=8."; }
    part obRefineGateR1 : TestResult { :>> id = "0d800374-0814-6374-9b3e-000000300374"; :>> outcome = VerdictKind::pass; :>> judgedAgainst = "faa366e"; :>> judgedAt = "2026-08-17"; :>> judgedBy = "claudeOpus5"; }

    verification obStandupGate : Test { :>> id = "0d800375-0814-6375-9b3e-000000300375"; :>> title = "Sprint 316 standup gate"; :>> createdAt = "2026-08-17"; :>> createdBy = "claudeOpus5"; :>> method = VerificationMethod::inspect; :>> procedureText = "Approach: put the status stamp at the ONE place every response already passes through, so it cannot be forgotten by a later endpoint; derive obligation classes from the act viewpoints; read each count from the existing computed view rather than re-deriving it. No blockers."; }
    part obStandupGateR1 : TestResult { :>> id = "0d800376-0814-6376-9b3e-000000300376"; :>> outcome = VerdictKind::pass; :>> judgedAgainst = "faa366e"; :>> judgedAt = "2026-08-17"; :>> judgedBy = "claudeOpus5"; }

    verification obImplementGate : Test { :>> id = "0d800377-0814-6377-9b3e-000000300377"; :>> title = "Sprint 316 implement gate"; :>> createdAt = "2026-08-17"; :>> createdBy = "claudeOpus5"; :>> method = VerificationMethod::test; :>> procedureText = "THE STALE PATH IS UNIT-TESTED AND NOT VERIFIED END TO END, stated because the reason is itself a finding. I tried to force a real compute failure by writing an unparseable file into `.tracking/`, twice, and the views kept reporting COMPUTED — because `Model::build` SUCCEEDS on a corrupt corpus: the parser silently skips what it cannot read, which is issue102, an open Critical. So file corruption cannot reach the failure path at all, and the stale/failed branches are exercised only by unit tests over `with_status` (three tests, including the load-bearing one that a COMPUTED-EMPTY body must not be interchangeable with a FAILED one). That is honest coverage of the mechanism and NOT a demonstration of the end-to-end behaviour, and the gap exists because of a defect elsewhere rather than because the branch is untestable in principle. A SECOND FINDING, recorded as issue135 rather than engineered around: sitting-review-due reports 311 of 315 sprints, because per-sitting review post-dates almost all of this repo's history and nothing distinguishes a sitting AWAITING review from one predating the convention. The number is correct and useless as a queue — N-C1 says the surface shows obligations requiring judgment AND NOTHING ELSE, and three real obligations are lost beside 311 that nobody will clear. It is reported WITH an explicit caveat rather than filtered, because choosing a cutoff silently would invent an actionable definition nobody agreed."; }
    part obImplementGateR1 : TestResult { :>> id = "0d800378-0814-6378-9b3e-000000300378"; :>> outcome = VerdictKind::pass; :>> judgedAgainst = "faa366e"; :>> judgedAt = "2026-08-17"; :>> judgedBy = "claudeOpus5"; }

    verification obReviewGate : Test { :>> id = "0d800379-0814-6379-9b3e-000000300379"; :>> title = "Sprint 316 review gate"; :>> createdAt = "2026-08-17"; :>> createdBy = "claudeOpus5"; :>> method = VerificationMethod::inspect; :>> procedureText = "Reviewed. THE EMPTY STATE CARRIES THE MOST WEIGHT and is written deliberately: with nothing owed the bar says 'Nothing is waiting on you. All 4 declared obligation classes computed and are empty' — it asserts that the classes COMPUTED, which is the only form of empty a reader can trust. A bar that simply showed nothing would be indistinguishable from a bar that failed, and that is the whole of N-C2. The NOT COUNTABLE state exists for the same reason: a class the console cannot count shows '?' with the unbound command named, never 0. The obligation fetch has its own failure path too — if /api/obligations itself fails the bar says so explicitly rather than rendering as 'nothing owed', which would have been the worst possible default for this particular surface."; }
    part obReviewGateR1 : TestResult { :>> id = "0d80037a-0814-637a-9b3e-00000030037a"; :>> outcome = VerdictKind::pass; :>> judgedAgainst = "faa366e"; :>> judgedAt = "2026-08-17"; :>> judgedBy = "claudeOpus5"; }

    verification obCloseOutGate : Test { :>> id = "0d80037b-0814-637b-9b3e-00000030037b"; :>> title = "Sprint 316 closeOut gate (autonomous, D0049)"; :>> createdAt = "2026-08-17"; :>> createdBy = "claudeOpus5"; :>> method = VerificationMethod::inspect; :>> procedureText = "Autonomous closeOut (D0049). Four of six console requirements now built; srConsoleModelScopeResolved and srConsoleProjectRebind remain. issue135 records the sitting-review scope question for the human. clippy clean; 224 tests; validate 343 clean; check-engine clean; 33 guards green. Serve processes stopped; the rebuild was confirmed by grepping the SERVED console for the new functions before trusting any result."; }
    part obCloseOutGateR1 : TestResult { :>> id = "0d80037c-0814-637c-9b3e-00000030037c"; :>> outcome = VerdictKind::pass; :>> judgedAgainst = "faa366e"; :>> judgedAt = "2026-08-17"; :>> judgedBy = "claudeOpus5"; }

    verification obRetroGate : Test { :>> id = "0d80037d-0814-637d-9b3e-00000030037d"; :>> title = "Sprint 316 retro gate (autonomous, D0049)"; :>> createdAt = "2026-08-17"; :>> createdBy = "claudeOpus5"; :>> method = VerificationMethod::analyze; :>> procedureText = "Autonomous retro (D0049) under D0131's retroTrack. WELL: (1) the rebuild was confirmed against the SERVED artifact before any result was trusted, which is last sprint's lesson applied rather than merely recorded; (2) the status stamp went at the single choke point rather than per-endpoint, so a future endpoint cannot forget it; (3) two attempts to force a failure both came back COMPUTED, and rather than declaring the branch verified I chased WHY and found issue102 — the parser's silent skip — then said plainly that the end-to-end path is unverified and only the mechanism is tested. AVOIDABLE-ISSUE: I corrupted serve.rs with an index-based python splice that landed inside the module header, producing 'expected outer doc comment' at line 53. Reverted with git checkout and redone with exact-match edits. Third time this session that a computed-offset string surgery has damaged a source file, and the remedy has been recorded twice already: use exact anchors, or the Edit tool. NO NEW ITEM — the remedy is known and the failure is loud and instantly recoverable via git; what is worth carrying is that 'loud and recoverable' is why this keeps not getting fixed. Estimate 8 pts, delivered."; }
    part obRetroGateR1 : TestResult { :>> id = "0d80037e-0814-637e-9b3e-00000030037e"; :>> outcome = VerdictKind::pass; :>> judgedAgainst = "faa366e"; :>> judgedAt = "2026-08-17"; :>> judgedBy = "claudeOpus5"; }
}
