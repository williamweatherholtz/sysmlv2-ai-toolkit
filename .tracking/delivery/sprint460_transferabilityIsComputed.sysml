// ProjectDeliveryS460 — Sprint 460: transferability becomes a computation, and the answer was 23-of-24 NO until 36 skill declarations moved beside their skills (issue253, D0222). EXECUTE. 3 pts.
package ProjectDeliveryS460 {
    private import EngineElement::*;
    private import EngineWork::*;
    private import EngineVerification::*;
    private import EngineRelationships::*;

    #CharteredBy dependency from transferabilityIsComputedStory to d0222;

    part transferabilityIsComputedStory : Story {
        :>> id = "800140d4-9caa-41da-9c46-8b822d2db428";
        :>> title = "Sprint 460: the final pass before migrating, and it said no (3 pts)";
        :>> createdAt = "2026-08-24"; :>> createdBy = "claudeFable5"; :>> kind = WorkKind::code; :>> priority = WorkPriority::p0; :>> owner = "claudeFable5"; :>> estimatedPoints = 3;
    }

    action def DeliveryRunS460 {
        action storyTransferabilityIsComputed;
        verification storyTransferabilityIsComputedDoD : Test { :>> id = "fd620339-ba26-4c2c-bdcb-d7e67cc16c27"; :>> method = VerificationMethod::test; :>> procedureText = "DELIVERED: dcTransferabilityIsComputed (resolves issue253, HIGH, discoveredInField). The human, before migrating to penumbra: 'fix keel, then we will migrate. not wanting to put the cart before the horse. i want a good transition. do a final pass to check if everything is easily transferrable.' Twice in the preceding hours a unit had been DECLARED transferable and was not - the channel left its mechanism behind (issue251), then left behind the declaration binding skill to process (issue252) - and BOTH were found by actually adopting, never by reading the export. So the answer could not be my reading of the tree; it had to be a computation. THE COMPUTATION SAID NO FOR 23 OF 24 UNITS: each carried its process definition and its SKILL.md while the entry BINDING them stayed in the single shared skills-registry, which cannot travel with one unit, so every adoption into a project lacking that process would have failed process-skill on arrival. WHAT WAS BUILT: `keel process audit` reports per unit whether it would land GREEN in a project that lacks it, naming the reason when it would not - checking that a deploying skill exists, that the binding declaration travels, that declared extras are present on disk, and that no carried file cites a path the adopter will not have. A committed migration transform then MOVED all 36 AISkill declarations out of the shared registry into `.engine/skills/<skill>/registry.sysml`, reconciled 36 found = 36 moved = 0 skipped and verbatim so ids and provenance are unchanged - duplicate-identity refusing a copy is what proves it was a move. `import` now RETIRES a central declaration that an incoming per-skill file supersedes, announced on stdout, because otherwise a project on an older engine - penumbra exactly - ends up with the same id in two files and duplicate-identity fails on arrival. And the dead references were swept, including a process still naming the Smartsheet tap-inbox tooling D0206 RETIRED. VERIFIED BY ADOPTION rather than by re-reading: the audit went 23 LANDS-RED to 0, and intake, migration, obligation-review and agile-workflow were each exported and imported into a fresh project that lacked them, each leaving that project at [guard] ALL PASS; penumbra's exact case was simulated and the import announced 'retired the superseded central skills-registry declaration for intakeSkill' with duplicate-identity clean afterwards. 260 tests; all gates green."; }
        part storyTransferabilityIsComputedDoDR1 : TestResult { :>> id = "cbcd3b39-4c45-4251-9af9-9ef8ebbbab47"; :>> outcome = VerdictKind::pass; :>> judgedAgainst = "43a7b10f0a9662043e4099dccbb746a280d1d850"; :>> judgedAt = "2026-08-24"; :>> judgedBy = "claudeFable5"; }
    }

    verification transferabilityIsComputedRefineGate : Test { :>> id = "506c2a55-722b-47e0-9c6e-0d902473daa4"; :>> title = "Sprint 460 refine gate (DoR)"; :>> createdAt = "2026-08-24"; :>> createdBy = "claudeFable5"; :>> method = VerificationMethod::inspect; :>> procedureText = "DoR. Resolves issue253, raised by the human as an explicit precondition on the penumbra migration: fix keel first, and check transferability before moving. Scope: make transferability computed, then fix whatever it reports. 3 points."; }
    part transferabilityIsComputedRefineGateR1 : TestResult { :>> id = "61aa5328-cf51-4db7-b4d2-5ec2065d7c65"; :>> outcome = VerdictKind::pass; :>> judgedAgainst = "43a7b10f0a9662043e4099dccbb746a280d1d850"; :>> judgedAt = "2026-08-24"; :>> judgedBy = "claudeFable5"; }
    verification transferabilityIsComputedStandupGate : Test { :>> id = "afa895c3-b7c4-46f3-96d3-5fd8df0129ff"; :>> title = "Sprint 460 standup gate"; :>> createdAt = "2026-08-24"; :>> createdBy = "claudeFable5"; :>> method = VerificationMethod::inspect; :>> procedureText = "Approach: do NOT answer by reading the tree - I had done that twice and been wrong twice. Compute it, then act on the number. Migrate in bulk under D0067 discipline: a committed transform, a dry run reconciling control totals, verbatim moves so ids survive, green at every step. Expect the audit itself to need narrowing, because a portability check reads prose. guards.rs and the process definitions are keystone-locked, so D0222 co-commits. No blockers."; }
    part transferabilityIsComputedStandupGateR1 : TestResult { :>> id = "58e63316-8ca2-4cd1-be8c-4d4c3e27a683"; :>> outcome = VerdictKind::pass; :>> judgedAgainst = "43a7b10f0a9662043e4099dccbb746a280d1d850"; :>> judgedAt = "2026-08-24"; :>> judgedBy = "claudeFable5"; }
    verification transferabilityIsComputedImplementGate : Test { :>> id = "24c62c57-7aad-48a5-a51e-53c6de22c4ca"; :>> title = "Sprint 460 implement gate"; :>> createdAt = "2026-08-24"; :>> createdBy = "claudeFable5"; :>> method = VerificationMethod::test; :>> procedureText = "Verified by running the audit and then by ADOPTING: audit 23 LANDS-RED of 24 -> 0; dry run reconciled 36 = 36 + 0 before anything was written; four separate units each imported into a fresh project lacking them and left it at guard ALL PASS; the pre-migration-engine collision was simulated and import retired the superseded declaration with duplicate-identity clean. cargo test --lib -> 260 passed; clippy --workspace --all-targets clean; validate 511 + all 49 guards + check-engine + rules green."; }
    part transferabilityIsComputedImplementGateR1 : TestResult { :>> id = "f64f6f5c-7b93-46d8-b798-3633d9f7075b"; :>> outcome = VerdictKind::pass; :>> judgedAgainst = "43a7b10f0a9662043e4099dccbb746a280d1d850"; :>> judgedAt = "2026-08-24"; :>> judgedBy = "claudeFable5"; }
    verification transferabilityIsComputedReviewGate : Test { :>> id = "e90b6cd5-61d1-492d-96c2-76df33d197bc"; :>> title = "Sprint 460 review gate — three passes per D0172"; :>> createdAt = "2026-08-24"; :>> createdBy = "claudeFable5"; :>> method = VerificationMethod::inspect; :>> procedureText = "PASS 1, CLAIMS: the audit counts, the four adoption results and the retirement message are quoted read-backs; the 23-of-24 figure is the tool's own output, not an estimate. PASS 2, BOUNDARY: (i) the audit is a REPORT and not a gate, because a project may legitimately hold units it never exports - so nothing stops the number regressing, and the honest counter is that the number is now cheap to re-run; (ii) it cannot check anything that depends on the TARGET (a duplicate id there, a missing prerequisite) - those are import-time concerns and import now handles the duplicate one; (iii) the audit was NARROWED TWICE against the real corpus after over-flagging a directory convention and a placeholder, so it is deliberately conservative and will miss an exotic dead reference. PASS 3, OWN DIFF: three findings against myself, all after recording the Decision. The central registry had FOUR readers; I fixed one before migrating and found the other three as each broke, which is the same-rule-in-N-places class and the systematic grep should have come FIRST. One of those breakages made claude-surface-drift pass vacuously on a population of zero - a FALSE GREEN, worse than the failure it hid. And is_engine_instance_file did not recognise the new files, so check-engine reported clean over 36 files it never read; fixing that immediately caught a real defect in the ONE file I had hand-written rather than generated. I completed D0222's consequences with all of it rather than leaving the record flattering. WHAT A REVIEWER SHOULD ATTACK: whether moving 36 declarations out of one browsable file costs more in discoverability than it buys in portability - the counter is that `keel process list|show|audit` are the discovery surfaces now, and a 37-entry file was never one."; }
    part transferabilityIsComputedReviewGateR1 : TestResult { :>> id = "ea115fa6-f6bf-438e-b25c-086ad0fc1a4d"; :>> outcome = VerdictKind::pass; :>> judgedAgainst = "43a7b10f0a9662043e4099dccbb746a280d1d850"; :>> judgedAt = "2026-08-24"; :>> judgedBy = "claudeFable5"; }
    verification transferabilityIsComputedCloseOutGate : Test { :>> id = "e5a3a055-c5e6-40d1-9f91-a256bffbc60e"; :>> title = "Sprint 460 closeOut gate (autonomous, D0049)"; :>> createdAt = "2026-08-24"; :>> createdBy = "claudeFable5"; :>> method = VerificationMethod::inspect; :>> procedureText = "Autonomous closeOut (D0049). issue253 resolved: transferability is computed, every unit travels whole, and four adoptions prove it rather than assert it. keel is ready for the penumbra migration, which is deliberately NOT bundled here - the human asked for the horse before the cart. validate + all 49 guards + check-engine + rules green."; }
    part transferabilityIsComputedCloseOutGateR1 : TestResult { :>> id = "9dd7f48c-1e11-409b-b194-14d13995f7f6"; :>> outcome = VerdictKind::pass; :>> judgedAgainst = "43a7b10f0a9662043e4099dccbb746a280d1d850"; :>> judgedAt = "2026-08-24"; :>> judgedBy = "claudeFable5"; }
    verification transferabilityIsComputedRetroGate : Test { :>> id = "2f4b8089-4be5-48ad-b2a6-85d58817b462"; :>> title = "Sprint 460 retro gate (autonomous, D0049)"; :>> createdAt = "2026-08-24"; :>> createdBy = "claudeFable5"; :>> method = VerificationMethod::analyze; :>> procedureText = "Autonomous retro (D0049). AVOIDABLE-ISSUE SCAN under rcRecurrence: (1) THE recurrence, and it cost the most: a shared fact had FOUR readers and I found them one at a time as each broke. Grepping for every reader BEFORE a migration is a five-second act I skipped, and the D0067 migration process should say so - a bulk move must enumerate its readers as part of the dry run, not discover them in the aftermath. (2) A false green appeared en route: a reader returning zero made its guard pass on an empty population, which is the same shape as the audit-adherence false clean (issue250) and argues for a general rule - a check over a population must assert the population is non-empty. (3) The heredoc-escaping class recurred a seventh time. WELL: the human's instinct to check before migrating was right and the number proved it - 23 of 24 units would have landed red, and no amount of my reading would have produced that figure. Estimate 3 pts, delivered 3."; }
    part transferabilityIsComputedRetroGateR1 : TestResult { :>> id = "fd301772-019d-49ab-81c0-8aa80a2d07dd"; :>> outcome = VerdictKind::pass; :>> judgedAgainst = "43a7b10f0a9662043e4099dccbb746a280d1d850"; :>> judgedAt = "2026-08-24"; :>> judgedBy = "claudeFable5"; }
}
