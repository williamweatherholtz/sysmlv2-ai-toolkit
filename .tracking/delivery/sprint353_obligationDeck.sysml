// ProjectDeliveryS353 — Sprint 353: their queue leaves the terminal. A skill that renders outstanding
// items as a static HTML deck they can operate on a phone and hand back. CHANGE (§3a). 5 pts.
package ProjectDeliveryS353 {
    private import EngineElement::*;
    private import EngineWork::*;
    private import EngineVerification::*;
    private import EngineRelationships::*;

    #CharteredBy dependency from obligationDeckStory to d0093;

    part obligationDeckStory : Story {
        :>> id = "0d8005c0-0814-65c0-9b3e-0000003005c0";
        :>> title = "Sprint 353: the obligation-review skill — outstanding items as a static HTML deck for mobile (5 pts)";
        :>> createdAt = "2026-08-20"; :>> createdBy = "claudeOpus5"; :>> kind = WorkKind::code; :>> priority = WorkPriority::p0; :>> owner = "claudeOpus5"; :>> estimatedPoints = 5;
    }

    action def DeliveryRunS353 {
        action storyObligationDeck;
        verification storyObligationDeckDoD : Test { :>> id = "0d8005c1-0814-65c1-9b3e-0000003005c1"; :>> method = VerificationMethod::demo; :>> procedureText = "THE HUMAN ASKED FOR A SKILL, NOT A PAGE: 'make a skill so I can look at and give feedback on outstanding items but with a static html so I can use as an artifact on mobile.' So the deliverable is the SKILL (D0040 - a recurring task with no skill becomes the skill first) plus one run of it. `obligation-review` deploys `.engine/tools/obligation_canvas.py`, which shells out to the `keel` binary for orient/authority-queue/dispositions/sitting-coverage - the authority, so the deck cannot disagree with `keel orient`, and no server is needed. THAT IS THE WHOLE POINT: `keel serve` requires a shell, a running server and a localhost browser, and their obligations do not wait for those conditions - 86 items were outstanding when this was written. Four classes, one hue each: 4 Decisions awaiting acceptance, 27 authority queue, 22 findings awaiting disposition, 33 sitting reviews due. Per item: accept / needs work / reject plus a note, stored in localStorage keyed by each item's MINTED UUID rather than its display label, with a content signature so an item edited after being judged re-surfaces with a `changed` badge instead of keeping a stale verdict. `Copy for Claude` emits markdown for paste-back. validate 381 clean; check-engine clean; 36 guards ALL PASS; process-skill PASS at 18."; }
        part storyObligationDeckDoDR1 : TestResult { :>> id = "0d8005c2-0814-65c2-9b3e-0000003005c2"; :>> outcome = VerdictKind::fail; :>> judgedAgainst = "PENDING"; :>> judgedAt = "2026-08-20"; :>> judgedBy = "claudeOpus5"; }
    }

    verification odRefineGate : Test { :>> id = "0d8005c3-0814-65c3-9b3e-0000003005c3"; :>> title = "Sprint 353 refine gate (DoR)"; :>> createdAt = "2026-08-20"; :>> createdBy = "claudeOpus5"; :>> method = VerificationMethod::inspect; :>> procedureText = "DoR. Routed as CHANGE rather than EXECUTE because they said SKILL: a one-off page would have satisfied the sentence and left the next regeneration to conversation history, which is exactly what D0040 forbids. Two harness skills applied and were loaded rather than improvised around - brainstorm-canvas for the review-board pattern and its anti-pattern list, artifact-design for the visual pass. estimatedPoints=5."; }
    part odRefineGateR1 : TestResult { :>> id = "0d8005c4-0814-65c4-9b3e-0000003005c4"; :>> outcome = VerdictKind::pass; :>> judgedAgainst = "dafc7f5"; :>> judgedAt = "2026-08-20"; :>> judgedBy = "claudeOpus5"; }

    verification odStandupGate : Test { :>> id = "0d8005c5-0814-65c5-9b3e-0000003005c5"; :>> title = "Sprint 353 standup gate"; :>> createdAt = "2026-08-20"; :>> createdBy = "claudeOpus5"; :>> method = VerificationMethod::inspect; :>> procedureText = "Approach: read the computed views THROUGH THE BINARY rather than parsing the model in the generator, so the deck has no second opinion about what is outstanding - the same reasoning that put `obligation_count` and the console's obligation bar on one dispatch table (issue146). localStorage plus an export, NOT the live-doc artifact capability: sync regions need a write grant that may not be active, and the failure mode is the reader being told the page is read-only. Static HTML plus paste-back is always writable and needs no grant. No blockers."; }
    part odStandupGateR1 : TestResult { :>> id = "0d8005c6-0814-65c6-9b3e-0000003005c6"; :>> outcome = VerdictKind::pass; :>> judgedAgainst = "dafc7f5"; :>> judgedAt = "2026-08-20"; :>> judgedBy = "claudeOpus5"; }

    verification odImplementGate : Test { :>> id = "0d8005c7-0814-65c7-9b3e-0000003005c7"; :>> title = "Sprint 353 implement gate"; :>> createdAt = "2026-08-20"; :>> createdBy = "claudeOpus5"; :>> method = VerificationMethod::test; :>> procedureText = "TWO DEFECTS FOUND BY CHECKING THE OUTPUT RATHER THAN THE CODE, which is this session's recurring lesson applied on purpose this time. (1) EVERY EM-DASH IN A DECISION TITLE WAS A REPLACEMENT CHARACTER: the artifact runtime supplies the `<head>`, so the file cannot declare a charset and the host's guess decides. Fixed by making `esc` numeric-entity-encode everything above 127, verified by counting bytes > 127 in the output: zero. Hoping the host declares UTF-8 is not a plan. (2) ONE ITEM CARRIED A SYNTHETIC UID, which would have orphaned its saved verdict on the next regeneration - investigated rather than waved off, and it is an AGGREGATE authority row whose `item` is the sentence `306 sprint(s) awaiting a sitting review`, not an item name. Synthetic is the correct answer there, and the skill's checklist now states that a synthetic uid is legitimate ONLY for aggregate rows. STATE IS KEYED BY MINTED UUID, NEVER BY LABEL, because the deck is regenerated from a moving model: label-keyed judgments orphan exactly when the human has invested the most in them, and keel items already carry UUIDs so the stable key was free. A content signature is stored WITH each verdict so an item edited afterwards re-surfaces flagged rather than silently retaining approval. Design: token CSS in all three theme states (bare :root, prefers-color-scheme guarded against an explicit light choice, and the [data-theme] stamp), 44px tap targets, one categorical hue per class kept separate from the semantic verdict colors, mono for every id because the ids ARE the data."; }
    part odImplementGateR1 : TestResult { :>> id = "0d8005c8-0814-65c8-9b3e-0000003005c8"; :>> outcome = VerdictKind::pass; :>> judgedAgainst = "dafc7f5"; :>> judgedAt = "2026-08-20"; :>> judgedBy = "claudeOpus5"; }

    verification odReviewGate : Test { :>> id = "0d8005c9-0814-65c9-9b3e-0000003005c9"; :>> title = "Sprint 353 review gate"; :>> createdAt = "2026-08-20"; :>> createdBy = "claudeOpus5"; :>> method = VerificationMethod::inspect; :>> procedureText = "Reviewed. THE SKILL'S GUARDRAILS ARE THE PART I WOULD DEFEND HARDEST, because the obvious next step is the wrong one: a deck that collects verdicts invites recording them, and a tap in a browser I never received is not an attestation. So the skill states plainly that the deck RECORDS NOTHING, that only their pasted-back export becomes a fact, that their note is the attestation text quoted VERBATIM, and that a verdict with no note records the verdict and nothing more - no invented rationale. §4 has been the hardest rule to hold this session (issue144 was me fabricating an attestation mechanically), and a new collection surface is exactly where it would break next. IT ALSO STATES WHAT THE DECK CANNOT DO: it cannot record, it cannot show an item the computed views omit, and its verdicts live in one browser's localStorage so a second device starts empty. That last one is a real limitation for someone moving between a phone and a desktop, and it is written down rather than discovered. WHAT I DID NOT BUILD: a way to push verdicts back automatically. It would need a network write path from an artifact to this machine, which D0158 makes local-only by decision, and paste-back keeps the human's word passing through the human."; }
    part odReviewGateR1 : TestResult { :>> id = "0d8005ca-0814-65ca-9b3e-0000003005ca"; :>> outcome = VerdictKind::pass; :>> judgedAgainst = "dafc7f5"; :>> judgedAt = "2026-08-20"; :>> judgedBy = "claudeOpus5"; }

    verification odCloseOutGate : Test { :>> id = "0d8005cb-0814-65cb-9b3e-0000003005cb"; :>> title = "Sprint 353 closeOut gate (autonomous, D0049)"; :>> createdAt = "2026-08-20"; :>> createdBy = "claudeOpus5"; :>> method = VerificationMethod::inspect; :>> procedureText = "Autonomous closeOut (D0049). The skill is registered in `.engine/skills/skills-registry.sysml` and `process-skill` PASSES at 18 - it is a skill without a process, which that guard permits (it requires every process to HAVE a skill, not the reverse). The generator lives at `.engine/tools/obligation_canvas.py`; the deck is published and the URL handed over. Its own removal path is stated in the SKILL file per D0163's proposed rule, even though D0163 is not yet accepted - delete the tool and the skill directory, drop the registry entry, and nothing else depends on either. RESULT RECORDED FAIL, method=demo: whether it is usable on their phone is theirs to judge, and the skill records nothing until they paste an export back. pendingAcceptances d0161, d0162, d0163, d0164. validate 381 clean; check-engine clean; 36 guards ALL PASS."; }
    part odCloseOutGateR1 : TestResult { :>> id = "0d8005cc-0814-65cc-9b3e-0000003005cc"; :>> outcome = VerdictKind::pass; :>> judgedAgainst = "dafc7f5"; :>> judgedAt = "2026-08-20"; :>> judgedBy = "claudeOpus5"; }

    verification odRetroGate : Test { :>> id = "0d8005cd-0814-65cd-9b3e-0000003005cd"; :>> title = "Sprint 353 retro gate (autonomous, D0049)"; :>> createdAt = "2026-08-20"; :>> createdBy = "claudeOpus5"; :>> method = VerificationMethod::analyze; :>> procedureText = "Autonomous retro (D0049) under D0131's retroTrack. WELL, AND IT IS A DELIBERATE CHANGE OF HABIT: I checked the OUTPUT before publishing rather than the source, and it found two defects in one pass - the charset problem that turned every em-dash into a replacement character, and a synthetic uid that would have orphaned a saved verdict. Five separate times this session the report agreed and only the effect settled it (the fingerprint instrument, the request log, the guard failing on a reintroduced defect, /api/surfaces after a deactivate, and now byte-counting the artifact). This is the first time I did it BEFORE being told something was broken. AVOIDABLE-ISSUE: I wrote the generator into a bash heredoc first and it died on the embedded quotes, which sprint 324 already recorded a remedy for - use the Write tool for anything containing quotes or apostrophes. I had the remedy and did not reach for it until the failure. That is the second time a recorded remedy went unread this session (the first was sprint 343's own note about the read-only panel), and it is the same failure the `keel why` half of D0161 is meant to address: a record nobody consults is a record that cost more than it returned. ALSO WELL: (1) routed as CHANGE because they said `skill`, so the next run is one command rather than a reconstruction from conversation; (2) the harness skills were LOADED rather than approximated, and brainstorm-caanvas's anti-pattern list is where the UUID-keying and change-detection requirements came from - not my own invention; (3) the skill's guardrails say what it must not do, since a surface that collects judgments is precisely where §4 would break next; (4) localStorage plus paste-back rather than live-doc sync, so there is no write grant to fail silently. THEN THEY USED IT AND FOUND TWO MORE (issue157), one of which they did not report and their paste proved. THE COPY BUTTON: `navigator.clipboard.writeText` rejects inside a sandboxed artifact frame without clipboard-write permission, and I wrote `.then()` with NO rejection handler - so it failed silently, the fallback never ran, and the button did not even change its label. They copied the text by hand. That is the sixth instance this session of a control that appears to do nothing, and this time I wrote it myself minutes after recording the pattern in sprint 351. THE DUPLICATION: their export carried 8 ACCEPT lines for 4 Decisions, because the authority queue reports the same decisionAcceptance rows orient reports as pendingAcceptances - a fact stated in MY OWN D0164 text (`largely the same items counted twice`) which I then built a deck around without deduping. They judged all four twice. AND MY FIRST FIX HAD ITS OWN DEFECT, caught by cross-checking counts rather than by trusting the total: deduping with the authority queue collected FIRST reclassified every finding as authority and took that class from 22 to 0 while 61 still looked like a plausible total. The aggregate class must be collected LAST. Estimate 5 pts, delivered as a skill, a tool and a published deck, with two field defects fixed inside the same sprint and usability still theirs to judge."; }
    part odRetroGateR1 : TestResult { :>> id = "0d8005ce-0814-65ce-9b3e-0000003005ce"; :>> outcome = VerdictKind::pass; :>> judgedAgainst = "dafc7f5"; :>> judgedAt = "2026-08-20"; :>> judgedBy = "claudeOpus5"; }
}
