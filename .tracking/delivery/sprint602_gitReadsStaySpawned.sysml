// ProjectDeliveryS602 — Sprint 602: Rank 5 of D0367: measure the residual git spawns in keel orient and keel guard, and let the number decide the gix move (dcGitReadsStayInProcess, D0372). EXECUTE. 1 pts.
package ProjectDeliveryS602 {
    private import EngineElement::*;
    private import EngineWork::*;
    private import EngineVerification::*;
    private import EngineRelationships::*;

    #CharteredBy dependency from gitReadsStaySpawnedStory to d0372;

    part gitReadsStaySpawnedStory : Story {
        :>> id = "16023d35-0302-488f-a875-79c7dae14374";
        :>> title = "Sprint 602: Rank 5 of D0367: measure the residual git spawns in keel orient and keel guard, and let the number decide the gix move (dcGitReadsStayInProcess, D0372) (1 pts)";
        :>> createdAt = "2026-09-08"; :>> createdBy = "claudeOpus5"; :>> kind = WorkKind::code; :>> priority = WorkPriority::p0; :>> owner = "claudeOpus5"; :>> estimatedPoints = 1;
    }

    action def DeliveryRunS602 {
        action storyGitReadsStaySpawned;
        verification storyGitReadsStaySpawnedDoD : Test { :>> id = "c35c1247-de7b-4ff6-aa1f-b542635a0516"; :>> method = VerificationMethod::test; :>> procedureText = "MEASURED on this tree, KEEL_PERF=2, warm cache, shell timer: `keel orient .` git x11 in 473 / 476 / 561 ms before (rev-parse --abbrev-ref x4, rev-list --left-right x2, cat-file --batch-check x1, log -1 x1, rev-parse --git-path x1, rev-parse --short x1, rev-parse HEAD x1); `sync::divergence` was called twice from orient::compute_after_fetch (orient.rs 721 and 841) and the second call now reuses the first's value: git x8 in 406 / 431 / 433 ms after, orient wall 1387-1459 ms, stdout byte-identical to the dd4d91f binary (diff). `keel guard --no-receipt` git x41 summing 4877 / 9432 ms across the worker threads (rev-parse --short x11 of which 10 are per-tag, core.quotePath diff --cached x6, rev-parse --show-prefix x6, cat-file x4, diff --cached x2, log x5, abbrev-ref x2); the slowest guard alone, priority-inversion, is 1452 ms with 7 spawns in 374 ms, and 4915 ms under contention - the guard wall is CPU under contention, not git. DECIDED by the item's rule: 406-433 ms per orient is under the 500 ms bar, so gix is mooted by D0372 naming the number. VERIFIED: cargo clippy pedantic clean; cargo build --release; the orient diff; keel validate ."; }
        // RAN: KEEL_PERF=2 keel orient . x3 each side: git x11 473/476/561 ms -> x8 406/431/433 ms; diff of orient stdout empty; keel validate . clean
        part storyGitReadsStaySpawnedDoDR1 : TestResult { :>> id = "832ab7bc-6d7f-4b12-8c38-6545591e619c"; :>> outcome = VerdictKind::pass; :>> judgedAgainst = "1335211ad79f2674d2b38b08906b0734c510aca2"; :>> judgedAt = "2026-09-08T01:07:00-06:00"; :>> judgedBy = "claudeOpus5"; }
    }

    verification gitReadsStaySpawnedRefineGate : Test { :>> id = "db11f479-62da-49ae-ab6c-fe7c6d2f3de5"; :>> title = "Sprint 602 refine gate (DoR)"; :>> createdAt = "2026-09-08"; :>> createdBy = "claudeOpus5"; :>> method = VerificationMethod::inspect; :>> procedureText = "READY, 1 pt: a measurement with the item's own rule deciding it, one duplicate read removed in orient.rs (outside the keystone lock), one Decision. Chartered by D0372. The DoD names each command it ran (`KEEL_PERF=2 keel orient .`, `KEEL_PERF=2 keel guard --no-receipt`, `keel guard <name>`), each of which exists."; }
    // RAN: KEEL_PERF=2 keel orient . x3 before (git x11 473/476/561 ms) and after orient.rs dedupe (git x8 406/431/433 ms); diff of orient stdout byte-identical; cargo clippy --release -p keel-cli --all-targets clean
    part gitReadsStaySpawnedRefineGateR1 : TestResult { :>> id = "1d0335f0-94d6-412f-b707-3ca7f096c909"; :>> outcome = VerdictKind::pass; :>> judgedAgainst = "1335211ad79f2674d2b38b08906b0734c510aca2"; :>> judgedAt = "2026-09-08T01:05:00-06:00"; :>> judgedBy = "claudeOpus5"; }
    verification gitReadsStaySpawnedStandupGate : Test { :>> id = "26d2ea08-deb4-4eb5-915f-aaff1e3361be"; :>> title = "Sprint 602 standup gate"; :>> createdAt = "2026-09-08"; :>> createdBy = "claudeOpus5"; :>> method = VerificationMethod::inspect; :>> procedureText = "ONE CHOICE. The duplicate divergence read is removed because it is the same value read twice in one function, not cached across calls - sync::cmd_sync calls divergence before and after a fetch and must see both, so a process-wide memo of it would be wrong for the one caller that needs it to move. The next tier, memoizing staged_changes across the six guards that call it, is in guards.rs under the keystone lock and is named in D0372 rather than taken."; }
    // RAN: KEEL_PERF=2 keel orient . x3 before (git x11 473/476/561 ms) and after orient.rs dedupe (git x8 406/431/433 ms); diff of orient stdout byte-identical; cargo clippy --release -p keel-cli --all-targets clean
    part gitReadsStaySpawnedStandupGateR1 : TestResult { :>> id = "3407216e-b75d-4988-8f86-0beffa72efdc"; :>> outcome = VerdictKind::pass; :>> judgedAgainst = "1335211ad79f2674d2b38b08906b0734c510aca2"; :>> judgedAt = "2026-09-08T01:05:00-06:00"; :>> judgedBy = "claudeOpus5"; }
    verification gitReadsStaySpawnedImplementGate : Test { :>> id = "9fea7726-1112-416d-9748-1eb04c51e60e"; :>> title = "Sprint 602 implement gate"; :>> createdAt = "2026-09-08"; :>> createdBy = "claudeOpus5"; :>> method = VerificationMethod::test; :>> procedureText = "RAN: KEEL_PERF=1 and =2 keel orient . three times each before and after; sed on orient.rs line 841; cargo clippy --release -p keel-cli --all-targets; cargo build --release; cp to keel-serve.exe; diff of orient stdout against .keel/bin/keel.exe (dd4d91f); KEEL_PERF=2 keel guard --no-receipt twice with the per-guard phase list sorted; keel guard priority-inversion / verification-trace / decision-scaffolding alone with KEEL_PERF=2; keel record decision --from d0372.md."; }
    // RAN: KEEL_PERF=2 keel orient . x3 before (git x11 473/476/561 ms) and after orient.rs dedupe (git x8 406/431/433 ms); diff of orient stdout byte-identical; cargo clippy --release -p keel-cli --all-targets clean
    part gitReadsStaySpawnedImplementGateR1 : TestResult { :>> id = "f1d6a81a-9651-46e5-b6c2-5c61574c5826"; :>> outcome = VerdictKind::pass; :>> judgedAgainst = "1335211ad79f2674d2b38b08906b0734c510aca2"; :>> judgedAt = "2026-09-08T01:05:00-06:00"; :>> judgedBy = "claudeOpus5"; }
    verification gitReadsStaySpawnedReviewGate : Test { :>> id = "61addda6-4da1-4dec-a912-a84617163a93"; :>> title = "Sprint 602 review gate — three passes per D0172"; :>> createdAt = "2026-09-08"; :>> createdBy = "claudeOpus5"; :>> method = VerificationMethod::inspect; :>> procedureText = "THREE QUESTIONS (D0172). Is the number the item asked for? Yes: count and timed total under KEEL_PERF=2 on a warm cache, per orient, three runs each side. Does the change alter output? Byte-identical orient. What is NOT claimed: that git is cheap in `keel guard` (x41, 4.9-9.4 s summed) - it is not the critical path there, which is CPU across sixty-five guards on eight threads; that gix would never pay - at a different spawn cost or on a host without the receipt the bar could be crossed, and the item's rule still decides."; }
    // RAN: KEEL_PERF=2 keel orient . x3 before (git x11 473/476/561 ms) and after orient.rs dedupe (git x8 406/431/433 ms); diff of orient stdout byte-identical; cargo clippy --release -p keel-cli --all-targets clean
    part gitReadsStaySpawnedReviewGateR1 : TestResult { :>> id = "fde2b8e3-3cd3-47fb-959d-e0912624b8e1"; :>> outcome = VerdictKind::pass; :>> judgedAgainst = "1335211ad79f2674d2b38b08906b0734c510aca2"; :>> judgedAt = "2026-09-08T01:05:00-06:00"; :>> judgedBy = "claudeOpus5"; }
    verification gitReadsStaySpawnedCloseOutGate : Test { :>> id = "86f2a2c0-eac3-4836-ac0d-9e3605c2d609"; :>> title = "Sprint 602 closeOut gate (autonomous, D0049)"; :>> createdAt = "2026-09-08"; :>> createdBy = "claudeOpus5"; :>> method = VerificationMethod::inspect; :>> procedureText = "CLOSED. Orient git x11 in 473-561 ms to x8 in 406-433 ms; gix mooted by D0372 at that number, accepted under standing consent as a non-fork. Rank 6 (dcHookDaemonOnlyIfTheReceiptIsNotEnough) is judged next on sprint 601's after number."; }
    // RAN: KEEL_PERF=2 keel orient . x3 before (git x11 473/476/561 ms) and after orient.rs dedupe (git x8 406/431/433 ms); diff of orient stdout byte-identical; cargo clippy --release -p keel-cli --all-targets clean
    part gitReadsStaySpawnedCloseOutGateR1 : TestResult { :>> id = "552395df-089f-4b55-999d-5b8c61954f10"; :>> outcome = VerdictKind::pass; :>> judgedAgainst = "1335211ad79f2674d2b38b08906b0734c510aca2"; :>> judgedAt = "2026-09-08T01:05:00-06:00"; :>> judgedBy = "claudeOpus5"; }
    verification gitReadsStaySpawnedRetroGate : Test { :>> id = "e78b712f-923d-4cd9-a31e-8050393b3816"; :>> title = "Sprint 602 retro gate (autonomous, D0049)"; :>> createdAt = "2026-09-08"; :>> createdBy = "claudeOpus5"; :>> method = VerificationMethod::analyze; :>> procedureText = "AVOIDABLE-ISSUE SCAN HELD. One finding: the KEEL_PERF summed git time in `keel guard` (9.4 s) reads as the dominant cost when the wall is 5 s - a sum across parallel threads is not a wall time, and the line does not say so. No new item - already tracked: issue410 holds the perf-line accuracy class, and the guard wall's real driver (CPU under contention) is named in D0372 for whoever measures next."; }
    // RAN: KEEL_PERF=2 keel orient . x3 before (git x11 473/476/561 ms) and after orient.rs dedupe (git x8 406/431/433 ms); diff of orient stdout byte-identical; cargo clippy --release -p keel-cli --all-targets clean
    part gitReadsStaySpawnedRetroGateR1 : TestResult { :>> id = "cff7fcf4-9b3a-4dfe-94ca-539525b963b2"; :>> outcome = VerdictKind::pass; :>> judgedAgainst = "1335211ad79f2674d2b38b08906b0734c510aca2"; :>> judgedAt = "2026-09-08T01:05:00-06:00"; :>> judgedBy = "claudeOpus5"; }
}
