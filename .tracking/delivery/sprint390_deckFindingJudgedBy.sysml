// ProjectDeliveryS390 — Sprint 390: the local deck's finding tap names the human - issue199, the issue197 class closed on its last path. EXECUTE. 1 pts.
package ProjectDeliveryS390 {
    private import EngineElement::*;
    private import EngineWork::*;
    private import EngineVerification::*;
    private import EngineRelationships::*;

    #CharteredBy dependency from deckFindingJudgedByStory to d0178;

    part deckFindingJudgedByStory : Story {
        :>> id = "2b8bd58d-bafd-48a4-aacc-387172c126ef";
        :>> title = "Sprint 390: judged_by travels with every human gesture (1 pts)";
        :>> createdAt = "2026-08-21"; :>> createdBy = "claudeFable5"; :>> kind = WorkKind::code; :>> priority = WorkPriority::p0; :>> owner = "claudeFable5"; :>> estimatedPoints = 1;
    }

    action def DeliveryRunS390 {
        action storyDeckFindingJudgedBy;
        verification storyDeckFindingJudgedByDoD : Test { :>> id = "e0c21172-7699-4323-bf99-dd62a761bd95"; :>> method = VerificationMethod::test; :>> procedureText = "DELIVERED BACKLOG ITEMS: dcDeckFindingJudgedBy. Clears issue199. The human dispositioned 19 findings on the LOCAL console deck and every record landed judgedBy=claudeFable5: saveLocal's finding body omitted judged_by, so the server resolved the machine binding - the exact issue197 defect, fixed in sprint 380 on the INBOX path only. Guard-invisible again under D0165's delegation; caught by the out-of-band diff review the turn started with. FIXED: the 19 records corrected to wweatherholtz (their taps, confirmed in chat: others processed on deck) with attestation texts stating both the event and the correction; deck.rs saveLocal now sends judged_by:HUMAN with a substantive default rationale; the emitted script still parses (node --check in the suite). THE CLASS RULE, third occurrence, final form per D0172: every write surface carrying a human gesture names that human IN THE REQUEST BODY - the actor is data the gesture carries, never ambient state any layer resolves."; }
        part storyDeckFindingJudgedByDoDR1 : TestResult { :>> id = "3e799033-a680-4c72-a974-14baf4a77e8c"; :>> outcome = VerdictKind::pass; :>> judgedAgainst = "92254e1"; :>> judgedAt = "2026-08-21"; :>> judgedBy = "claudeFable5"; }
    }

    verification deckFindingJudgedByRefineGate : Test { :>> id = "b083dee7-0620-47d1-aa75-a05532de67c8"; :>> title = "Sprint 390 refine gate (DoR)"; :>> createdAt = "2026-08-21"; :>> createdBy = "claudeFable5"; :>> method = VerificationMethod::inspect; :>> procedureText = "DoR. A one-line page fix plus 19 record corrections, routed EXECUTE under d0178 (the human-channel decision this defect violates in spirit). estimatedPoints=1."; }
    part deckFindingJudgedByRefineGateR1 : TestResult { :>> id = "252851b3-cb93-4175-b81d-bbe95761009f"; :>> outcome = VerdictKind::pass; :>> judgedAgainst = "92254e1"; :>> judgedAt = "2026-08-21"; :>> judgedBy = "claudeFable5"; }
    verification deckFindingJudgedByStandupGate : Test { :>> id = "32973e25-389b-46e0-98c7-51da3a7587c0"; :>> title = "Sprint 390 standup gate"; :>> createdAt = "2026-08-21"; :>> createdBy = "claudeFable5"; :>> method = VerificationMethod::inspect; :>> procedureText = "Approach: records first (truth), tool second (recurrence) - the sprint-380 playbook replayed on the surface that sprint missed. No blockers."; }
    part deckFindingJudgedByStandupGateR1 : TestResult { :>> id = "04459e94-6857-483b-8818-c6e951c13513"; :>> outcome = VerdictKind::pass; :>> judgedAgainst = "92254e1"; :>> judgedAt = "2026-08-21"; :>> judgedBy = "claudeFable5"; }
    verification deckFindingJudgedByImplementGate : Test { :>> id = "28d9023e-5dde-4f88-a094-d4bbd2f0c538"; :>> title = "Sprint 390 implement gate"; :>> createdAt = "2026-08-21"; :>> createdBy = "claudeFable5"; :>> method = VerificationMethod::test; :>> procedureText = "The 19 corrections verified by grep over the staged diff (19x judgedBy=wweatherholtz, zero claudeFable5 remaining in the new records); the page fix verified by the deck test suite (emitted script parses, dead-mechanism pin, config round-trip)."; }
    part deckFindingJudgedByImplementGateR1 : TestResult { :>> id = "1f558a38-075f-4f47-bbff-8947a962b905"; :>> outcome = VerdictKind::pass; :>> judgedAgainst = "92254e1"; :>> judgedAt = "2026-08-21"; :>> judgedBy = "claudeFable5"; }
    verification deckFindingJudgedByReviewGate : Test { :>> id = "ee2b98f6-41e6-4bb5-9924-74cac5fb5876"; :>> title = "Sprint 390 review gate — three passes per D0172"; :>> createdAt = "2026-08-21"; :>> createdBy = "claudeFable5"; :>> method = VerificationMethod::inspect; :>> procedureText = "PASS 1, CLAIMS: diff-grep counts quoted; suite green. PASS 2, BOUNDARY: issue170's record kept the human's own typed note verbatim rather than the template text. PASS 3, OWN DIFF: sprint 380's fix was scoped to the recorder when the CLASS spanned every surface - this sprint pays that scoping debt and states the rule in its final form. WHAT A REVIEWER SHOULD ATTACK: the acceptance and sitting paths already carried identity; an audit of OTHER agent-callable write surfaces for ambient-actor resolution is the natural next sweep - the WRITE_OPS table is where such an audit anchors."; }
    part deckFindingJudgedByReviewGateR1 : TestResult { :>> id = "484515cf-4873-4a5a-8cf3-88bb68144824"; :>> outcome = VerdictKind::pass; :>> judgedAgainst = "92254e1"; :>> judgedAt = "2026-08-21"; :>> judgedBy = "claudeFable5"; }
    verification deckFindingJudgedByCloseOutGate : Test { :>> id = "1e1ecd1d-c18f-46b2-a0ee-f5c766949b32"; :>> title = "Sprint 390 closeOut gate (autonomous, D0049)"; :>> createdAt = "2026-08-21"; :>> createdBy = "claudeFable5"; :>> method = VerificationMethod::inspect; :>> procedureText = "Autonomous closeOut (D0049). issue199 recorded with its resolver via the write API; DoD flipped via append-result; the 7 superseded inbox rows marked Processed. validate clean; guards ALL PASS."; }
    part deckFindingJudgedByCloseOutGateR1 : TestResult { :>> id = "385c7a8b-5f26-4189-a4b7-12981b91769d"; :>> outcome = VerdictKind::pass; :>> judgedAgainst = "92254e1"; :>> judgedAt = "2026-08-21"; :>> judgedBy = "claudeFable5"; }
    verification deckFindingJudgedByRetroGate : Test { :>> id = "a7cdb01e-2668-4856-883b-253d5371f008"; :>> title = "Sprint 390 retro gate (autonomous, D0049)"; :>> createdAt = "2026-08-21"; :>> createdBy = "claudeFable5"; :>> method = VerificationMethod::analyze; :>> procedureText = "Autonomous retro (D0049). AVOIDABLE-ISSUE SCAN under rcRecurrence: fix-scoped-to-one-surface-of-a-class is the recurrence here (sprint 380 fixed the recorder, not the page) - the preventing practice: when a defect is a CLASS instance, enumerate every surface of the class in the fixing sprint's review gate, which this record now does (the WRITE_OPS-anchored sweep named). WELL: the out-of-band-writes hook flagged the human's uncommitted deck writes at turn start, which is what routed them through the diff review that caught the misattribution - a control built for co-mingling prevention caught an attribution defect as a side effect. Estimate 1 pt, delivered."; }
    part deckFindingJudgedByRetroGateR1 : TestResult { :>> id = "58d7d075-dd6e-4e8b-8549-30f357c8ba62"; :>> outcome = VerdictKind::pass; :>> judgedAgainst = "92254e1"; :>> judgedAt = "2026-08-21"; :>> judgedBy = "claudeFable5"; }
}
