// ProjectDeliveryS411 — Sprint 411: the run gate is a pure function of the tree (issue206): K15's tree-derivability wins the verdict, K3's signal rides beside it. EXECUTE. 1 pts.
package ProjectDeliveryS411 {
    private import EngineElement::*;
    private import EngineWork::*;
    private import EngineVerification::*;
    private import EngineRelationships::*;

    #CharteredBy dependency from runGateTreeDerivableStory to d0182;

    part runGateTreeDerivableStory : Story {
        :>> id = "5d8e3106-8096-479d-ac3f-79bd47adf041";
        :>> title = "Sprint 411: the run gate is tree-pure (1 pts)";
        :>> createdAt = "2026-08-22"; :>> createdBy = "claudeFable5"; :>> kind = WorkKind::code; :>> priority = WorkPriority::p0; :>> owner = "claudeFable5"; :>> estimatedPoints = 1;
    }

    action def DeliveryRunS411 {
        action storyRunGateTreeDerivable;
        verification storyRunGateTreeDerivableDoD : Test { :>> id = "55ba1c77-3636-4884-8d3c-94cd8e77ab21"; :>> method = VerificationMethod::test; :>> procedureText = "DELIVERED: dcRunGateTreeDerivable (resolves issue206), taking OPTION (a) of the fork its resolver deliberately left open, with the rationale recorded: K15 (every enforcement verdict re-derivable from committed truth) is a kernel invariant while K3's enforcement-loss check is a signal, so the signal moves OUT of the verdict and BESIDE it. finish() no longer pushes the fired-since-spawn problem into the gate's problems (a machine-local gitignored file can no longer redden a verdict another clone cannot re-derive); instead ledgerSignal (fired | SILENT | not-checked) is carried in BOTH run records - a new field in the machine-local JSON (RUN_RECORD_FIELDS 13 -> 14) and a named clause in the tracked summary's procedureText marked report-only - so the K3 evidence reaches the human review the diff already awaits unconditionally, with no loss of visibility. Verified: launcher tests green; clippy clean; the tracked-summary format threads the signal through its argument order (compile-checked by the format string arity)."; }
        part storyRunGateTreeDerivableDoDR1 : TestResult { :>> id = "27655de8-dbfa-4ab9-a224-bdfaf3caabce"; :>> outcome = VerdictKind::pass; :>> judgedAgainst = "29adc28"; :>> judgedAt = "2026-08-22"; :>> judgedBy = "claudeFable5"; }
    }

    verification runGateTreeDerivableRefineGate : Test { :>> id = "e67f0005-baaa-41b0-9740-34e283860a60"; :>> title = "Sprint 411 refine gate (DoR)"; :>> createdAt = "2026-08-22"; :>> createdBy = "claudeFable5"; :>> method = VerificationMethod::inspect; :>> procedureText = "DoR. Chartered by d0182 (the run-record decision this amends within scope); resolves the campaign's K15-vs-K3 contradiction finding. 1 point."; }
    part runGateTreeDerivableRefineGateR1 : TestResult { :>> id = "0044d70b-f8b2-4d96-a5b7-b748d3707004"; :>> outcome = VerdictKind::pass; :>> judgedAgainst = "29adc28"; :>> judgedAt = "2026-08-22"; :>> judgedBy = "claudeFable5"; }
    verification runGateTreeDerivableStandupGate : Test { :>> id = "5d2dd38f-0d51-4e73-b3cd-42f4760750d6"; :>> title = "Sprint 411 standup gate"; :>> createdAt = "2026-08-22"; :>> createdBy = "claudeFable5"; :>> method = VerificationMethod::inspect; :>> procedureText = "Approach: the fork's option (a) - demote to report-only - over option (b) (commit the ledger excerpt), because (b) publishes machine-local instrumentation into tracked facts and grows every run record for a signal whose consumer is the human reviewing THIS machine's run; the choice and its reasoning are recorded here and in the code comment where the tension lived. No blockers."; }
    part runGateTreeDerivableStandupGateR1 : TestResult { :>> id = "835504f4-29d8-4e4b-af33-428dcdc9d40e"; :>> outcome = VerdictKind::pass; :>> judgedAgainst = "29adc28"; :>> judgedAt = "2026-08-22"; :>> judgedBy = "claudeFable5"; }
    verification runGateTreeDerivableImplementGate : Test { :>> id = "c91d891a-7802-40ec-8497-cae8925db327"; :>> title = "Sprint 411 implement gate"; :>> createdAt = "2026-08-22"; :>> createdBy = "claudeFable5"; :>> method = VerificationMethod::test; :>> procedureText = "The problems-push removed; ledgerSignal computed once and written to both records; RUN_RECORD_FIELDS doc + array updated to 14; the tracked summary names the signal report-only inline. launcher tests green, clippy pedantic+nursery clean; no run was spawned to demo (the field is exercised by the next real launch, and the format-arity compile check binds the threading)."; }
    part runGateTreeDerivableImplementGateR1 : TestResult { :>> id = "2026f252-543f-458a-9aa1-a9ea014ce3d9"; :>> outcome = VerdictKind::pass; :>> judgedAgainst = "29adc28"; :>> judgedAt = "2026-08-22"; :>> judgedBy = "claudeFable5"; }
    verification runGateTreeDerivableReviewGate : Test { :>> id = "66a14ca3-29c1-49f9-bfe9-ba0345b4eb8a"; :>> title = "Sprint 411 review gate — three passes per D0172"; :>> createdAt = "2026-08-22"; :>> createdBy = "claudeFable5"; :>> method = VerificationMethod::inspect; :>> procedureText = "PASS 1, CLAIMS: the behavior change is a diff any reviewer can read in one screen; the compile-checked format arity is the threading proof. PASS 2, BOUNDARY: the trade is real and stated - a run whose hooks silently failed now lands gate-GREEN with ledgerSignal=SILENT rather than gate-RED; the defense is that the diff review is UNCONDITIONAL (green or red) and the record shouts SILENT in capitals; a reviewer who thinks silent-hooks should still redden should reopen option (b). PASS 3, OWN DIFF: the first edit left a dangling reference after moving the flag's scope - machine-caught by the compiler, restructured to a hoisted flag. WHAT A REVIEWER SHOULD ATTACK: not-checked on empty diffs conflates did-not-look with nothing-to-see; acceptable because an empty-diff run records locally only, and stated here."; }
    part runGateTreeDerivableReviewGateR1 : TestResult { :>> id = "5333008b-a1f2-4869-9525-022ec67369be"; :>> outcome = VerdictKind::pass; :>> judgedAgainst = "29adc28"; :>> judgedAt = "2026-08-22"; :>> judgedBy = "claudeFable5"; }
    verification runGateTreeDerivableCloseOutGate : Test { :>> id = "2c8dcd1e-74e8-462e-a055-6d04584ed24e"; :>> title = "Sprint 411 closeOut gate (autonomous, D0049)"; :>> createdAt = "2026-08-22"; :>> createdBy = "claudeFable5"; :>> method = VerificationMethod::inspect; :>> procedureText = "Autonomous closeOut (D0049). DoD flipped; issue206 resolves; validate + all 45 guards green."; }
    part runGateTreeDerivableCloseOutGateR1 : TestResult { :>> id = "64b365eb-9031-4bde-b077-88df2b342409"; :>> outcome = VerdictKind::pass; :>> judgedAgainst = "29adc28"; :>> judgedAt = "2026-08-22"; :>> judgedBy = "claudeFable5"; }
    verification runGateTreeDerivableRetroGate : Test { :>> id = "1a3da9df-0572-49ca-89cd-4bc962061da4"; :>> title = "Sprint 411 retro gate (autonomous, D0049)"; :>> createdAt = "2026-08-22"; :>> createdBy = "claudeFable5"; :>> method = VerificationMethod::analyze; :>> procedureText = "Autonomous retro (D0049). AVOIDABLE-ISSUE SCAN under rcRecurrence: none new. WELL: recording the fork's options in the resolver (sprint 399) meant this sprint argued a CHOICE rather than rediscovering the tension - the deliberately-does-not-pick pattern paid off. Estimate 1 pt, delivered 1."; }
    part runGateTreeDerivableRetroGateR1 : TestResult { :>> id = "2587be2b-2f76-4024-a3cc-73dc3fa169d9"; :>> outcome = VerdictKind::pass; :>> judgedAgainst = "29adc28"; :>> judgedAt = "2026-08-22"; :>> judgedBy = "claudeFable5"; }
}
