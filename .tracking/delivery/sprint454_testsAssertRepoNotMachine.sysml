// ProjectDeliveryS454 — Sprint 454: a unit test may assert a REPO property, never a MACHINE property (issue248) - and a review finding must not be overridden by its author. EXECUTE. 1 pts.
package ProjectDeliveryS454 {
    private import EngineElement::*;
    private import EngineWork::*;
    private import EngineVerification::*;
    private import EngineRelationships::*;

    #CharteredBy dependency from testsAssertRepoNotMachineStory to d0209;

    part testsAssertRepoNotMachineStory : Story {
        :>> id = "b2d00c84-d01b-49c5-a945-cb754297ba19";
        :>> title = "Sprint 454: the reviewer was right and the author overrode him (1 pts)";
        :>> createdAt = "2026-08-24"; :>> createdBy = "claudeFable5"; :>> kind = WorkKind::code; :>> priority = WorkPriority::p0; :>> owner = "claudeFable5"; :>> estimatedPoints = 1;
    }

    action def DeliveryRunS454 {
        action storyTestsAssertRepoNotMachine;
        verification storyTestsAssertRepoNotMachineDoD : Test { :>> id = "954cce1c-90c0-4176-84d6-2174444511a2"; :>> method = VerificationMethod::test; :>> procedureText = "DELIVERED: dcTestsAssertRepoNotMachine (resolves issue248, HIGH). THE DEFECT: the regression test added in sprint447 for issue240, this_repos_commit_gate_is_armed, asserted that THIS repository has an armed local git hook. That is a property of a MACHINE, not of the repository - a CI checkout configures no core.hooksPath and correctly does not need one, because CI is the hook-INDEPENDENT layer (K15/D0179) that exists precisely so nothing has to assume a hook ran. Every ci run from the issue243 commit onward failed on it, six commits red, while the paired decision-issue workflow kept succeeding - which is why a run list showing both was easy to skim past. THE FIX: assert the CONDITIONAL invariant instead - IF core.hooksPath is configured, it must resolve to a directory holding pre-commit - which still fails the exact issue240 state (configured to a null device) while an unconfigured checkout is not a violation. WHAT MAKES THIS WORTH A SPRINT RATHER THAN A QUIET FIX: my own sprint447 review gate named this risk in almost these words - 'it couples a unit test to machine-local git config, and will fail for a contributor who has not run the setup step' - and I wrote that I judged it 'acceptable and deliberate'. The review pass FOUND the defect and the author OVERRODE the reviewer. That is a failure of the review process, not of the analysis, and it is the more important finding: a three-pass review whose findings the same actor can wave through is a review in form only. VERIFIED: 253 lib tests pass locally where a hooksPath is configured and reachable; the unchanged negative test still fails an unreachable path; CI on main is GREEN again (run 32745563901, rust 2m8s)."; }
        part storyTestsAssertRepoNotMachineDoDR1 : TestResult { :>> id = "d8640ccb-3ec3-482d-b4b1-57e448e4d678"; :>> outcome = VerdictKind::pass; :>> judgedAgainst = "dfae3ca847e41f040906a06b4dd92bf53bd7b4e1"; :>> judgedAt = "2026-08-24"; :>> judgedBy = "claudeFable5"; }
    }

    verification testsAssertRepoNotMachineRefineGate : Test { :>> id = "70c4d0fa-7a47-44ec-9ad0-d300bcd991a2"; :>> title = "Sprint 454 refine gate (DoR)"; :>> createdAt = "2026-08-24"; :>> createdBy = "claudeFable5"; :>> method = VerificationMethod::inspect; :>> procedureText = "DoR. Resolves issue248 (HIGH): main was red for six commits on a test I added. Scope: correct the invariant, record the defect, and record the process finding about the overridden review. 1 point."; }
    part testsAssertRepoNotMachineRefineGateR1 : TestResult { :>> id = "ac48f7e9-09f3-47ed-9e6a-d6416c94f1b9"; :>> outcome = VerdictKind::pass; :>> judgedAgainst = "dfae3ca847e41f040906a06b4dd92bf53bd7b4e1"; :>> judgedAt = "2026-08-24"; :>> judgedBy = "claudeFable5"; }
    verification testsAssertRepoNotMachineStandupGate : Test { :>> id = "a732dfdc-9ad5-4031-a641-16a52218cd3e"; :>> title = "Sprint 454 standup gate"; :>> createdAt = "2026-08-24"; :>> createdBy = "claudeFable5"; :>> method = VerificationMethod::inspect; :>> procedureText = "Approach: the property a test can assert is the repo's, so make the assertion conditional on the machine actually claiming a local gate. That keeps the issue240 detection (configured-but-unreachable) and drops the unassertable part (must be configured). No blockers."; }
    part testsAssertRepoNotMachineStandupGateR1 : TestResult { :>> id = "a14ab0d4-a82e-4477-aef7-abf4655c43bd"; :>> outcome = VerdictKind::pass; :>> judgedAgainst = "dfae3ca847e41f040906a06b4dd92bf53bd7b4e1"; :>> judgedAt = "2026-08-24"; :>> judgedBy = "claudeFable5"; }
    verification testsAssertRepoNotMachineImplementGate : Test { :>> id = "f31c4088-31f6-41c0-8d05-fb40eca050e8"; :>> title = "Sprint 454 implement gate"; :>> createdAt = "2026-08-24"; :>> createdBy = "claudeFable5"; :>> method = VerificationMethod::test; :>> procedureText = "Verified by running: cargo test --lib gitx -> 3 passed including the corrected test and the unchanged unreachable-path negative; full lib suite 253 passed; clippy clean after a super:: import fix; landed and CI watched to completion - run 32745563901 completed SUCCESS with rust green in 2m8s, ending a six-commit red streak."; }
    part testsAssertRepoNotMachineImplementGateR1 : TestResult { :>> id = "dc216df2-4aa2-4b2b-9870-ef43dee6cc79"; :>> outcome = VerdictKind::pass; :>> judgedAgainst = "dfae3ca847e41f040906a06b4dd92bf53bd7b4e1"; :>> judgedAt = "2026-08-24"; :>> judgedBy = "claudeFable5"; }
    verification testsAssertRepoNotMachineReviewGate : Test { :>> id = "54ef544e-63e7-40a8-bf2f-7fe31e124e5b"; :>> title = "Sprint 454 review gate — three passes per D0172"; :>> createdAt = "2026-08-24"; :>> createdBy = "claudeFable5"; :>> method = VerificationMethod::inspect; :>> procedureText = "PASS 1, CLAIMS: the CI run id, its conclusion and the test counts are quoted read-backs, and CI green is read from the run rather than inferred from the local pass - which is the whole point, since the local pass is exactly what hid this. PASS 2, BOUNDARY: the corrected test cannot detect an UNARMED machine (nothing configured), which is deliberate and is the difference between a repo property and a machine property; the orient warning and the hardening row cover that case at runtime for the human, and neither belongs in a unit test. PASS 3, OWN DIFF: the finding was already in my own review gate and I overrode it with 'acceptable and deliberate', so the defect cost six red commits that the review had already priced. The durable lesson is not about hooks: it is that a review finding I disagree with must be resolved by EVIDENCE or by a recorded refutation, never by an author's judgment call in the same pass - which is precisely the adversarial-panel-review honesty rule (a panelist is never argued into accepting) applied to the solo review gate, where I am both author and reviewer and nothing structurally separates them. WHAT A REVIEWER SHOULD ATTACK: whether the solo three-pass review can ever hold that line without a second actor - and the honest answer is that it cannot reliably, which is what dcHeterogeneousCritics is parked on."; }
    part testsAssertRepoNotMachineReviewGateR1 : TestResult { :>> id = "f6a45e52-dc76-4866-8620-0be11409a265"; :>> outcome = VerdictKind::pass; :>> judgedAgainst = "dfae3ca847e41f040906a06b4dd92bf53bd7b4e1"; :>> judgedAt = "2026-08-24"; :>> judgedBy = "claudeFable5"; }
    verification testsAssertRepoNotMachineCloseOutGate : Test { :>> id = "17bf11ab-0822-4a8c-ade9-4bf016bd70b9"; :>> title = "Sprint 454 closeOut gate (autonomous, D0049)"; :>> createdAt = "2026-08-24"; :>> createdBy = "claudeFable5"; :>> method = VerificationMethod::inspect; :>> procedureText = "Autonomous closeOut (D0049). issue248 resolved, CI green on main, validate + all 49 guards + check-engine + rules green. All eight panel findings plus issue247 and issue248 are closed; two chartered follow-ons remain on the frontier (dcControlsReportArming, dcNoFalseCleanRange)."; }
    part testsAssertRepoNotMachineCloseOutGateR1 : TestResult { :>> id = "3d46a87a-8758-41db-b2b1-8ae53fd8465a"; :>> outcome = VerdictKind::pass; :>> judgedAgainst = "dfae3ca847e41f040906a06b4dd92bf53bd7b4e1"; :>> judgedAt = "2026-08-24"; :>> judgedBy = "claudeFable5"; }
    verification testsAssertRepoNotMachineRetroGate : Test { :>> id = "cc9ecc00-d873-4a56-b7cb-8227cbc0c442"; :>> title = "Sprint 454 retro gate (autonomous, D0049)"; :>> createdAt = "2026-08-24"; :>> createdBy = "claudeFable5"; :>> method = VerificationMethod::analyze; :>> procedureText = "Autonomous retro (D0049). AVOIDABLE-ISSUE SCAN under rcRecurrence: (1) THE recurrence that matters - I overrode my own review finding. The three-pass review gate produced the correct objection and the author dismissed it in the same breath, which means the review's value depended entirely on my willingness to be bound by it. That is the structural weakness the adversarial-panel-review process exists to fix and which the solo gate cannot fix alone. Candidate control: a review-gate finding marked as a risk must be either resolved in substance or carried forward as a tracked item, never closed by author judgment in the same pass. (2) A related process gap: I did not check CI after the issue243 land, so five further commits stacked on red. The memory rule 'check gh run after EVERY push' exists and I followed it at the start of the session and stopped once the sprints got rhythmic. WELL: once seen, the fix was small and correct, and the CI-green claim in this record is read from the run rather than inferred. Estimate 1 pt, delivered 1."; }
    part testsAssertRepoNotMachineRetroGateR1 : TestResult { :>> id = "3ee37ead-3675-4cad-a3e8-28bc11905fd0"; :>> outcome = VerdictKind::pass; :>> judgedAgainst = "dfae3ca847e41f040906a06b4dd92bf53bd7b4e1"; :>> judgedAt = "2026-08-24"; :>> judgedBy = "claudeFable5"; }
}
