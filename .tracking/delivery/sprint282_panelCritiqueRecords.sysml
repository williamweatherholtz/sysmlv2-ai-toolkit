// ProjectDeliveryS282 — Sprint 282: the three-critic panel's findings become engine-native critique
// facts (dcPanelCritiqueRecords, D0018/D0080). EXECUTE. 5 pts.
package ProjectDeliveryS282 {
    private import EngineElement::*;
    private import EngineWork::*;
    private import EngineVerification::*;
    private import EngineRelationships::*;

    #CharteredBy dependency from panelRecordsStory to d0144;

    part panelRecordsStory : Story {
        :>> id = "0d80014c-0814-614c-9b3e-00000030014c";
        :>> title = "Sprint 282: the panel's findings become critique facts, with independence resolved explicitly (5 pts)";
        :>> createdAt = "2026-08-14"; :>> createdBy = "claudeOpus5"; :>> kind = WorkKind::modeling; :>> priority = WorkPriority::p0; :>> owner = "claudeOpus5"; :>> estimatedPoints = 5;
    }

    action def DeliveryRunS282 {
        action storyPanelRecords;
        verification storyPanelRecordsDoD : Test { :>> id = "0d80014d-0814-614d-9b3e-00000030014d"; :>> method = VerificationMethod::demo; :>> procedureText = "Delivers dcPanelCritiqueRecords. The human commissioned a three-critic panel and asked for deliberation to unanimity; the panel ran and its findings lived only in conversation history, which D0018 forbids as a home for anything a successor needs. DELIVERED: `.tracking/panel-critiques.sysml` — ten `method=critique` verifications, each lens-tagged, severity-carrying, `#Verify`-linked to the Decision it bears on, with a result attributed to the critic that raised it. PROVENANCE IS FROM COMMITTED RECORDS, NOT MEMORY: commit ec7d548 carries the panel's verdict and issues 098/099 in full, and D0142's `context` enumerates findings (a),(b),(d),(f),(g), with (c) and (e) becoming D0143 and issue106. THE CONSTRAINT THAT SHAPED THE RECORD is what the item asked for — no finding recorded as unanimous that was not. Three unanimity claims are documented and exactly three are recorded: the central verdict against D0139(E), the ranking of the non-marker findings above the marker count, and finding (c). Findings (a),(b),(d),(f),(g) carry the raising critic and NO unanimity claim, and the record says so. INDEPENDENCE RESOLVED EXPLICITLY, not by convenience: the three critics were separate subagent CONTEXTS of the SAME model as the author, which is a distinct framing and not a distinct judgement substrate, so every panel critique is `critiquedBy = aiModel` and passes nothing by itself. The one genuinely independent verdict is the OMG kernel's undeclared-name discriminator, recorded separately as `critiquedBy = tool`. VERIFIED THAT THE GATE IS LIVE RATHER THAN VACUOUS: downgrading that single critique to aiModel makes `critic-independence` FAIL with 'd0139: target of a Critical-severity finding but has only aiModel critiques'; restoring it passes. Also recorded: the panel's one MISS — finding (e) proposed a fix that is structurally impossible — and the protagonist's surviving position, so the record is not findings-only. validate 304 clean; all 28 guards green; check-engine clean."; }
        part storyPanelRecordsDoDR1 : TestResult { :>> id = "0d80014e-0814-614e-9b3e-00000030014e"; :>> outcome = VerdictKind::pass; :>> judgedAgainst = "55f181e"; :>> judgedAt = "2026-08-14"; :>> judgedBy = "claudeOpus5"; }
    }

    verification prRefineGate : Test { :>> id = "0d80014f-0814-614f-9b3e-00000030014f"; :>> title = "Sprint 282 refine gate (DoR)"; :>> createdAt = "2026-08-14"; :>> createdBy = "claudeOpus5"; :>> method = VerificationMethod::inspect; :>> procedureText = "DoR. CONSUMER CHECK (dorConsumer, D0144): the consumers of a critique record are `critic-independence`, `critique-rigor`, `critique-coverage` and the render surface — all of which read `lens`, `critiquedBy`, `severity` and the result's `judgedBy`, so the record had to carry real values in all four rather than prose about a critique. Checking `critic-independence` FIRST is what surfaced the sprint's central problem: it demands a non-aiModel critique on any Critical-severity target, and the panel cannot supply one. That is a content question, not a formatting one, and it had to be answered before a single record was written. estimatedPoints=5. DoR met."; }
    part prRefineGateR1 : TestResult { :>> id = "0d800150-0814-6150-9b3e-000000300150"; :>> outcome = VerdictKind::pass; :>> judgedAgainst = "55f181e"; :>> judgedAt = "2026-08-14"; :>> judgedBy = "claudeOpus5"; }

    verification prStandupGate : Test { :>> id = "0d800151-0814-6151-9b3e-000000300151"; :>> title = "Sprint 282 standup gate"; :>> createdAt = "2026-08-14"; :>> createdBy = "claudeOpus5"; :>> method = VerificationMethod::inspect; :>> procedureText = "Approach: recover from git before writing anything. The panel ran in a conversation that has since been compacted, so writing these records from recollection would have produced plausible findings with no evidence behind them — the precise failure the item exists to prevent, committed in the act of preventing it. `git log --grep` found ec7d548 carrying the verdict verbatim, and D0142's `context` carried the seven non-marker findings. Everything recorded traces to one of those two. No blockers."; }
    part prStandupGateR1 : TestResult { :>> id = "0d800152-0814-6152-9b3e-000000300152"; :>> outcome = VerdictKind::pass; :>> judgedAgainst = "55f181e"; :>> judgedAt = "2026-08-14"; :>> judgedBy = "claudeOpus5"; }

    verification prImplementGate : Test { :>> id = "0d800153-0814-6153-9b3e-000000300153"; :>> title = "Sprint 282 implement gate"; :>> createdAt = "2026-08-14"; :>> createdBy = "claudeOpus5"; :>> method = VerificationMethod::test; :>> procedureText = "The decisive call was refusing to register the critics as independent. Marking them `critiquedBy = human` or inventing a tool identity for them would have made `critic-independence` pass instantly and silently converted three framings of one model into three reviewers — self-assurance dressed as assurance, which D0098 exists to forbid. Instead the actor records STATE what they were, in the `name` field a viewer renders and not only in a comment: 'Opus 5 subagent context, not an independent model'. The independence that does exist is the kernel's, recorded as the separate thing it is. The in-loop gate also caught an error mid-sprint: `ActorKind` is human|ai and has no `tool` member, so the kernel cannot be a registered actor — correctly, because the schema puts tool-ness on the CRITIQUE and identity in `judgedBy`. Recorded in the registry rather than worked around."; }
    part prImplementGateR1 : TestResult { :>> id = "0d800154-0814-6154-9b3e-000000300154"; :>> outcome = VerdictKind::pass; :>> judgedAgainst = "55f181e"; :>> judgedAt = "2026-08-14"; :>> judgedBy = "claudeOpus5"; }

    verification prReviewGate : Test { :>> id = "0d800155-0814-6155-9b3e-000000300155"; :>> title = "Sprint 282 review gate"; :>> createdAt = "2026-08-14"; :>> createdBy = "claudeOpus5"; :>> method = VerificationMethod::inspect; :>> procedureText = "Reviewed. Two things are in this record that a self-serving version would have omitted. The panel's MISS: finding (e) named a real defect and proposed a fix that cannot be built, because the critics assessed the type surface and not the packaging — recorded on the critique itself, where someone reading the panel's work will see it, rather than only in the item that redirected. And the protagonist's SURVIVING position, that the base-first rule is vindicated by its own migrations being refuted: a panel record containing only findings reads as a model with no strengths, and the human asked for a protagonist precisely so that conclusion could not be drawn by default. LIMITATION: `#Verify` targets the Decision each finding bears on, not the schema element itself, because a `part def` is not an addressable item in this model. The specific element is named in every procedureText, but it is not traversable."; }
    part prReviewGateR1 : TestResult { :>> id = "0d800156-0814-6156-9b3e-000000300156"; :>> outcome = VerdictKind::pass; :>> judgedAgainst = "55f181e"; :>> judgedAt = "2026-08-14"; :>> judgedBy = "claudeOpus5"; }

    verification prCloseOutGate : Test { :>> id = "0d800157-0814-6157-9b3e-000000300157"; :>> title = "Sprint 282 closeOut gate (autonomous, D0049)"; :>> createdAt = "2026-08-14"; :>> createdBy = "claudeOpus5"; :>> method = VerificationMethod::inspect; :>> procedureText = "Autonomous closeOut (D0049). dcPanelCritiqueRecords carries a passing DoD TestResult. Ten critique records authored with lens, severity, critic kind and attributed results; four critic actors registered with what they actually were; independence demonstrated live by negative test. ALSO IN THIS COMMIT, and it is a state correction rather than an addition: `#Supersede dependency from dcActorTraceView to dcProvenanceAsRefs`. Sprint 278 recorded that dcProvenanceAsRefs 'must not be executed as written' in PROSE inside a procedureText and nowhere else, so the item stayed third on the auto-followed ready frontier, pointing a successor at work already found structurally impossible. Read back from the computed view: ready 20 -> 19. validate 304 clean; all 28 guards green; check-engine clean. No gate bypassed."; }
    part prCloseOutGateR1 : TestResult { :>> id = "0d800158-0814-6158-9b3e-000000300158"; :>> outcome = VerdictKind::pass; :>> judgedAgainst = "55f181e"; :>> judgedAt = "2026-08-14"; :>> judgedBy = "claudeOpus5"; }

    verification prRetroGate : Test { :>> id = "0d800159-0814-6159-9b3e-000000300159"; :>> title = "Sprint 282 retro gate (autonomous, D0049)"; :>> createdAt = "2026-08-14"; :>> createdBy = "claudeOpus5"; :>> method = VerificationMethod::analyze; :>> procedureText = "Autonomous retro (D0049) under D0131's retroTrack. WELL: (1) recovering the panel from git before writing anything meant every recorded finding traces to a committed record, in a sprint whose entire failure mode is plausible-sounding reconstruction; (2) the independence question was answered by declining the easy pass and then PROVING the gate is live with a negative test, rather than reporting a green guard that might have been vacuous — `scanned: 0` in that guard's output would have hidden a vacuous pass completely; (3) the panel's miss and the protagonist's surviving position are both recorded, so the artifact is a record rather than a case. AVOIDABLE-ISSUE 1: `dcProvenanceAsRefs` sat third on the ready frontier for four sprints after sprint 278 concluded it must not be executed, because that conclusion was written in a procedureText instead of as a `#Supersede` edge. The machinery to honour the edge already existed — issue100 built it two sprints earlier — so this was not a missing capability but a fact recorded in prose in a project whose first invariant is that prose is not state. NO NEW ITEM, reason stated: fixed in this commit and read back from the computed frontier, and the class is already carried by D0018 and issue100; what it adds is that I wrote the prose myself while holding the rule, which argues the risk is highest in a sprint's own closing narrative, where conclusions get stated for the human rather than authored for the model. Estimate 5 pts, delivered."; }
    part prRetroGateR1 : TestResult { :>> id = "0d80015a-0814-615a-9b3e-00000030015a"; :>> outcome = VerdictKind::pass; :>> judgedAgainst = "55f181e"; :>> judgedAt = "2026-08-14"; :>> judgedBy = "claudeOpus5"; }
}
