// ProjectDeliveryS585 — Sprint 585: the standing executive summary stops being prose I compose and becomes a document with a contract - the ASI exec-summary surface, its checker, and its harness. EXECUTE. 3 pts.
package ProjectDeliveryS585 {
    private import EngineElement::*;
    private import EngineWork::*;
    private import EngineVerification::*;
    private import EngineRelationships::*;

    #CharteredBy dependency from execSummaryKitStory to d0354;

    part execSummaryKitStory : Story {
        :>> id = "59add496-a773-4a2f-9242-f527881aace0";
        :>> title = "Sprint 585: the standing executive summary stops being prose I compose and becomes a document with a contract - the ASI exec-summary surface, its checker, and its harness (3 pts)";
        :>> createdAt = "2026-09-06"; :>> createdBy = "claudeOpus5"; :>> kind = WorkKind::code; :>> priority = WorkPriority::p0; :>> owner = "claudeOpus5"; :>> estimatedPoints = 3;
    }

    action def DeliveryRunS585 {
        action storyExecSummaryKit;
        verification storyExecSummaryKitDoD : Test { :>> id = "78db5818-3f67-46e6-9ff0-af73087bd311"; :>> method = VerificationMethod::test; :>> procedureText = "DELIVERED BACKLOG ITEMS: dcStandingSummaryUsesTheKit (D0354, accepted on the human's quoted direction st098). DONE: asi-templates v3 imported (39 files - the template, brand tokens, vendored fonts, the contract checker, the harness); the standing queue page rebuilt from templates/exec-summary/exec-summary.html as five tabbed decisions (CLI surface, consent scope, attestation safety, gate integrity, release), each with steel-manned choices carrying real costs, the four-line reasoning chain, a pros/cons table, three mechanism diagrams and the Copy-for-AI digest; the source project named in the title, the badge and the digest's first line; published to the standing artifact URL. The pre-commit hook now runs scripts/check_templates.py whenever templates/ or the checker is staged and BLOCKS when python is absent. VERIFIED: brand-watch comparator - no drift on every observed field against the 2026-08-25 baseline, re-read live through the Microsoft 365 connector, baseline untouched; check_templates clean over the rendered page and over templates/; EXEC_SUMMARY_FILE harness 8/8 including the mobile-webkit one-tap copy; keel validate 664 clean; keel guard ALL PASS; keel suite for the tree that carries the import."; }
        // RAN: dcStandingSummaryUsesTheKit DoD pass on keel suite 562/0 (receipt 2adf3b98f93f); the implement section names each run
        part storyExecSummaryKitDoDR1 : TestResult { :>> id = "54f06bed-358c-4677-8f06-9948951caf7a"; :>> outcome = VerdictKind::pass; :>> judgedAgainst = "24911a2072ac8d6430a4e95ccff8a28b6eac5483"; :>> judgedAt = "2026-09-06"; :>> judgedBy = "claudeOpus5"; }
    }

    verification execSummaryKitRefineGate : Test { :>> id = "3b75eddb-181f-4c5a-8fbc-a0a7c9097cc3"; :>> title = "Sprint 585 refine gate (DoR)"; :>> createdAt = "2026-09-06"; :>> createdBy = "claudeOpus5"; :>> method = VerificationMethod::inspect; :>> procedureText = "READY: the human named the surface, so no fork. Two content decisions were mine: how many tabs (five - the fork plus four batches, inside the surface's 3-6) and whether the release ask belongs on the page (yes - it is a decision only they can make, and it was buried in terminal prose)."; }
    verification execSummaryKitStandupGate : Test { :>> id = "724a1481-f16c-47af-90ee-d2569592ef7c"; :>> title = "Sprint 585 standup gate"; :>> createdAt = "2026-09-06"; :>> createdBy = "claudeOpus5"; :>> method = VerificationMethod::inspect; :>> procedureText = "THE HARNESS CAUGHT A REAL GAP, NOT A FORMAT NIT: it clicks the third choice of the first decision, and the CLI tab had two. The middle course - collapse only the gating family - was genuinely available and unwritten, so it went into D0346's text and onto the page, where it loses for a stated reason (same breakage class as A on the most-called verbs, a quarter of the consolidation)."; }
    verification execSummaryKitImplementGate : Test { :>> id = "424f1da2-4997-49f4-ab8f-816728464a08"; :>> title = "Sprint 585 implement gate"; :>> createdAt = "2026-09-06"; :>> createdBy = "claudeOpus5"; :>> method = VerificationMethod::test; :>> procedureText = "RAN: keel process import --from-library asi-templates (39 files); Microsoft 365 read_resource over the three watched roots, then check_manifest.py - no drift; python scripts/check_templates.py - clean (it first refused my own footer word 'checked' as a pre-selected radio, and refused a 15-word cost line: both my prose, both fixed); pytest tests/exec_summary 8/8 against the rendered page; keel sync-claude (46 skills); keel validate 664; keel guard ALL PASS; keel suite."; }
    verification execSummaryKitReviewGate : Test { :>> id = "2bf2cec9-de6c-4280-b897-17783e60c7ee"; :>> title = "Sprint 585 review gate — three passes per D0172"; :>> createdAt = "2026-09-06"; :>> createdBy = "claudeOpus5"; :>> method = VerificationMethod::inspect; :>> procedureText = "THREE PASSES. (1) IS THE SURFACE THE SKILL'S OR MINE: the style block, the tabs JS and the digest builder are copied byte-for-byte from the source template; only content changed. (2) DOES EVERY TAB ASK SOMETHING: five tabs, five distinct asks, each with a recommendation and its cost - no appendix tabs. (3) IS THE GATE REAL: the unit ships no guard, so the hook step is the enforcement; it blocks rather than skips when python is absent."; }
    verification execSummaryKitCloseOutGate : Test { :>> id = "d7af26ed-3d42-4b67-bc49-85b42e9ae3c8"; :>> title = "Sprint 585 closeOut gate (autonomous, D0049)"; :>> createdAt = "2026-09-06"; :>> createdBy = "claudeOpus5"; :>> method = VerificationMethod::inspect; :>> procedureText = "CLOSED. The queue now lives at one URL in the format the human asked for, and the next standing summary is a re-render, not a re-composition."; }
    verification execSummaryKitRetroGate : Test { :>> id = "9549eb12-3c0a-4f56-a36b-e0cfee166f8c"; :>> title = "Sprint 585 retro gate (autonomous, D0049)"; :>> createdAt = "2026-09-06"; :>> createdBy = "claudeOpus5"; :>> method = VerificationMethod::analyze; :>> procedureText = "no new item - already tracked: issue338's class shows up here as D0346's third option - a criterion (or an option set) written without deriving it from the measurement beside it. The lesson: a checker that reads the deliverable catches what a reviewer skims past, including two of my own sentences."; }
}
