// ProjectDeliveryS263 — Sprint 263: a hook referencing a deleted script is caught by a guard, not by
// the human noticing stderr (issue093, D0047). Field-reported. EXECUTE. 2 pts.
package ProjectDeliveryS263 {
    private import EngineElement::*;
    private import EngineWork::*;
    private import EngineVerification::*;
    private import EngineRelationships::*;

    #CharteredBy dependency from hookConfigStory to d0047;

    part hookConfigStory : Story {
        :>> id = "0d800003-0814-6003-9b3e-000000300003";
        :>> title = "Sprint 263: remove the stale Stop hook; hook-config-integrity guard (2 pts)";
        :>> createdAt = "2026-08-14"; :>> createdBy = "claudeOpus5"; :>> kind = WorkKind::code; :>> priority = WorkPriority::p0; :>> owner = "claudeOpus5"; :>> estimatedPoints = 2;
    }

    action def DeliveryRunS263 {
        action storyHookConfig;
        verification storyHookConfigDoD : Test { :>> id = "0d800004-0814-6004-9b3e-000000300004"; :>> method = VerificationMethod::test; :>> procedureText = "Delivers dcHookConfigIntegrity (issue093). The human reported the Stop hook breaking; reproduced exactly as `python .engine/tools/stop_gate.py` -> \"can't open file ... No such file or directory\", firing at EVERY turn end for a full sitting. D0134 moved the in-loop gates into the binary and deleted the python scripts, and .claude/settings.json received the replacement — but .claude/settings.local.json ALSO declared a Stop hook pointing at the deleted script, and Claude Code MERGES hooks across settings files rather than letting the more specific one override, so two Stop hooks fired and the stale one failed every turn. FIX: remove the stale hook (its file's only content), plus the `hook-config-integrity` guard checking that every hook `command` in .claude/settings*.json naming a repo-relative script exists. WARNING-level deliberately: the config is machine-local and partly gitignored, so CI cannot see it and one contributor's personal hook must never block another's commit; a warning still fires on every `keel guard`, INCLUDING inside the Stop hook itself, which makes a sibling hook's breakage self-reporting. VERIFY, all measured: the real failure reproduced before the fix; guard clean at 3 scanned after removal; NEGATIVE TEST — restoring the exact stale settings.local.json yields the warning naming the missing script, and removing it returns to clean; a malformed settings JSON is reported since every hook it declares is silently inert; absolute paths and .exe references are deliberately not flagged, because an unbuilt binary is a legitimate transient state the hook commands already probe for. `keel version` now reports 24 guards (18 hard, 6 warning-only) computed from GUARD_NAMES. Doc-sync: guards.md catalogue + count, CLAUDE.md §5. clippy clean; 157 tests; validate + all 24 guards + check-engine green at 97530bf."; }
        part storyHookConfigDoDR1 : TestResult { :>> id = "0d800005-0814-6005-9b3e-000000300005"; :>> outcome = VerdictKind::pass; :>> judgedAgainst = "97530bf"; :>> judgedAt = "2026-08-14"; :>> judgedBy = "claudeOpus5"; }
    }

    verification hcRefineGate : Test { :>> id = "0d800006-0814-6006-9b3e-000000300006"; :>> title = "Sprint 263 refine gate (DoR)"; :>> createdAt = "2026-08-14"; :>> createdBy = "claudeOpus5"; :>> method = VerificationMethod::inspect; :>> procedureText = "DoR: a FIELD report from the human — 'why are the stop hooks breaking? should be fixed, yes?' — with no stack trace. The plan was to reproduce before theorising, since I wrote this gate and had never once observed it fire. estimatedPoints=2. DoR met."; }
    part hcRefineGateR1 : TestResult { :>> id = "0d800007-0814-6007-9b3e-000000300007"; :>> outcome = VerdictKind::pass; :>> judgedAgainst = "97530bf"; :>> judgedAt = "2026-08-14"; :>> judgedBy = "claudeOpus5"; }

    verification hcStandupGate : Test { :>> id = "0d800008-0814-6008-9b3e-000000300008"; :>> title = "Sprint 263 standup gate"; :>> createdAt = "2026-08-14"; :>> createdBy = "claudeOpus5"; :>> method = VerificationMethod::inspect; :>> procedureText = "Approach: run the hook directly on both branches (green and red), then run the EXACT command string from settings.json rather than the binary, then audit every settings file in play. The first three all PASSED — the code was correct — which is what forced attention onto configuration, where the defect actually was. No blockers."; }
    part hcStandupGateR1 : TestResult { :>> id = "0d800009-0814-6009-9b3e-000000300009"; :>> outcome = VerdictKind::pass; :>> judgedAgainst = "97530bf"; :>> judgedAt = "2026-08-14"; :>> judgedBy = "claudeOpus5"; }

    verification hcImplementGate : Test { :>> id = "0d80000a-0814-600a-9b3e-00000030000a"; :>> title = "Sprint 263 implement gate"; :>> createdAt = "2026-08-14"; :>> createdBy = "claudeOpus5"; :>> method = VerificationMethod::test; :>> procedureText = "Implemented at 97530bf. The guard's LEVEL carried more design weight than its logic: hard-blocking would have been wrong, because a contributor's personal gitignored hook referencing a path outside the repo would then block an unrelated commit — the issue076/issue081 dynamic where an over-strict gate trains the actor to disable it. Warning-level keeps it visible on every run without that failure mode. Scope kept narrow to script extensions, excluding .exe and extensionless binaries, so the guard never fires on a legitimately unbuilt target/release/keel.exe."; }
    part hcImplementGateR1 : TestResult { :>> id = "0d80000b-0814-600b-9b3e-00000030000b"; :>> outcome = VerdictKind::pass; :>> judgedAgainst = "97530bf"; :>> judgedAt = "2026-08-14"; :>> judgedBy = "claudeOpus5"; }

    verification hcReviewGate : Test { :>> id = "0d80000c-0814-600c-9b3e-00000030000c"; :>> title = "Sprint 263 review gate"; :>> createdAt = "2026-08-14"; :>> createdBy = "claudeOpus5"; :>> method = VerificationMethod::inspect; :>> procedureText = "Reviewed. The uncomfortable part is not the bug but the blindness around it: I wired this gate, stated REPEATEDLY across the sitting that I could not verify a Stop hook from inside the turn that wires it, and treated that as a limitation to disclose rather than a problem to solve. The config surface was readable at any moment and I never read it. Disclosing an unverifiable claim is not the same as verifying what CAN be verified, and the honest generalisation is that when a component breaks after a migration, what REFERENCES it should be swept before what it DOES is audited — the code was newly written and tested, so it was the least likely culprit and I probed it first anyway."; }
    part hcReviewGateR1 : TestResult { :>> id = "0d80000d-0814-600d-9b3e-00000030000d"; :>> outcome = VerdictKind::pass; :>> judgedAgainst = "97530bf"; :>> judgedAt = "2026-08-14"; :>> judgedBy = "claudeOpus5"; }

    verification hcCloseOutGate : Test { :>> id = "0d80000e-0814-600e-9b3e-00000030000e"; :>> title = "Sprint 263 closeOut gate (autonomous, D0049)"; :>> createdAt = "2026-08-14"; :>> createdBy = "claudeOpus5"; :>> method = VerificationMethod::inspect; :>> procedureText = "Autonomous closeOut (D0049). dcHookConfigIntegrity carries a passing DoD TestResult at 97530bf; issue093 RESOLVES. The stale hook is gone and exactly one Stop hook remains — the binary one. Every settings file in play was audited and no hook references a missing script. validate + all 24 guards + check-engine green; clippy clean; 157 tests."; }
    part hcCloseOutGateR1 : TestResult { :>> id = "0d80000f-0814-600f-9b3e-00000030000f"; :>> outcome = VerdictKind::pass; :>> judgedAgainst = "97530bf"; :>> judgedAt = "2026-08-14"; :>> judgedBy = "claudeOpus5"; }

    verification hcRetroGate : Test { :>> id = "0d800010-0814-6010-9b3e-000000300010"; :>> title = "Sprint 263 retro gate (autonomous, D0049)"; :>> createdAt = "2026-08-14"; :>> createdBy = "claudeOpus5"; :>> method = VerificationMethod::analyze; :>> procedureText = "Autonomous retro (D0049) under D0131's retroTrack. WELL: (1) reproduced the human's report before theorising, and the reproduction — not reasoning — is what located it; (2) testing the EXACT settings.json command string rather than the binary is what proved the code correct and redirected attention to config; (3) the negative test restores the precise broken config, so the guard is verified against the real defect rather than a synthetic one. FINDING 1 (tracked): a control depended on something its owner could not guarantee — instance FIVE of the class (issue076 runtime, issue081 bypass-scope, issue089/090 project data). NEW here: the dependency ran through GITIGNORED config, so no repo-side rigour could have caught it. TRACKED as issue093 with the hook-config-integrity guard as the permanent control (D0047), which now sweeps the untracked config surface automatically instead of relying on the deleter to remember. AVOIDABLE-ISSUE 1 (behavioural, no new item, reason stated): I probed the newly-written code — exit codes, `|| true`, stdin blocking, PATH resolution — before reading the config, i.e. audited the least likely culprit first. The transferable rule is 'after a migration, sweep what REFERENCES the deleted thing before auditing what replaced it', and it is not gate-able beyond the guard just built, which enforces exactly that sweep for hooks. AVOIDABLE-ISSUE 2 (recurrence, no new item, reason stated): I again handed an MSYS path (/tmp/out.txt) to Windows Python and again briefly misread the result — second instance in consecutive sprints, the class of the now-closed issue065. It is NOT automatable: the defect lives in throwaway diagnostic shell commands, not in any committed artifact, so a control could only be a reminder, which D0047 explicitly rejects as a control. The concrete rule learned is to pass paths through `cygpath -w` when crossing from bash to a Windows program, which worked in this same sprint. If it recurs a third time it should become an INDICATOR (§1.7) — monitored without an enforced threshold — rather than a fabricated gate. Estimate 2 pts, delivered."; }
    part hcRetroGateR1 : TestResult { :>> id = "0d800011-0814-6011-9b3e-000000300011"; :>> outcome = VerdictKind::pass; :>> judgedAgainst = "97530bf"; :>> judgedAt = "2026-08-14"; :>> judgedBy = "claudeOpus5"; }
}
