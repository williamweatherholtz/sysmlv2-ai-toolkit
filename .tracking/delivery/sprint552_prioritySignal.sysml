// ProjectDeliveryS552 — Sprint 552: recurrence is a priority signal, not a violation - the human's correction of guard 62, and the metric made visible. EXECUTE. 2 pts.
package ProjectDeliveryS552 {
    private import EngineElement::*;
    private import EngineWork::*;
    private import EngineVerification::*;
    private import EngineRelationships::*;

    #CharteredBy dependency from prioritySignalStory to d0311;

    part prioritySignalStory : Story {
        :>> id = "914ff7f5-7b5e-4969-830d-3fd50f5cf06e";
        :>> title = "Sprint 552: recurrence is a priority signal, not a violation - the human's correction of guard 62, and the metric made visible (2 pts)";
        :>> createdAt = "2026-09-05"; :>> createdBy = "claudeOpus5"; :>> kind = WorkKind::code; :>> priority = WorkPriority::p0; :>> owner = "claudeOpus5"; :>> estimatedPoints = 2;
    }

    action def DeliveryRunS552 {
        action storyPrioritySignal;
        verification storyPrioritySignalDoD : Test { :>> id = "47e9b4f1-c5ab-418f-a519-fb3085275dd8"; :>> method = VerificationMethod::test; :>> procedureText = "DELIVERED BACKLOG ITEMS: none new - a correction to sprint 551 under the human's words (guard 62 is improper. repeated findings increase priority, not compare against items and make their own violation. is there a priority metric?). DONE (D0311, superseding D0310): view::priority_signals computes each ready item's effective class as the higher of its resolver Issue's severity and its retro-recurrence class (two citations High, three or more Critical, one nothing); priority_inversions compares effective classes, so the existing priority-inversion warning carries recurrence and refineAssessPriority discharges it; keel show priority lists every ready item in declared order with position, class, driving signal, severity and citation count, plus the inversions; guard 62 recurrence-escalates is withdrawn with its constraint identity; D0310 flipped to superseded with the edge. VERIFY: on this tree dcVerificationByAuthority reads Critical by recurrence (3) at position 1 and the eight inversion warnings D0310 produced are gone because the class justifies the order; cli-surface-declared 103; the priority-inversion guard passes with 0; suite and clippy in the RAN line."; }
        // RAN: cargo test --release --no-fail-fast 488 passed 0 failed (completed before this line; one fewer than 489 = guard 62's test removed); clippy 0; keel show priority: dcVerificationByAuthority Critical/recurrence rec=3 at position 1, inversions 0; priority-inversion guard 0 scanned 0 warnings (was 8); cli-surface-declared 103
        part storyPrioritySignalDoDR1 : TestResult { :>> id = "bf0bf567-77c9-4206-9878-039c62190e71"; :>> outcome = VerdictKind::pass; :>> judgedAgainst = "2bc23d4"; :>> judgedAt = "2026-09-05"; :>> judgedBy = "claudeOpus5"; }
    }

    verification prioritySignalRefineGate : Test { :>> id = "782ae718-b54b-4e5c-bb52-3394d9831f6d"; :>> title = "Sprint 552 refine gate (DoR)"; :>> createdAt = "2026-09-05"; :>> createdBy = "claudeOpus5"; :>> method = VerificationMethod::inspect; :>> procedureText = "READY the moment the human named the shape: the ranking mechanism existed (D0052 order, D0258 severity signal, the inversion guard, the refinement step) and guard 62 had duplicated it with its own verdict and exemptions instead of feeding it. The question is there a priority metric had an honest answer of no - declared p0-p3 computed by nothing, and no lens."; }
    verification prioritySignalStandupGate : Test { :>> id = "21fcb102-3a89-4550-bc2a-5c0c6147d6e3"; :>> title = "Sprint 552 standup gate"; :>> createdAt = "2026-09-05"; :>> createdBy = "claudeOpus5"; :>> method = VerificationMethod::inspect; :>> procedureText = "ONE CHOICE: two citations map to High and three to Critical - the same ladder a resolver Issue's severity climbs, so one comparison serves both and the human's ordering keeps its D0052 authority with a warning, never a stop. Second: the lens is JSON like every other lens, so the console and the deck can render it without a second computation."; }
    verification prioritySignalImplementGate : Test { :>> id = "30ed7508-49cc-4230-90a7-af2249ea1a20"; :>> title = "Sprint 552 implement gate"; :>> createdAt = "2026-09-05"; :>> createdBy = "claudeOpus5"; :>> method = VerificationMethod::test; :>> procedureText = "RAN: the D0309 deny caught me a third time while writing this correction (a python heredoc with regex backslashes) and the script was written by path; guard 62 and its tests removed, LENS_NAMES 36 to 37, CLI_FACTS 102 to 103, commands.sysml, dispatch arm; clippy const fn; D0310 status flipped and the Supersede edge added by hand in D0311."; }
    verification prioritySignalReviewGate : Test { :>> id = "3fcc5991-914c-4796-8205-28cf93a64a55"; :>> title = "Sprint 552 review gate — three passes per D0172"; :>> createdAt = "2026-09-05"; :>> createdBy = "claudeOpus5"; :>> method = VerificationMethod::inspect; :>> procedureText = "THREE PASSES. (1) DOES THE SIGNAL OVER-RANK: a finding named twice ranks with High resolvers - that is the claim, and it is the human's rule now, discharged like any inversion if they disagree. (2) IS GUARD REMOVAL A WEAKENING: audit-adherence sees a guard vanish; the co-committed safety-change Decision is the sanctioned path, and the control's substance moved into the inversion guard rather than disappearing. (3) WHAT THE LENS CANNOT SEE: WorkPriority p0-p3 stays a declared attribute nobody computes - stated, not fixed."; }
    verification prioritySignalCloseOutGate : Test { :>> id = "ba62e759-33e9-4a9f-bba5-d229ccb5eb96"; :>> title = "Sprint 552 closeOut gate (autonomous, D0049)"; :>> createdAt = "2026-09-05"; :>> createdBy = "claudeOpus5"; :>> method = VerificationMethod::inspect; :>> procedureText = "CLOSED. D0310 superseded; guard count 61; the metric is a lens."; }
    verification prioritySignalRetroGate : Test { :>> id = "2a4aaff9-6dd8-434f-a349-8f5d7da83460"; :>> title = "Sprint 552 retro gate (autonomous, D0049)"; :>> createdAt = "2026-09-05"; :>> createdBy = "claudeOpus5"; :>> method = VerificationMethod::analyze; :>> procedureText = "no new item - already tracked: dcVerificationByAuthority is the front of the frontier by its own recurrence class and is worked next; the declared-but-uncomputed WorkPriority attribute is the standing D0088 indicator-versus-requirement question and is noted in d0311. The correction itself is the lesson: when a control duplicates a mechanism that already exists, the fix is to feed the mechanism, not to add a verdict beside it."; }
}
