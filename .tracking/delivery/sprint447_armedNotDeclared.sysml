// ProjectDeliveryS447 — Sprint 447: a control is reported on its REACHABILITY, not on a setting that points at it (issue240). EXECUTE. 2 pts.
package ProjectDeliveryS447 {
    private import EngineElement::*;
    private import EngineWork::*;
    private import EngineVerification::*;
    private import EngineRelationships::*;

    #CharteredBy dependency from armedNotDeclaredStory to d0209;

    part armedNotDeclaredStory : Story {
        :>> id = "f92751b6-c4b1-40fc-880c-571a3aea4e23";
        :>> title = "Sprint 447: the commit gate says whether it can actually fire (2 pts)";
        :>> createdAt = "2026-08-24"; :>> createdBy = "claudeFable5"; :>> kind = WorkKind::code; :>> priority = WorkPriority::p0; :>> owner = "claudeFable5"; :>> estimatedPoints = 2;
    }

    action def DeliveryRunS447 {
        action storyArmedNotDeclared;
        verification storyArmedNotDeclaredDoD : Test { :>> id = "f5c44fb5-bd35-4f15-9070-e2abf2c05594"; :>> method = VerificationMethod::test; :>> procedureText = "DELIVERED: dcArmedNotDeclared (resolves issue240, HIGH). THE DEFECT, found by the panel's mechanisms lens and confirmed directly: core.hooksPath was set to `nul` in this repo's .git/config, so git resolved hooks to a nonexistent directory and .githooks/pre-commit, pre-push and pre-merge-commit could not run AT ALL for an unknown period covering an entire working session - during which I repeatedly told the human 'the hook passed'. The substance had in fact been checked, because I ran keel validate/guard/gate by hand and CI re-derives on push, but the mechanism I NAMED was dead. Three shipped surfaces asserted otherwise: keel hardening reported the pre-commit point present=true failMode=fail-closed, keel orient printed no warning, and keel controls reported uncoveredHazards=[] against ctlCommitGate. ROOT CAUSE: wiredness was computed as 'git config core.hooksPath returned a non-empty value' - a PROXY for the control being reachable rather than the control being reachable - so issue116's bypass vector was closed in the action space and wide open in the detector. THE FIX: one shared gitx::commit_gate_armed(root) that asks git itself for the effective hooks path (rev-parse --git-path hooks, which honours core.hooksPath and falls back correctly), then requires that path to BE a directory CONTAINING pre-commit; it returns the directory when armed or a REASON when not, so callers can distinguish 'not configured' from 'configured but missing' from 'no pre-commit in it' rather than collapsing three states into one boolean - the N-C2 honest-surface invariant applied to the authority substrate. orient now warns with the measured reason; hardening reports present=false with 'NOT ARMED: <reason>' instead of a text describing only the one failure mode it used to check. VERIFIED end-to-end in a throwaway inited repo with a freshness-checked binary: with hooksPath=nul, orient prints 'the commit gate is NOT ARMED - core.hooksPath resolves to `nul`, which is not a directory - the gate CANNOT run' and hardening flips to present=false fail-open-announced; with hooksPath=.githooks, orient is silent and hardening reads present=true fail-closed; the real repo reads armed. Three gitx tests including a STANDING regression (this_repos_commit_gate_is_armed) that fails the build if this repo's own gate is ever unreachable again - the check whose absence let issue240 run silently. NOT CLOSED HERE, stated rather than claimed: keel controls has no notion of runtime arming at all, so its uncoveredHazards=[] was structurally unable to know; that third surface is tracked as dcControlsReportArming because it needs a modeling decision (which controls have machine-checkable bindings) rather than a predicate swap."; }
        part storyArmedNotDeclaredDoDR1 : TestResult { :>> id = "24f155c2-3190-428b-abc4-a4d146fc678c"; :>> outcome = VerdictKind::pass; :>> judgedAgainst = "60dc411f4858899910a2b83ca9ccb7ef9677435a"; :>> judgedAt = "2026-08-24"; :>> judgedBy = "claudeFable5"; }
    }

    verification armedNotDeclaredRefineGate : Test { :>> id = "163b203c-2e0d-4253-8eb8-e6a5cf751c3d"; :>> title = "Sprint 447 refine gate (DoR)"; :>> createdAt = "2026-08-24"; :>> createdBy = "claudeFable5"; :>> method = VerificationMethod::inspect; :>> procedureText = "DoR. Resolves issue240 (HIGH) from the 2026-08-24 panel: the highest-severity finding in the set, because it is the one that made me tell the human something false about enforcement repeatedly. Scope: the two predicates that made a positive false claim (orient, hardening) plus a standing regression on this repo's own gate. The declarative controls view is explicitly out of scope and tracked separately. 2 points."; }
    part armedNotDeclaredRefineGateR1 : TestResult { :>> id = "54b8ba41-9483-4a1e-addc-7223d6e38c6d"; :>> outcome = VerdictKind::pass; :>> judgedAgainst = "60dc411f4858899910a2b83ca9ccb7ef9677435a"; :>> judgedAt = "2026-08-24"; :>> judgedBy = "claudeFable5"; }
    verification armedNotDeclaredStandupGate : Test { :>> id = "c208436f-7c3d-415b-a7f2-2ccc2bf6eb41"; :>> title = "Sprint 447 standup gate"; :>> createdAt = "2026-08-24"; :>> createdBy = "claudeFable5"; :>> method = VerificationMethod::inspect; :>> procedureText = "Approach: one shared helper rather than two call sites re-deriving hook precedence - and ask GIT for the effective path (rev-parse --git-path hooks) instead of re-implementing the core.hooksPath fallback rules and getting them subtly wrong. Return Result<PathBuf, String> not bool, so every surface can report WHY it is not armed; a boolean is what collapsed three distinguishable states into a false positive in the first place. None of gitx.rs, main.rs or hardening.rs is on the frozen enforcement surface, so no marked Decision is required. No blockers."; }
    part armedNotDeclaredStandupGateR1 : TestResult { :>> id = "30126916-8405-40af-934d-ddc23a5295c8"; :>> outcome = VerdictKind::pass; :>> judgedAgainst = "60dc411f4858899910a2b83ca9ccb7ef9677435a"; :>> judgedAt = "2026-08-24"; :>> judgedBy = "claudeFable5"; }
    verification armedNotDeclaredImplementGate : Test { :>> id = "54fd50ec-12e0-4e8d-8a1a-9946dd5cf5e2"; :>> title = "Sprint 447 implement gate"; :>> createdAt = "2026-08-24"; :>> createdBy = "claudeFable5"; :>> method = VerificationMethod::test; :>> procedureText = "Verified by running a freshness-checked binary (the release build hit os error 5 and left a stale exe on the first attempt - caught by grepping the exe for a new string, per the sprint445 lesson - then rebuilt): in a throwaway inited repo, hooksPath=nul yields the orient warning naming the reason and hardening present=false fail-open-announced; hooksPath=.githooks yields silence and present=true fail-closed; this repo reads armed. cargo test --lib gitx -> 3 passed (unreachable-path refuses with a reason, a tree with no hook says 'nothing to arm', this repo's gate is armed); full lib suite green; cargo clippy --workspace --all-targets -D warnings clean after fixing a missing-Errors-section and a redundant-clone lint."; }
    part armedNotDeclaredImplementGateR1 : TestResult { :>> id = "0d237b57-c0d8-46b9-9ba1-8058353ed2e2"; :>> outcome = VerdictKind::pass; :>> judgedAgainst = "60dc411f4858899910a2b83ca9ccb7ef9677435a"; :>> judgedAt = "2026-08-24"; :>> judgedBy = "claudeFable5"; }
    verification armedNotDeclaredReviewGate : Test { :>> id = "dba9e800-2e4c-4932-9386-bcac21c7abbc"; :>> title = "Sprint 447 review gate — three passes per D0172"; :>> createdAt = "2026-08-24"; :>> createdBy = "claudeFable5"; :>> method = VerificationMethod::inspect; :>> procedureText = "PASS 1, CLAIMS: both probe directions and the three test names are quoted read-backs from the built binary, and binary freshness was verified before the run rather than inferred from exit 0. PASS 2, BOUNDARY: (i) keel controls is NOT fixed and is not claimed fixed - it has no runtime-arming concept, so it could not have known; tracked as dcControlsReportArming with the reason. (ii) The helper checks that pre-commit EXISTS in the resolved directory, not that it is executable or that git will succeed in running it - a non-executable hook on a POSIX host would still read armed; stated, and weaker than reachability in that one respect. (iii) pre-push and pre-merge-commit are not separately reported; pre-commit is the point the inventory names. PASS 3, OWN DIFF: the honest part of this sprint is that the defect was MINE and self-inflicted - almost certainly residue from my own red-team probe setting hooksPath to a null device to simulate a bypass and never restoring it - and the detector I had shipped could not see it. That is the same shape as issue242: a control evaluation that mutates the thing under test must restore it, and the surface that reports the control must check the control rather than the setting. WHAT A REVIEWER SHOULD ATTACK: whether a standing test asserting THIS repo's gate is armed belongs in the library's unit tests at all - it couples a unit test to machine-local git config, and will fail for a contributor who has not run the setup step. I judged that acceptable and deliberate: a loud failure telling a new contributor to arm their gate is strictly better than the silence that produced issue240."; }
    part armedNotDeclaredReviewGateR1 : TestResult { :>> id = "b9de2a0d-3bf8-44fe-a6b5-c5305ad3e690"; :>> outcome = VerdictKind::pass; :>> judgedAgainst = "60dc411f4858899910a2b83ca9ccb7ef9677435a"; :>> judgedAt = "2026-08-24"; :>> judgedBy = "claudeFable5"; }
    verification armedNotDeclaredCloseOutGate : Test { :>> id = "28f53682-808c-4a0b-a287-59c306c24de7"; :>> title = "Sprint 447 closeOut gate (autonomous, D0049)"; :>> createdAt = "2026-08-24"; :>> createdBy = "claudeFable5"; :>> method = VerificationMethod::inspect; :>> procedureText = "Autonomous closeOut (D0049). issue240 resolved for the two surfaces that made a false positive claim; the third is tracked as dcControlsReportArming rather than silently included; hooksPath restored to .githooks and a standing regression now guards it; validate + all 48 guards + check-engine + rules green."; }
    part armedNotDeclaredCloseOutGateR1 : TestResult { :>> id = "5195aa8e-a500-4e09-ae87-9d7aa2ce316f"; :>> outcome = VerdictKind::pass; :>> judgedAgainst = "60dc411f4858899910a2b83ca9ccb7ef9677435a"; :>> judgedAt = "2026-08-24"; :>> judgedBy = "claudeFable5"; }
    verification armedNotDeclaredRetroGate : Test { :>> id = "b440e841-ea7d-455c-86e6-14c2b0d74aa1"; :>> title = "Sprint 447 retro gate (autonomous, D0049)"; :>> createdAt = "2026-08-24"; :>> createdBy = "claudeFable5"; :>> method = VerificationMethod::analyze; :>> procedureText = "Autonomous retro (D0049). AVOIDABLE-ISSUE SCAN under rcRecurrence: (1) the stale-binary class recurred AGAIN - the release build reported os error 5 (Access denied, keel.exe held) and left the old exe, and I caught it only because the freshness grep is now habit; the recurring cause is that a build can fail to relink while the surrounding shell pipeline still exits 0. (2) A control evaluation that mutates the thing under test must restore it: this defect is almost certainly residue from a red-team probe of mine that set hooksPath to a null device to simulate a bypass; the probe harness needs the restore in a trap, not at the end of a happy path. WELL: the panel's mechanisms lens found a live, severe, self-inflicted enforcement hole that three of my own computed surfaces were reporting as healthy, and the fix generalised into the honest-surface shape (report the reason, never a bare boolean) that issue239 will widen across the CLI. Estimate 2 pts, delivered 2."; }
    part armedNotDeclaredRetroGateR1 : TestResult { :>> id = "4bb4be33-5403-4719-9956-1f827d9ca93e"; :>> outcome = VerdictKind::pass; :>> judgedAgainst = "60dc411f4858899910a2b83ca9ccb7ef9677435a"; :>> judgedAt = "2026-08-24"; :>> judgedBy = "claudeFable5"; }
}
