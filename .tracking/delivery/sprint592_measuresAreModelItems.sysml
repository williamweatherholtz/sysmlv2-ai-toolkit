// ProjectDeliveryS592 — Sprint 592: a measure becomes a model item that a verification case can verify, and the analysis gains the element type its own scenarios needed. EXECUTE. 1 pts.
package ProjectDeliveryS592 {
    private import EngineElement::*;
    private import EngineWork::*;
    private import EngineVerification::*;
    private import EngineRelationships::*;

    #CharteredBy dependency from measuresAreModelItemsStory to d0363;

    part measuresAreModelItemsStory : Story {
        :>> id = "89e2f061-8b20-4a00-932a-6ebac61bd436";
        :>> title = "Sprint 592: a measure becomes a model item that a verification case can verify, and the analysis gains the element type its own scenarios needed (1 pts)";
        :>> createdAt = "2026-09-07"; :>> createdBy = "claudeOpus5"; :>> kind = WorkKind::code; :>> priority = WorkPriority::p0; :>> owner = "claudeOpus5"; :>> estimatedPoints = 1;
    }

    action def DeliveryRunS592 {
        action storyMeasuresAreModelItems;
        verification storyMeasuresAreModelItemsDoD : Test { :>> id = "c4a983e5-a0bb-4005-ab78-4bf987248187"; :>> method = VerificationMethod::test; :>> procedureText = "DELIVERED BACKLOG ITEMS: dcInstrumentsAreVerifiableElements (resolves issue395) and the schema half of dcStpaStepTwoIsComplete (issue394's fifth element type). Chartered by D0363, authorised by the owner on 2026-09-07: 'we can change schema. proceed'. DONE: the frozen safety schema gains OtherInputOutput with a direction and an external party - the STPA Handbook's fifth element type, page 25, named for the source's own term - and Sensor gains mechanism, measures, determinism as a four-value enum, reading, and producesFeedback, so a measure has model identity and a verify edge can reach it. The twenty measures move from a contract file into the model as twenty Feedback and twenty Sensor items, GENERATED from the manifest rather than retyped, and .engine/contracts/instruments.toml is DELETED rather than kept as a second home. Guard 65 holds the tree against Sensor.mechanism both ways; a deliberate exclusion is argued in the excluded file itself. The computed control structure, guard 65 and the facts script all read the model. VERIFIED: the JVM kernel validator passes 20/20 schema files INCLUDING schema/safety/stpa.sysml, which is the frozen-schema requirement rather than a nicety; instruments_declared_catches_it 4/4 after being rewritten for items; keel suite 569 passed 0 failed (receipt 622c510b3e28); validate 673; check-engine clean; guard ALL PASS at 65; clippy -D warnings clean."; }
        // RAN: kernel validate_schema.py 20/20 including schema/safety/stpa.sysml; keel suite 569 passed 0 failed (receipt 622c510b3e28); instruments_declared_catches_it 4/4; validate 673; guard ALL PASS (65); clippy clean
        part storyMeasuresAreModelItemsDoDR1 : TestResult { :>> id = "39358953-4d5c-4a2e-96c4-699d58505b78"; :>> outcome = VerdictKind::pass; :>> judgedAgainst = "HEAD"; :>> judgedAt = "2026-09-07"; :>> judgedBy = "claudeOpus5"; }
    }

    verification measuresAreModelItemsRefineGate : Test { :>> id = "33c78d6c-8aad-4235-8b77-97c3ecb669dc"; :>> title = "Sprint 592 refine gate (DoR)"; :>> createdAt = "2026-09-07"; :>> createdBy = "claudeOpus5"; :>> method = VerificationMethod::inspect; :>> procedureText = "READY: the owner authorised the schema change after asking whether assessment belonged in metadata - it did not - and the brief had priced both additions as one review. The one design question was whether determinism should be a string or an enum, and it is an enum because its four values ARE the point: a run of a tree-deterministic measure is a measurement and a run of a stochastic one is a sample, and free text there would let a reader interpret what should be read."; }
    // RAN: kernel 20/20; keel suite 569/0 (622c510b3e28)
    part measuresAreModelItemsRefineGateR1 : TestResult { :>> id = "19ff4d51-8630-4234-8ed1-8a1db397c861"; :>> outcome = VerdictKind::pass; :>> judgedAgainst = "HEAD"; :>> judgedAt = "2026-09-07"; :>> judgedBy = "claudeOpus5"; }
    verification measuresAreModelItemsStandupGate : Test { :>> id = "3faedb99-b726-4f43-a058-95a8fa5215ed"; :>> title = "Sprint 592 standup gate"; :>> createdAt = "2026-09-07"; :>> createdBy = "claudeOpus5"; :>> method = VerificationMethod::inspect; :>> procedureText = "THE ACCEPTANCE IS REFUSED AND THAT IS CORRECT. Their words authorised the WORK - 'we can change schema. proceed' - and the read-back check will not bind those words to d0363 because they name no record. The schema is changed, gated and green; the signature is not recorded, and I am not working around the control that says so."; }
    // RAN: kernel 20/20; keel suite 569/0 (622c510b3e28)
    part measuresAreModelItemsStandupGateR1 : TestResult { :>> id = "74de5ee0-c24f-4a38-ba7b-8c472f24ce23"; :>> outcome = VerdictKind::pass; :>> judgedAgainst = "HEAD"; :>> judgedAt = "2026-09-07"; :>> judgedBy = "claudeOpus5"; }
    verification measuresAreModelItemsImplementGate : Test { :>> id = "afd237bb-d0ef-40f4-b0de-f157f0d91508"; :>> title = "Sprint 592 implement gate"; :>> createdAt = "2026-09-07"; :>> createdBy = "claudeOpus5"; :>> method = VerificationMethod::test; :>> procedureText = "RAN: the handbook read at pp.22-26 to get the element set from the source rather than our summary; the schema edited and put through the JVM kernel lane, 20/20; twenty measures generated into the model from the manifest so the two could not disagree; the view, the guard and the facts script rewired to the model; the contract file deleted; three exclusions moved into the files they excuse; the proof test rewritten to author a Sensor and shown 4/4; keel suite 569/0."; }
    // RAN: kernel 20/20; keel suite 569/0 (622c510b3e28)
    part measuresAreModelItemsImplementGateR1 : TestResult { :>> id = "f7100818-deff-4940-acf0-6fab65791315"; :>> outcome = VerdictKind::pass; :>> judgedAgainst = "HEAD"; :>> judgedAt = "2026-09-07"; :>> judgedBy = "claudeOpus5"; }
    verification measuresAreModelItemsReviewGate : Test { :>> id = "2a6b9337-92c2-4ed1-846d-a48e1beee1fa"; :>> title = "Sprint 592 review gate — three passes per D0172"; :>> createdAt = "2026-09-07"; :>> createdBy = "claudeOpus5"; :>> method = VerificationMethod::inspect; :>> procedureText = "THREE PASSES. (1) IS THE SCHEMA CHANGE ACTUALLY VALID SYSML: yes, and this is the pass that matters - the Rust parser accepting it proves nothing (issue097), so the kernel ran and passed 20/20. (2) DID ANYTHING KEEP THE OLD SOURCE: no - the contract file is deleted, the migrate exclusion for it is removed rather than left as a tombstone, and the facts script counts model items; the historical records that mention it are left exactly as written, because rewriting them would falsify the sequence. (3) DID THE CONTROLS CATCH ME: twice - the keystone lock refused the turn because the governing Decision was untracked while the deletion was staged, which is the lock working exactly as designed, and guard 65 named three files whose exclusions had lived in the deleted manifest."; }
    // RAN: kernel 20/20; keel suite 569/0 (622c510b3e28)
    part measuresAreModelItemsReviewGateR1 : TestResult { :>> id = "c05b75dc-526a-4caf-b389-f010ceefa0ca"; :>> outcome = VerdictKind::pass; :>> judgedAgainst = "HEAD"; :>> judgedAt = "2026-09-07"; :>> judgedBy = "claudeOpus5"; }
    verification measuresAreModelItemsCloseOutGate : Test { :>> id = "00db0892-01a8-475e-af13-b63f6a104579"; :>> title = "Sprint 592 closeOut gate (autonomous, D0049)"; :>> createdAt = "2026-09-07"; :>> createdBy = "claudeOpus5"; :>> method = VerificationMethod::inspect; :>> procedureText = "CLOSED. A measure is now a thing that can be verified rather than a thing that can only be described, and the analysis can express an input nobody controls."; }
    // RAN: kernel 20/20; keel suite 569/0 (622c510b3e28)
    part measuresAreModelItemsCloseOutGateR1 : TestResult { :>> id = "f161c614-6b56-4497-a926-727a4cce7b07"; :>> outcome = VerdictKind::pass; :>> judgedAgainst = "HEAD"; :>> judgedAt = "2026-09-07"; :>> judgedBy = "claudeOpus5"; }
    verification measuresAreModelItemsRetroGate : Test { :>> id = "61c62a81-ba8a-4fae-82c9-8778f28d0481"; :>> title = "Sprint 592 retro gate (autonomous, D0049)"; :>> createdAt = "2026-09-07"; :>> createdBy = "claudeOpus5"; :>> method = VerificationMethod::analyze; :>> procedureText = "AVOIDABLE-ISSUE SCAN HELD. Already tracked, no new item: issue394 keeps its open half (actuators are zero, four controllers have no process model), and issue395 is resolved by this. The avoidable one is mine and it is the third of its kind today: my patch script for the facts file fell through to an append when its anchor did not match, which put the new computation AFTER the serialisation, so the script ran clean and silently omitted everything it had just computed - visible only because I read the values back. A patch that cannot find its anchor must fail, not append; that is the same class as a control that passes while blind, and it is worth carrying rather than filing, because the fix is a habit no guard can hold."; }
    // RAN: kernel 20/20; keel suite 569/0 (622c510b3e28)
    part measuresAreModelItemsRetroGateR1 : TestResult { :>> id = "90c6eaef-dc6c-4c46-aa0c-4bd8f83de04c"; :>> outcome = VerdictKind::pass; :>> judgedAgainst = "HEAD"; :>> judgedAt = "2026-09-07"; :>> judgedBy = "claudeOpus5"; }
}
