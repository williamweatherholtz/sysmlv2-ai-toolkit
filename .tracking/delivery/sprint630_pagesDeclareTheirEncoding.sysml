// ProjectDeliveryS630 — Sprint 630: Sprint 630: A published page declares its encoding where a guessing host looks, and the executive-brief checker refuses one that does not (dcPagesDeclareTheirEncoding, issue401, D0409). EXECUTE. 2 pts.. EXECUTE. 2 pts.
package ProjectDeliveryS630 {
    private import EngineElement::*;
    private import EngineWork::*;
    private import EngineVerification::*;
    private import EngineRelationships::*;

    #CharteredBy dependency from pagesDeclareTheirEncodingStory to d0409;

    part pagesDeclareTheirEncodingStory : Story {
        :>> id = "1886bca1-81b9-4602-bcaa-9a7d797926a0";
        :>> title = "Sprint 630: Sprint 630: A published page declares its encoding where a guessing host looks, and the executive-brief checker refuses one that does not (dcPagesDeclareTheirEncoding, issue401, D0409). EXECUTE. 2 pts. (2 pts)";
        :>> createdAt = "2026-09-09"; :>> createdBy = "claudeOpus5"; :>> kind = WorkKind::code; :>> priority = WorkPriority::p0; :>> owner = "claudeOpus5"; :>> estimatedPoints = 2;
    }

    action def DeliveryRunS630 {
        action storyPagesDeclareTheirEncoding;
        verification storyPagesDeclareTheirEncodingDoD : Test { :>> id = "6945ce77-621e-47bf-b66a-0cda0e3a2364"; :>> method = VerificationMethod::test; :>> procedureText = "DELIVERED (dcPagesDeclareTheirEncoding, resolves issue401 through that item): scripts/check_templates.py check_brief gains clause 0 - a <meta charset=utf-8> (any quoting or case, or the http-equiv form) within the first 1024 bytes of the raw file, the browsers' prescan window - refusing the page otherwise and naming the mojibake it prevents; CHARSET_META is the pattern; _brief_fixture declares the charset by default and takes charset=False; the self-test carries three cases (no declaration refused, declaration at byte ~1100 refused, http-equiv passing), 18 to 21. SKILL.md 2.2 states the rule; D0409 is recorded proposed under --process-change with NOT A FORK stated. The condition that produced the defect was reproduced once: a local HTTP server sending text/html with no charset served a constructed no-declaration page (decoded windows-1252, em dash rendered as three characters in the screenshot) and the tabbed brief (decoded UTF-8, clean); the probe is not kept, its two cases are named in the backlog DoD result."; }
        // RAN: python scripts/check_templates.py --self-test -> pass 21/21 (no charset refused; charset past the first 1024 bytes refused; http-equiv passes); --brief decision-brief.13b.html -> no clause-0 finding; nocharset_host.py -> positive windows-1252 mojibake, brief UTF-8 clean; D0409 recorded proposed; dcPagesDeclareTheirEncoding DoD stamped
        part storyPagesDeclareTheirEncodingDoDR1 : TestResult { :>> id = "2df3d6e8-99b9-43a7-852d-7cb332313ec5"; :>> outcome = VerdictKind::pass; :>> judgedAgainst = "07d7601"; :>> judgedAt = "2026-09-09"; :>> judgedBy = "claudeOpus5"; }
    }

    verification pagesDeclareTheirEncodingRefineGate : Test { :>> id = "e97629bf-6a4a-40f7-b70d-e937d166c84f"; :>> title = "Sprint 630 refine gate (DoR)"; :>> createdAt = "2026-09-09"; :>> createdBy = "claudeOpus5"; :>> method = VerificationMethod::inspect; :>> procedureText = "Definition of Ready: dcPagesDeclareTheirEncoding at the head of keel whats-next . after 07d7601; its DoD names the three verifications (checker refuses a constructed page, the brief passes, an image read from a no-charset host); builders since 2026-09-08 already emit the meta, so the scope is the checker clause, the contract text and the probe; 2 points - one checker clause with cases, one Decision, one skill bullet."; }
    // RAN: keel whats-next . at 07d7601: dcPagesDeclareTheirEncoding at the head; grep charset scripts/check_templates.py -> 0 sites before, 7 builders under scripts/exec_brief/ emit the meta since 2026-09-08; 2 points
    part pagesDeclareTheirEncodingRefineGateR1 : TestResult { :>> id = "27956fbc-876e-4864-a340-00b0396427aa"; :>> outcome = VerdictKind::pass; :>> judgedAgainst = "07d7601"; :>> judgedAt = "2026-09-09"; :>> judgedBy = "claudeOpus5"; }
    verification pagesDeclareTheirEncodingStandupGate : Test { :>> id = "8ba934bf-4622-48ec-9dd2-bf41ca74ddfb"; :>> title = "Sprint 630 standup gate"; :>> createdAt = "2026-09-09"; :>> createdBy = "claudeOpus5"; :>> method = VerificationMethod::inspect; :>> procedureText = "No blocker. The one judgment the DoD asked for - entities versus a declaration - is settled by the tree: seven builders already declare the charset, so entities would be a second mechanism; stated as NOT A FORK in D0409."; }
    // RAN: no blocker; the entities-vs-declaration weighing settled by the seven builders already declaring - NOT A FORK stated in D0409
    part pagesDeclareTheirEncodingStandupGateR1 : TestResult { :>> id = "10eb0bbf-a753-4b9c-be36-133966013edd"; :>> outcome = VerdictKind::pass; :>> judgedAgainst = "07d7601"; :>> judgedAt = "2026-09-09"; :>> judgedBy = "claudeOpus5"; }
    verification pagesDeclareTheirEncodingImplementGate : Test { :>> id = "e2973789-4d02-4d0a-bdab-53e1ce6a883f"; :>> title = "Sprint 630 implement gate"; :>> createdAt = "2026-09-09"; :>> createdBy = "claudeOpus5"; :>> method = VerificationMethod::test; :>> procedureText = "python scripts/check_templates.py --self-test -> pass, 21 of 21; --brief decision-brief.13b.html -> 3 findings, all D0404-D0406 clauses, none from clause 0; nocharset_host.py served both pages from a no-charset host: positive characterSet=windows-1252 with visible mojibake, brief characterSet=UTF-8 clean; D0409 recorded proposed (process-change, OUTSIDE standing consent per D0337); keel sync-claude 46/46."; }
    // RAN: check_templates --self-test 21/21; --brief 13b.html 3 findings none from clause 0; nocharset_host.py positive characterSet=windows-1252 (screenshot shows the em dash as three characters), brief characterSet=UTF-8 clean; record decision --from d0409.md --process-change -> D0409 proposed, OUTSIDE standing consent (D0337); sync-claude 46/46
    part pagesDeclareTheirEncodingImplementGateR1 : TestResult { :>> id = "2596710c-2565-4b9c-ab14-58ed963b3792"; :>> outcome = VerdictKind::pass; :>> judgedAgainst = "07d7601"; :>> judgedAt = "2026-09-09"; :>> judgedBy = "claudeOpus5"; }
    verification pagesDeclareTheirEncodingReviewGate : Test { :>> id = "9317729b-4638-4cad-b6e9-8809f2136c83"; :>> title = "Sprint 630 review gate — three passes per D0172"; :>> createdAt = "2026-09-09"; :>> createdBy = "claudeOpus5"; :>> method = VerificationMethod::inspect; :>> procedureText = "Three passes per D0172: (1) the clause reads the raw bytes, not the parsed markup, because the host that fails has parsed nothing - and the 1024-byte boundary is a tested case, not a comment; (2) the fixture's default gained the declaration so the eighteen prior cases still exercise what they exercised, and the three new ones each name a distinct condition; (3) SKILL.md 2.2, D0409 and the clause comment state one rule in the same words, and the .claude rendering is synced."; }
    // RAN: three passes: clause reads raw bytes not parsed markup and the 1024 boundary is a tested case; fixture default gained the meta so the 18 prior cases exercise what they did; SKILL.md 2.2, D0409 and the clause comment state one rule, .claude rendering synced
    part pagesDeclareTheirEncodingReviewGateR1 : TestResult { :>> id = "1369538c-93de-4a4c-b795-b6de50133861"; :>> outcome = VerdictKind::pass; :>> judgedAgainst = "07d7601"; :>> judgedAt = "2026-09-09"; :>> judgedBy = "claudeOpus5"; }
    verification pagesDeclareTheirEncodingCloseOutGate : Test { :>> id = "a6ba69fc-8631-4501-92f6-d5fbdaa3d191"; :>> title = "Sprint 630 closeOut gate (autonomous, D0049)"; :>> createdAt = "2026-09-09"; :>> createdBy = "claudeOpus5"; :>> method = VerificationMethod::inspect; :>> procedureText = "keel validate . clean (715 files), keel check-engine . clean, keel gate --fast clean, keel guard . 64 non-blocking warnings all pre-existing classes and no FAIL line except the D0064 coverage this sprint supplies; dcPagesDeclareTheirEncoding DoD stamped at 07d7601 with the two probe cases named."; }
    // RAN: keel validate . 715 clean; check-engine clean; gate --fast clean; guard . no FAIL line once this sprint covers the done item (D0064); backlog DoD stamped at 07d7601 naming both probe cases
    part pagesDeclareTheirEncodingCloseOutGateR1 : TestResult { :>> id = "1be3782d-1d5f-4353-be21-1c4b7b52d53f"; :>> outcome = VerdictKind::pass; :>> judgedAgainst = "07d7601"; :>> judgedAt = "2026-09-09"; :>> judgedBy = "claudeOpus5"; }
    verification pagesDeclareTheirEncodingRetroGate : Test { :>> id = "3aafa1cd-d802-4a09-9d3a-ee40a5c5d26e"; :>> title = "Sprint 630 retro gate (autonomous, D0049)"; :>> createdAt = "2026-09-09"; :>> createdBy = "claudeOpus5"; :>> method = VerificationMethod::analyze; :>> procedureText = "Avoidable-issue scan: the defect class was a page reviewed where it looked right and read where it looked wrong; the fix that closes the class is a check that reads the file the way the failing host does, which no visual review from the publisher can substitute for. No new item: the finding is already tracked as issue401, whose resolver dcPagesDeclareTheirEncoding is done in this sprint. The probe was one-time and stays one-time because the checker clause is the permanent control and a host-serving Sensor would measure the browser, not the page."; }
    // RAN: avoidable-issue scan: a page reviewed where it looked right and read where it looked wrong; the closing control reads the file as the failing host does; no new issue - issue401 is the tracked item and its resolver is done; the probe stays one-time, the clause is the permanent control
    part pagesDeclareTheirEncodingRetroGateR1 : TestResult { :>> id = "157fa1e1-2ab8-4ba1-88fd-eb456b4eb666"; :>> outcome = VerdictKind::pass; :>> judgedAgainst = "07d7601"; :>> judgedAt = "2026-09-09"; :>> judgedBy = "claudeOpus5"; }
}
