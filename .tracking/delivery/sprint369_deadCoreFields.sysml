// ProjectDeliveryS369 — Sprint 369: hardening round 9, the last of the series. One finding, and it is
// the first one I cannot clear myself. EXECUTE. 3 pts.
package ProjectDeliveryS369 {
    private import EngineElement::*;
    private import EngineWork::*;
    private import EngineVerification::*;
    private import EngineRelationships::*;

    #CharteredBy dependency from deadFieldsStory to d0170;

    part deadFieldsStory : Story {
        :>> id = "0d8006c0-0814-66c0-9b3e-0000003006c0";
        :>> title = "Sprint 369: a schema field declared on 370 items and set on none — and a finding left OPEN (3 pts)";
        :>> createdAt = "2026-08-20"; :>> createdBy = "claudeOpus5"; :>> kind = WorkKind::research; :>> priority = WorkPriority::p0; :>> owner = "claudeOpus5"; :>> estimatedPoints = 3;
    }

    action def DeliveryRunS369 {
        action storyDeadFields;
        verification storyDeadFieldsDoD : Test { :>> id = "0d8006c1-0814-66c1-9b3e-0000003006c1"; :>> method = VerificationMethod::test; :>> procedureText = "DELIVERED BACKLOG ITEMS: dcDeadCoreFields. Records issue186 and proposes D0170. THE FINDING: of 88 attributes in schema/core, five are never set. Two are accounted for (actualHours demoted by issue175, safetyLevel in the optional safety schema); `impact` and `reasonForChange` sit on ChangeRequest, which has exactly THREE instances. What survives is `actualPoints` - declared on Story, which has 370 instances, set on NONE of them, and read by no Rust code, while `estimatedPoints` is set on all 370. THIS PASS ALSO CAME BACK CLEAN ON EVERYTHING ELSE, recorded as plainly as the finding: the console's 17 getElementById targets all exist in the markup and its one inline handler is defined; conformanceIndicator reads 100.00 against a 2026-08-14 measurement, which is HONEST rather than suspicious - the lane measures whether current instance files use constructs the kernel accepts, while issue097 is about the risk of ADOPTING a rejected one. THE FINDING IS LEFT OPEN. schema/core is frozen (invariant 5) so retiring a field needs a signature, and it cannot be filled retroactively without fabricating 370 measurements. validate 401 clean; check-engine clean; 38 guards ALL PASS; 202 tests; clippy clean."; }
        part storyDeadFieldsDoDR1 : TestResult { :>> id = "0d8006c2-0814-66c2-9b3e-0000003006c2"; :>> outcome = VerdictKind::pass; :>> judgedAgainst = "add755c"; :>> judgedAt = "2026-08-20"; :>> judgedBy = "claudeOpus5"; }
    }

    verification dfRefineGate : Test { :>> id = "0d8006c3-0814-66c3-9b3e-0000003006c3"; :>> title = "Sprint 369 refine gate (DoR)"; :>> createdAt = "2026-08-20"; :>> createdBy = "claudeOpus5"; :>> method = VerificationMethod::inspect; :>> procedureText = "DoR. Pass 9 swept the surfaces nothing had examined: console JS integrity (the class behind issue152, where a script that throws leaves every later listener unregistered), the SysML kernel conformance number, and schema attribute liveness. Two of the three came back clean. The third produced a finding I corrected TWICE while writing it, which is why the refine gate says so - the first draft named the wrong owning type, and the second was about to claim 368 sprints recorded no reason for any change when the type in question has three instances. estimatedPoints=3."; }
    part dfRefineGateR1 : TestResult { :>> id = "0d8006c4-0814-66c4-9b3e-0000003006c4"; :>> outcome = VerdictKind::pass; :>> judgedAgainst = "add755c"; :>> judgedAt = "2026-08-20"; :>> judgedBy = "claudeOpus5"; }

    verification dfStandupGate : Test { :>> id = "0d8006c5-0814-66c5-9b3e-0000003006c5"; :>> title = "Sprint 369 standup gate"; :>> createdAt = "2026-08-20"; :>> createdBy = "claudeOpus5"; :>> method = VerificationMethod::inspect; :>> procedureText = "Approach: check the owning TYPE's instance count before calling an unset field a systemic gap. That one question turned a dramatic finding into an accurate small one, and it is the check the three earlier overstatements in this series (13-that-was-3, nine-that-was-three) were all missing - each of them read a count without asking what the count was OF. No blockers."; }
    part dfStandupGateR1 : TestResult { :>> id = "0d8006c6-0814-66c6-9b3e-0000003006c6"; :>> outcome = VerdictKind::pass; :>> judgedAgainst = "add755c"; :>> judgedAt = "2026-08-20"; :>> judgedBy = "claudeOpus5"; }

    verification dfImplementGate : Test { :>> id = "0d8006c7-0814-66c7-9b3e-0000003006c7"; :>> title = "Sprint 369 implement gate"; :>> createdAt = "2026-08-20"; :>> createdBy = "claudeOpus5"; :>> method = VerificationMethod::test; :>> procedureText = "NOTHING WAS IMPLEMENTED AND THAT IS THE DELIVERABLE. `schema/core` is frozen under invariant 5, so retiring `actualPoints` needs an explicit signature, and filling it retroactively would mean inventing 370 measurements that were never taken - precisely the fabrication guard 36 exists to catch. So D0170 is PROPOSED with both options argued, and issue186 stays OPEN. THE ARGUMENT I WOULD DEFEND HARDEST is in D0170 and it is against filling the field: an AI writing `actualPoints` minutes after `estimatedPoints`, with no independent measurement in between, is not producing feedback - the same judgment made both numbers, so they will agree, and the agreement will read as calibration. `actualHours` at least had a clock behind it in principle. This has nothing. Filling it would be worse than leaving it visibly empty. LEAVING THE ISSUE OPEN IS THE POINT. Closing it as `documented` is the exact move this series kept finding and rejecting - D0169 documented a limitation and shipped a false green one sprint later, which became issue183. A finding I cannot clear stays uncleared, and eight of nine cleared with one honestly open is a better record than nine of nine with one closed on a technicality."; }
    part dfImplementGateR1 : TestResult { :>> id = "0d8006c8-0814-66c8-9b3e-0000003006c8"; :>> outcome = VerdictKind::pass; :>> judgedAgainst = "add755c"; :>> judgedAt = "2026-08-20"; :>> judgedBy = "claudeOpus5"; }

    verification dfReviewGate : Test { :>> id = "0d8006c9-0814-66c9-9b3e-0000003006c9"; :>> title = "Sprint 369 review gate"; :>> createdAt = "2026-08-20"; :>> createdBy = "claudeOpus5"; :>> method = VerificationMethod::inspect; :>> procedureText = "Reviewed, and this gate reviews the SERIES rather than only the sprint. NINE PASSES, 16 FINDINGS, 15 CLEARED, 12 PERMANENT CONTROLS. The human's claim was that keel is not doing what it says and half-baked implementations are loose in the model. SUPPORTED, and more strongly than I expected: 47% of subcommands were undiscoverable, three guards reported violations against a zero scan, five write paths fabricated a provenance date, every model write truncated the truth first, concurrent writers silently lost facts, and `keel init --help` scaffolded an engine into a directory named `--help` which I then committed. REFUTED: every command the docs name resolves, guard documentation matches the live set exactly, all declared views compute, and the unused schema is the optional safety package. The engine does MORE than it says, not less. THE PATTERN UNDER MOST OF IT is one defect wearing many costumes - a surface that does not declare or defend its own boundary, always permissive by default, with the strict behaviour a separate act nobody was forced to perform. FIVE OF THE SIXTEEN FINDINGS WERE IN CODE WRITTEN DURING THE SERIES, and three findings were overstated before being corrected in place. Both numbers are in the record on purpose."; }
    part dfReviewGateR1 : TestResult { :>> id = "0d8006ca-0814-66ca-9b3e-0000003006ca"; :>> outcome = VerdictKind::pass; :>> judgedAgainst = "add755c"; :>> judgedAt = "2026-08-20"; :>> judgedBy = "claudeOpus5"; }

    verification dfCloseOutGate : Test { :>> id = "0d8006cb-0814-66cb-9b3e-0000003006cb"; :>> title = "Sprint 369 closeOut gate (autonomous, D0049)"; :>> createdAt = "2026-08-20"; :>> createdBy = "claudeOpus5"; :>> method = VerificationMethod::inspect; :>> procedureText = "Autonomous closeOut (D0049). issue186 recorded and left OPEN; D0170 proposed with both options argued. The hardening series is complete at nine passes. TWO DECISIONS AWAIT A SIGNATURE from this series - D0169 (the audit measures itself, and the four contracts and controls under it) and D0170 (retire or fill actualPoints) - plus D0167 and D0168 from earlier in the session. validate 401 clean; check-engine clean; 38 guards ALL PASS; 202 tests; clippy clean."; }
    part dfCloseOutGateR1 : TestResult { :>> id = "0d8006cc-0814-66cc-9b3e-0000003006cc"; :>> outcome = VerdictKind::pass; :>> judgedAgainst = "add755c"; :>> judgedAt = "2026-08-20"; :>> judgedBy = "claudeOpus5"; }

    verification dfRetroGate : Test { :>> id = "0d8006cd-0814-66cd-9b3e-0000003006cd"; :>> title = "Sprint 369 retro gate (autonomous, D0049)"; :>> createdAt = "2026-08-20"; :>> createdBy = "claudeOpus5"; :>> method = VerificationMethod::analyze; :>> procedureText = "Autonomous retro (D0049) under D0131's retroTrack, covering the sprint and closing the series. WELL: (1) the owning type's instance count was checked BEFORE the finding was written, which turned a dramatic claim into an accurate small one - the check all three earlier overstatements were missing; (2) the finding was left OPEN rather than closed as documented, which is the discipline the series itself kept finding violations of; (3) the argument against filling `actualPoints` is about the independence of the measurement rather than the cost of the work, which is the honest objection; (4) two clean sweeps were recorded as plainly as the finding, so a successor knows the console's DOM references and the conformance number have been checked. AVOIDABLE-ISSUE: I corrected this one finding TWICE inside a single sprint - wrong owning type, then a near-miss claim about 368 sprints. THE SERIES RULE, earned four times: a count is not a finding until you know what it is a count OF. Three overstatements and one near-miss all had that same shape, and the near-miss is the only one I caught before writing it down. SERIES-LEVEL OBSERVATION worth more than any single finding: 12 of the 16 findings were caught by a CONTROL or a MEASUREMENT rather than by reading, and in three sprints running a text-level control found more instances than I had fixed by hand. My reading of this codebase is systematically less reliable than a cheap mechanical check over it, and the correct response is to keep writing the check first. Estimate 3 pts, delivered as one finding, one proposed Decision, and two clean sweeps."; }
    part dfRetroGateR1 : TestResult { :>> id = "0d8006ce-0814-66ce-9b3e-0000003006ce"; :>> outcome = VerdictKind::pass; :>> judgedAgainst = "add755c"; :>> judgedAt = "2026-08-20"; :>> judgedBy = "claudeOpus5"; }
}
