// ProjectDeliveryS240 — Sprint 240: viewerInProgramEdit — complete the in-program disciplined write
// surface (N-16): supersede-edge authoring + inline guard-rejection feedback + D0108 conflict detection.
// The LAST viewer item. Satisfies srViewerInProgramEdit. EXECUTE. 3 pts.
package ProjectDeliveryS240 {
    private import EngineElement::*;
    private import EngineWork::*;
    private import EngineVerification::*;
    private import EngineRelationships::*;

    #CharteredBy dependency from viewerInProgramEditStory to srViewerInProgramEdit;

    part viewerInProgramEditStory : Story {
        :>> id = "63940516-2c7d-4e8f-c240-51627384c001";
        :>> title = "Sprint 240: viewerInProgramEdit (3 pts) - in-program disciplined writes: supersede-edge, inline guard feedback, conflict detection";
        :>> createdAt = "2026-07-16"; :>> createdBy = "wweatherholtz"; :>> kind = WorkKind::code; :>> priority = WorkPriority::p2; :>> owner = "claudeOpus"; :>> estimatedPoints = 3;
    }

    action def DeliveryRunS240 {
        action storyViewerInProgramEdit;
        verification storyViewerInProgramEditDoD : Test { :>> id = "63940516-2c7d-4e8f-c240-51627384c002"; :>> method = VerificationMethod::demo; :>> procedureText = "Satisfies srViewerInProgramEdit (N-16, human-clarified: modify via keel PROCESSES, not rogue edits). KEEL (v1.12.0, ee0fc87): write::append_marker_edge generalises append_resolves_edge to any typed marker; three endpoints — POST /api/edge (author a whitelisted marker edge, EDGE_MARKER_WHITELIST={Supersede,DependsOn,DerivedFrom,Covers,Resolves,Dispositions}, identifier-shaped, append-only, idempotent, never auto-commits); GET /api/check (run validate + all GUARD_NAMES against the working tree -> {ok,parseErrors,blocking,warnings}); GET /api/fingerprint (model content fingerprint). VIEWER (sysmlv2-viewer@d755597): (1) SUPERSEDE — from a Need/SystemRequirement/Decision detail, a 'Supersede' button (gated on the advertised /api/edge endpoint) records a superseding Decision via /api/decision then authors a #Supersede edge via /api/edge (§2.4 — scope = a superseding Decision, not a deletion). (2) INLINE GUARD FEEDBACK — every write runs /api/check and shows the honest verdict; a would-be-rejected write is surfaced, not silent (D0098). (3) D0108 CONFLICT — captures the fingerprint when a write form opens, re-checks at submit, flags a concurrent change before committing. This completes the disciplined write surface (record a Decision was already delivered; disposition/apply-review + gate-accept exist via the review queue). VERIFY (demo, live, keel API v1.12.0): end-to-end supersede recorded D0126(proposed) + '#Supersede d0126 -> nViewerEncodingViewpoints' + inline 'guards pass (5 warning-level)'; stale-fingerprint conflict detected, matching-fingerprint clean; /api/edge whitelist rejects non-permitted markers/traversal-paths/non-identifiers; edge idempotent (no dup, git clean). Throwaway test Decision deleted. clippy + validate + guard + check-engine green."; }
        part storyViewerInProgramEditDoDR1 : TestResult { :>> id = "63940516-2c7d-4e8f-c240-51627384c003"; :>> outcome = VerdictKind::pass; :>> judgedAgainst = "ee0fc87"; :>> judgedAt = "2026-07-16"; :>> judgedBy = "claudeOpus"; }
    }

    verification ipeRefineGate : Test { :>> id = "63940516-2c7d-4e8f-c240-51627384c004"; :>> title = "Sprint 240 refine gate (DoR)"; :>> createdAt = "2026-07-16"; :>> createdBy = "claudeOpus"; :>> method = VerificationMethod::inspect; :>> procedureText = "DoR: record-Decision was already delivered; the remaining gaps are supersede-edge authoring, inline guard-rejection surfacing, and D0108 conflict detection. Build the keel edge/check/fingerprint endpoints + wire the viewer. #CharteredBy srViewerInProgramEdit. estimatedPoints=3. DoR met."; }
    part ipeRefineGateR1 : TestResult { :>> id = "63940516-2c7d-4e8f-c240-51627384c005"; :>> outcome = VerdictKind::pass; :>> judgedAgainst = "ee0fc87"; :>> judgedAt = "2026-07-16"; :>> judgedBy = "claudeOpus"; }
    verification ipeStandupGate : Test { :>> id = "63940516-2c7d-4e8f-c240-51627384c006"; :>> title = "Sprint 240 standup gate"; :>> createdAt = "2026-07-16"; :>> createdBy = "claudeOpus"; :>> method = VerificationMethod::inspect; :>> procedureText = "Approach: keel — generalise the resolves-edge helper to append_marker_edge; add /api/edge (whitelisted marker), /api/check (validate+guards), /api/fingerprint; advertise in /api/version (v1.12.0). Viewer — reuse the Decision dialog for supersede, run /api/check after every write, capture+recheck the fingerprint. No blockers."; }
    part ipeStandupGateR1 : TestResult { :>> id = "63940516-2c7d-4e8f-c240-51627384c007"; :>> outcome = VerdictKind::pass; :>> judgedAgainst = "ee0fc87"; :>> judgedAt = "2026-07-16"; :>> judgedBy = "claudeOpus"; }
    verification ipeImplementGate : Test { :>> id = "63940516-2c7d-4e8f-c240-51627384c008"; :>> title = "Sprint 240 implement gate"; :>> createdAt = "2026-07-16"; :>> createdBy = "claudeOpus"; :>> method = VerificationMethod::demo; :>> procedureText = "keel@ee0fc87 (append_marker_edge + 3 endpoints) + viewer@d755597 (supersede button, inline check, conflict detection) implemented. Live-verified end-to-end (supersede recorded a Decision + #Supersede edge + guards-pass verdict; conflict detected on stale fingerprint; whitelist + idempotency confirmed; throwaway cleaned up). clippy + validate + guard + check-engine green."; }
    part ipeImplementGateR1 : TestResult { :>> id = "63940516-2c7d-4e8f-c240-51627384c009"; :>> outcome = VerdictKind::pass; :>> judgedAgainst = "ee0fc87"; :>> judgedAt = "2026-07-16"; :>> judgedBy = "claudeOpus"; }
    verification ipeReviewGate : Test { :>> id = "63940516-2c7d-4e8f-c240-51627384c00a"; :>> title = "Sprint 240 review gate"; :>> createdAt = "2026-07-16"; :>> createdBy = "claudeOpus"; :>> method = VerificationMethod::inspect; :>> procedureText = "Reviewed. Writes go THROUGH keel processes (record a Decision + typed #Supersede edge, §2.4) — no raw field mutation, no second store, never auto-commits (the human commits). The marker whitelist + identifier-shaping keep the surface disciplined (no free-text injection). Inline /api/check is the same honest-state gate the pre-commit hook runs — a rejected write is surfaced, not faked (D0098). Conflict detection realises D0108 in-program. Clean."; }
    part ipeReviewGateR1 : TestResult { :>> id = "63940516-2c7d-4e8f-c240-51627384c00b"; :>> outcome = VerdictKind::pass; :>> judgedAgainst = "ee0fc87"; :>> judgedAt = "2026-07-16"; :>> judgedBy = "claudeOpus"; }
    verification ipeCloseOutGate : Test { :>> id = "63940516-2c7d-4e8f-c240-51627384c00c"; :>> title = "Sprint 240 closeOut gate (autonomous, D0049)"; :>> createdAt = "2026-07-16"; :>> createdBy = "claudeOpus"; :>> method = VerificationMethod::inspect; :>> procedureText = "Autonomous closeOut (D0049): DoD pass; the in-program disciplined write surface is complete (srViewerInProgramEdit). Self-evidencing. This is the LAST viewer item — the entire keel-viewer line (N-1/N-2/N-6/N-12/N-15/N-16/N-17/N-18) is now delivered."; }
    part ipeCloseOutGateR1 : TestResult { :>> id = "63940516-2c7d-4e8f-c240-51627384c00d"; :>> outcome = VerdictKind::pass; :>> judgedAgainst = "ee0fc87"; :>> judgedAt = "2026-07-16"; :>> judgedBy = "claudeOpus"; }
    verification ipeRetroGate : Test { :>> id = "63940516-2c7d-4e8f-c240-51627384c00e"; :>> title = "Sprint 240 retro gate (autonomous, D0049)"; :>> createdAt = "2026-07-16"; :>> createdBy = "claudeOpus"; :>> method = VerificationMethod::analyze; :>> procedureText = "Autonomous retro (D0049). WELL: generalised the existing resolves-edge helper rather than a bespoke supersede writer (one primitive, whitelisted at the endpoint) — modular, matches the D0124 registry ethos. Reused /api/check = the SAME gates the hook enforces, so inline feedback can't drift from the real gate. Verified end-to-end in-browser and CLEANED UP the throwaway test Decision (no junk in the model). AVOIDABLE-ISSUE SCAN: the viewer's DOMContentLoaded autoconnect still targets the hardcoded default :7777 and logged one benign ERR_CONNECTION_REFUSED before the manual connect — cosmetic, not tracked. LESSON: when a write path exists (append_resolves_edge), generalise it + whitelist at the boundary rather than adding a parallel writer. Estimate 3 pts. The keel-viewer program line is COMPLETE."; }
    part ipeRetroGateR1 : TestResult { :>> id = "63940516-2c7d-4e8f-c240-51627384c00f"; :>> outcome = VerdictKind::pass; :>> judgedAgainst = "ee0fc87"; :>> judgedAt = "2026-07-16"; :>> judgedBy = "claudeOpus"; }
}
