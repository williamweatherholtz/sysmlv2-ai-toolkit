// ProjectDeliveryS515 — Sprint 515: the session's actor reaches the hooks. EXECUTE. 2 pts.
package ProjectDeliveryS515 {
    private import EngineElement::*;
    private import EngineWork::*;
    private import EngineVerification::*;
    private import EngineRelationships::*;

    #CharteredBy dependency from sessionActorStory to d0280;

    part sessionActorStory : Story {
        :>> id = "0e6a9d31-4c72-4b58-a3f0-8b1c5e2d9f47";
        :>> title = "Sprint 515: a session's declared actor is what the hooks see (2 pts)";
        :>> createdAt = "2026-09-01"; :>> createdBy = "claudeOpus5"; :>> kind = WorkKind::code; :>> priority = WorkPriority::p0; :>> owner = "claudeOpus5"; :>> estimatedPoints = 2;
    }

    action def DeliveryRunS515 {
        action storySessionActor;
        verification storySessionActorDoD : Test { :>> id = "1f7bae42-5d83-4c69-b4a1-9c2d6f3e0a58"; :>> method = VerificationMethod::test; :>> procedureText = "DELIVERED BACKLOG ITEMS: dcSessionActorReachesHooks (resolves issue337, which supersedes issue332). THE DEFECT: KEEL_ACTOR is set per command in the session's shell; the Stop hook is spawned by the harness in ITS environment, so actor::resolve fell through to the MACHINE binding - and on a machine two models share, the binding named the other one. 22 edits attributed to the wrong actor, 12 owned items flagged as non-owner edits. The guard's predicate was correct; the identity had no path to it. DONE: a per-session binding at .keel/sessions/<id>/actor, remembered by any command that runs with KEEL_ACTOR, read by resolve between KEEL_ACTOR and the machine binding, keyed by the id the harness gives both sides (CLAUDE_CODE_SESSION_ID in the shell, session_id in every hook payload, which the dispatcher seeds). VERIFY: live, with KEEL_ACTOR unset, keel actor resolves to the session's actor; three unit tests on the pure halves. The ownership entry leaves the D0278 registry in this same commit."; }
        // RAN: env -u KEEL_ACTOR keel actor -> claudeOpus5 (session) not claudeFable5 (machine), read back live; actor::session_binding_tests 3/3; control-defect-registry 2 scanned after the ownership entry was removed
        part storySessionActorDoDR1 : TestResult { :>> id = "208cbf53-6e94-4d70-c5b2-0d3e7a4f1b69"; :>> outcome = VerdictKind::pass; :>> judgedAgainst = "24dcc73"; :>> judgedAt = "2026-09-01"; :>> judgedBy = "claudeOpus5"; }
    }

    verification sessionActorRefineGate : Test { :>> id = "319dc064-7fa5-4e81-d6c3-1e4f8b5a2c7a"; :>> title = "Sprint 515 refine gate (DoR)"; :>> createdAt = "2026-09-01"; :>> createdBy = "claudeOpus5"; :>> method = VerificationMethod::inspect; :>> procedureText = "READY because the rigor panel had already done the hard part - reading actor.rs:97-112 and guards.rs:2498 to establish that the guard was RIGHT and the diagnosis in issue332 was wrong. The remaining question was whether the shell and the hook share a session key, answered by comparing CLAUDE_CODE_SESSION_ID against the session_id the Stop hook had written into an obligation record hours earlier: identical."; }
    verification sessionActorStandupGate : Test { :>> id = "42aed175-80b6-4f92-e7d4-2f509c6b3d8b"; :>> title = "Sprint 515 standup gate"; :>> createdAt = "2026-09-01"; :>> createdBy = "claudeOpus5"; :>> method = VerificationMethod::inspect; :>> procedureText = "ONE DESIGN CHOICE with a smell, stated: resolve() now has a write side-effect - when KEEL_ACTOR wins, it remembers that actor for the session. A read that writes is normally wrong. It is accepted here because the alternative is a new command every session must remember to run, which is the manual-vigilance shape D0047 rejects; the write is idempotent (an unchanged declaration does not touch the file), machine-local, gitignored, and records only what the session itself declared. The other choice: the pure halves are separated from the env-reading wrappers so the tests never touch process environment - env-var tests race across threads and a flaky test here would be a control that lies."; }
    verification sessionActorImplementGate : Test { :>> id = "53bfe286-91c7-4003-f8e5-306a0d7c4e9c"; :>> title = "Sprint 515 implement gate"; :>> createdAt = "2026-09-01"; :>> createdBy = "claudeOpus5"; :>> method = VerificationMethod::test; :>> procedureText = "RAN: KEEL_ACTOR=claudeOpus5 keel actor -> writes .keel/sessions/60405c11-.../actor; then env -u KEEL_ACTOR keel actor -> claudeOpus5 (registered). Before this change the same command returned claudeFable5, the machine binding. cargo test --lib session_binding -> 3 passed: read-back by session id and isolation between sessions; a malformed id (empty, path traversal, shell metacharacters) never becomes a path; an unchanged declaration does not rewrite the file. keel guard control-defect-registry -> 2 scanned, 0 violations after the ownership entry was removed."; }
    verification sessionActorReviewGate : Test { :>> id = "64c0f397-a2d8-4114-0906-417b1e8d5fad"; :>> title = "Sprint 515 review gate — three passes per D0172"; :>> createdAt = "2026-09-01"; :>> createdBy = "claudeOpus5"; :>> method = VerificationMethod::inspect; :>> procedureText = "THREE PASSES. (1) CAN THIS ATTRIBUTE TO THE WRONG ACTOR: only if a session declares one actor and then another - and then the binding follows the latest declaration, which is what the session said. It cannot invent an actor; it records only what KEEL_ACTOR carried. (2) IS THE PATH SAFE: the session id comes from an environment variable, so it is validated as UUID characters only before becoming a directory name - tested against traversal and shell metacharacters. (3) WAS issue332's CARRY-REASON WRONG, and does it matter: yes and yes. It said 'guard source under the keystone lock'. actor.rs and the hook dispatcher are not on D0209 clause 2's surface, so no signature was needed and the defect could have been fixed the hour it was found. The control-defect process names an unjustified carry as its unacceptable case; this was one, and it is recorded as such rather than tidied."; }
    verification sessionActorCloseOutGate : Test { :>> id = "75d104a8-b3e9-4225-1a17-528c2f9e60be"; :>> title = "Sprint 515 closeOut gate (autonomous, D0049)"; :>> createdAt = "2026-09-01"; :>> createdBy = "claudeOpus5"; :>> method = VerificationMethod::inspect; :>> procedureText = "CLOSED. issue337 resolved and its registry entry removed in the same commit, as the process requires. The D0278 registry holds two entries: issues and decision-scaffolding, both under-reporting, both carried with reasons that still stand (a fork between fix shapes; a schema question)."; }
    verification sessionActorRetroGate : Test { :>> id = "86e215b9-c4fa-4336-2b28-639d3a0f71cf"; :>> title = "Sprint 515 retro gate (autonomous, D0049)"; :>> createdAt = "2026-09-01"; :>> createdBy = "claudeOpus5"; :>> method = VerificationMethod::analyze; :>> procedureText = "no new item - already tracked: the finding of this sprint is issue337 itself, that a diagnosis written from memory (issue332) named the wrong mechanism and the wrong carry-reason, and only reading the source corrected it. That is recorded in issue337's description and in the rigor panel's fifth critique (rigorSelfReferenceCritique), and the generalisable rule - a defect claim names the file:line it read - is already the response contract's section 3. Nothing here needs a third home."; }
}
