// ProjectDeliveryS146 — Sprint 146: rootednessGuard (D0099, partial issue047) — the UPWARD requirement-
// rootedness honesty gate. Data-driven: the rootedness computation showed 144/147 Stories are decision-
// chartered (legitimate, D0064), so a blanket gate would flood. The honest narrow rule (D0099): a
// `#Capability`-marked user-facing feature must `#DerivedFrom` a Need, else `guard requirement-rootedness`
// fails; unmarked work exempt; full charter-source balance is the non-blocking `keel rootedness` burndown.
// CHANGE (CR): Decision d0099 (accepted). 4 pts. AUTONOMOUS ceremony (D0049).
package ProjectDeliveryS146 {
    private import EngineElement::*;
    private import EngineWork::*;
    private import EngineVerification::*;
    private import EngineRelationships::*;

    #CharteredBy dependency from rootednessGuardStory to d0099;

    part rootednessGuardStory : Story {
        :>> id = "63940516-2c7d-4e8f-c146-51627384c001";
        :>> title = "Sprint 146: rootednessGuard (4 pts) — #Capability must state a driving Need (hard gate) + the rootedness burndown view (D0099)";
        :>> createdAt = "2026-06-24"; :>> createdBy = "wweatherholtz"; :>> kind = WorkKind::code; :>> priority = WorkPriority::p1; :>> owner = "claudeOpus"; :>> estimatedPoints = 4;
    }

    action def DeliveryRunS146 {
        action storyRootednessGuard;
        verification storyRootednessGuardDoD : Test { :>> id = "63940516-2c7d-4e8f-c146-51627384c002"; :>> method = VerificationMethod::test; :>> procedureText = "D0099 (rootedness half of issue047/requirementRootednessGuard). DATA FIRST (D0098 surface-before-gate): built `keel rootedness` + ran it — 144/147 delivery Stories are decision-chartered, NOT need-rooted (the engine is decision-driven by design, D0064), so a blanket Story->Need hard gate would flood + miscategorize legitimate evolution as a lie. FIX (the honest narrow rule): a new enforced honest-state guard `requirement-rootedness` (GUARD_NAMES 11 -> 12) fails iff a `#Capability`-marked element lacks a `#DerivedFrom`->Need edge; UNMARKED work is exempt. The `keel rootedness` view reports the charter-source BURNDOWN (need-rooted / decision-chartered / orphan) + the #Capability gate set. A `rootedness` Viewpoint declares the concern; the viewpoint-renderer guard's known-command list + README/CLAUDE.md doc-synced. VERIFIED (live): `keel guard` = 12 ALL PASS (requirement-rootedness passes vacuously — 0 #Capability items today, no flood); `keel rootedness` = need 3 / decision 106 / orphan 38 / capViol 0; viewpoint-renderer PASS (rootedness vp resolves). clippy -D warnings + keel validate 159 + kernel validate_instances (pre-commit) green. NOTE: serveRequirementsTrace will mark d0094 #Capability + add its Need (gate then bites for serve). REMAINING under requirementRootednessGuard: the DOWNWARD tier-satisfaction comprehensiveness burndown + the orient surfacing."; }
        part storyRootednessGuardDoDR1 : TestResult { :>> id = "63940516-2c7d-4e8f-c146-51627384c003"; :>> outcome = VerdictKind::pass; :>> judgedAgainst = "4df27d4"; :>> judgedAt = "2026-06-24"; :>> judgedBy = "claudeOpus"; }
    }

    verification rootednessGuardRefineGate : Test { :>> id = "63940516-2c7d-4e8f-c146-51627384c004"; :>> title = "Sprint 146 refine gate (DoR)"; :>> createdAt = "2026-06-24"; :>> createdBy = "claudeOpus"; :>> method = VerificationMethod::inspect; :>> procedureText = "DoR: D0098 authorized a rootedness hard gate; issue047 wants rootedness un-ignorable. Build it data-first. Decision d0099 accepted (#Capability marker rule, chosen after the 144/147 data). estimatedPoints=4. #CharteredBy d0099. DoR met."; }
    part rootednessGuardRefineGateR1 : TestResult { :>> id = "63940516-2c7d-4e8f-c146-51627384c005"; :>> outcome = VerdictKind::pass; :>> judgedAgainst = "4df27d4"; :>> judgedAt = "2026-06-24"; :>> judgedBy = "claudeOpus"; }
    verification rootednessGuardStandupGate : Test { :>> id = "63940516-2c7d-4e8f-c146-51627384c006"; :>> title = "Sprint 146 standup gate"; :>> createdAt = "2026-06-24"; :>> createdBy = "claudeOpus"; :>> method = VerificationMethod::inspect; :>> procedureText = "Approach: compute rootedness as a view first (ground the rule on data); then the #Capability hard guard (passes vacuously now); rootedness Viewpoint + known-command + doc-sync. Defer tier-satisfaction + orient burndown. No blockers."; }
    part rootednessGuardStandupGateR1 : TestResult { :>> id = "63940516-2c7d-4e8f-c146-51627384c007"; :>> outcome = VerdictKind::pass; :>> judgedAgainst = "4df27d4"; :>> judgedAt = "2026-06-24"; :>> judgedBy = "claudeOpus"; }
    verification rootednessGuardImplementGate : Test { :>> id = "63940516-2c7d-4e8f-c146-51627384c008"; :>> title = "Sprint 146 implement gate"; :>> createdAt = "2026-06-24"; :>> createdBy = "claudeOpus"; :>> method = VerificationMethod::test; :>> procedureText = "Added rootedness computation + `keel rootedness` view + `requirement-rootedness` guard (GUARD_NAMES 12) + rootedness Viewpoint + VIEW_SUBCOMMANDS entry + d0099 + doc-sync. VERIFIED: guard 12 ALL PASS; rootedness burndown need 3/decision 106/orphan 38/capViol 0; viewpoint-renderer PASS; clippy green; validate 159."; }
    part rootednessGuardImplementGateR1 : TestResult { :>> id = "63940516-2c7d-4e8f-c146-51627384c009"; :>> outcome = VerdictKind::pass; :>> judgedAgainst = "4df27d4"; :>> judgedAt = "2026-06-24"; :>> judgedBy = "claudeOpus"; }
    verification rootednessGuardReviewGate : Test { :>> id = "63940516-2c7d-4e8f-c146-51627384c00a"; :>> title = "Sprint 146 review gate"; :>> createdAt = "2026-06-24"; :>> createdBy = "claudeOpus"; :>> method = VerificationMethod::inspect; :>> procedureText = "Diff reviewed. The data probe earned its keep — it killed a wrong blanket gate (144 false 'lies') and yielded the honest narrow #Capability rule that targets the serve class without flooding or taxing legitimate decision-driven evolution (D0064). The marker ADDS an obligation (state your Need), it does not hide a gap — distinct from the rejected WIP flag. Burndown surfaces the full balance for visibility. Clean; tier-satisfaction + orient surfacing correctly deferred."; }
    part rootednessGuardReviewGateR1 : TestResult { :>> id = "63940516-2c7d-4e8f-c146-51627384c00b"; :>> outcome = VerdictKind::pass; :>> judgedAgainst = "4df27d4"; :>> judgedAt = "2026-06-24"; :>> judgedBy = "claudeOpus"; }
    verification rootednessGuardCloseOutGate : Test { :>> id = "63940516-2c7d-4e8f-c146-51627384c00c"; :>> title = "Sprint 146 closeOut gate (autonomous, D0049)"; :>> createdAt = "2026-06-24"; :>> createdBy = "claudeOpus"; :>> method = VerificationMethod::inspect; :>> procedureText = "Autonomous closeOut (D0049): DoD pass; rootedness honesty gate live (vacuous today, binds the next #Capability); rootedness burndown computes. guard 12 ALL PASS; clippy + validate 159 + kernel validate_instances (pre-commit) green. Self-evidencing (D0051) except d0099 acceptance (human, held). CR. issue047 partially resolved (upward rootedness); tier-satisfaction + orient surfacing remain; serveRequirementsTrace now unblocked + will exercise the gate."; }
    part rootednessGuardCloseOutGateR1 : TestResult { :>> id = "63940516-2c7d-4e8f-c146-51627384c00d"; :>> outcome = VerdictKind::pass; :>> judgedAgainst = "4df27d4"; :>> judgedAt = "2026-06-24"; :>> judgedBy = "claudeOpus"; }
    verification rootednessGuardRetroGate : Test { :>> id = "63940516-2c7d-4e8f-c146-51627384c00e"; :>> title = "Sprint 146 retro gate (autonomous, D0049)"; :>> createdAt = "2026-06-24"; :>> createdBy = "claudeOpus"; :>> method = VerificationMethod::analyze; :>> procedureText = "Autonomous retro (D0049). WELL: building the computation as a VIEW first (D0098 surface-before-gate) produced the 144/147 datum that overturned the blanket-gate premise — a wrong hard gate avoided BY data, not opinion. The #Capability marker cleanly separates declared features (must justify) from decision-driven evolution (legitimate, D0064). AVOIDABLE-ISSUE SCAN: the risk was a flooding/ceremony-heavy gate; mitigated by data + the opt-in marker; the rootedness burndown keeps the full picture visible so nothing is silently ignored. LESSON: surface a candidate gate as a burndown and read the real distribution BEFORE hard-gating — premises about 'what is a lie' must be checked against the model. NON-blocking: tier-satisfaction comprehensiveness + orient burndown surfacing remain under requirementRootednessGuard; serveRequirementsTrace is next. Estimate 4 pts held."; }
    part rootednessGuardRetroGateR1 : TestResult { :>> id = "63940516-2c7d-4e8f-c146-51627384c00f"; :>> outcome = VerdictKind::pass; :>> judgedAgainst = "4df27d4"; :>> judgedAt = "2026-06-24"; :>> judgedBy = "claudeOpus"; }
}
