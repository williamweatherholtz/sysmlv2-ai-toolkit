// ProjectDeliveryS271 — Sprint 271: type-def BODIES are read — ref / port / assert constraint /
// require constraint / redefine (issue102 constructs 3-5). dcParserReadBase COMPLETE. EXECUTE. 3 pts.
package ProjectDeliveryS271 {
    private import EngineElement::*;
    private import EngineWork::*;
    private import EngineVerification::*;
    private import EngineRelationships::*;

    #CharteredBy dependency from readMembersStory to d0139;

    part readMembersStory : Story {
        :>> id = "0d800099-0814-6099-9b3e-000000300099";
        :>> title = "Sprint 271: read type-def member features; dcParserReadBase complete (3 pts)";
        :>> createdAt = "2026-08-14"; :>> createdBy = "claudeOpus5"; :>> kind = WorkKind::code; :>> priority = WorkPriority::p0; :>> owner = "claudeOpus5"; :>> estimatedPoints = 3;
    }

    action def DeliveryRunS271 {
        action storyReadMembers;
        verification storyReadMembersDoD : Test { :>> id = "0d80009a-0814-609a-9b3e-00000030009a"; :>> method = VerificationMethod::test; :>> procedureText = "Completes dcParserReadBase (constructs 3-5 of 6). Type-definition BODIES were discarded wholesale, so 149 member declarations in the engine's own schema carried type references nothing resolved — including the two the base-first programme depends on: `ref`, the base construct that replaces a marker for a one-to-many edge, and `assert constraint`, where D0139(D) puts process-to-controls. DELIVERED: `MemberFeature { kind, name, type_name, line }`, `TypeDef.members`, `parse_type_def_body` + `parse_member_feature` handling `attribute` / `ref` / `port` / `assert constraint` / `require constraint` / `:>>` redefinition, and registry resolution of member types. TOLERANT BY DESIGN: an unrecognised member is skipped and recorded exactly as before, so this widens what is READ without narrowing what is ACCEPTED — no previously-parsing file can become a parse error. `attribute` members are deliberately EXCLUDED from type checking: they are typed by `ScalarValues` primitives, which is treated as system-provided and is not a registered package, so checking them would report all 108 as unresolved, and a guard that fires on correct input trains its author to disable it (issue081). VERIFIED, six cases both polarities: `ref` undeclared FAILS / declared PASSES; `assert constraint` undeclared FAILS / declared PASSES; `port` undeclared FAILS; `attribute : String` PASSES. parser-coverage returned to 0 after two intermediate corrections — descending into bodies first exposed 42 multiplicity tails and then 1 redefinition as phantom skipped statements, both tails of constructs already understood, so a silent tail-skip now distinguishes discarded-because-understood from discarded-because-unread. clippy clean; 161 tests; validate + all 27 guards + check-engine green."; }
        part storyReadMembersDoDR1 : TestResult { :>> id = "0d80009b-0814-609b-9b3e-00000030009b"; :>> outcome = VerdictKind::pass; :>> judgedAgainst = "3df2ef0"; :>> judgedAt = "2026-08-14"; :>> judgedBy = "claudeOpus5"; }
    }

    verification rmRefineGate : Test { :>> id = "0d80009c-0814-609c-9b3e-00000030009c"; :>> title = "Sprint 271 refine gate (DoR)"; :>> createdAt = "2026-08-14"; :>> createdBy = "claudeOpus5"; :>> method = VerificationMethod::inspect; :>> procedureText = "DoR: the three remaining constructs have zero instances in the model, so unlike sprints 269-270 they cannot be verified by a drop in parser-coverage. They are verified instead by the undeclared-name discriminator on synthetic input, which is the only honest test for a construct nothing yet uses. estimatedPoints=3. DoR met."; }
    part rmRefineGateR1 : TestResult { :>> id = "0d80009d-0814-609d-9b3e-00000030009d"; :>> outcome = VerdictKind::pass; :>> judgedAgainst = "3df2ef0"; :>> judgedAt = "2026-08-14"; :>> judgedBy = "claudeOpus5"; }

    verification rmStandupGate : Test { :>> id = "0d80009e-0814-609e-9b3e-00000030009e"; :>> title = "Sprint 271 standup gate"; :>> createdAt = "2026-08-14"; :>> createdBy = "claudeOpus5"; :>> method = VerificationMethod::inspect; :>> procedureText = "Approach: one member-feature mechanism covering all five forms rather than a branch per construct — they differ only in a leading keyword, and separate paths would drift. Keep the body parse tolerant so nothing that parsed before can fail now. No blockers."; }
    part rmStandupGateR1 : TestResult { :>> id = "0d80009f-0814-609f-9b3e-00000030009f"; :>> outcome = VerdictKind::pass; :>> judgedAgainst = "3df2ef0"; :>> judgedAt = "2026-08-14"; :>> judgedBy = "claudeOpus5"; }

    verification rmImplementGate : Test { :>> id = "0d8000a0-0814-60a0-9b3e-0000003000a0"; :>> title = "Sprint 271 implement gate"; :>> createdAt = "2026-08-14"; :>> createdBy = "claudeOpus5"; :>> method = VerificationMethod::test; :>> procedureText = "The attribute-exclusion is the judgement call worth recording. Checking attribute member types would be more complete and would immediately report 108 false failures, because ScalarValues is deliberately unregistered. Completeness that fires on correct input is not completeness — it is the issue081 dynamic. The exclusion is narrow (one member kind), stated in the code, and reversible the moment primitives are registered."; }
    part rmImplementGateR1 : TestResult { :>> id = "0d8000a1-0814-60a1-9b3e-0000003000a1"; :>> outcome = VerdictKind::pass; :>> judgedAgainst = "3df2ef0"; :>> judgedAt = "2026-08-14"; :>> judgedBy = "claudeOpus5"; }

    verification rmReviewGate : Test { :>> id = "0d8000a2-0814-60a2-9b3e-0000003000a2"; :>> title = "Sprint 271 review gate"; :>> createdAt = "2026-08-14"; :>> createdBy = "claudeOpus5"; :>> method = VerificationMethod::inspect; :>> procedureText = "Reviewed. dcParserReadBase is COMPLETE: every construct the base-first conversions target is now read AND resolved, so a conversion can no longer parse clean and lose its edges. That was the stated gate on the whole pass. The metric corrected itself twice under pressure this sprint, which is healthy behaviour — each time it over-reported, the cause was the same category error (counting a TAIL as an unread statement), and the fix distinguishes discarded-because-understood from discarded-because-unread at the point of discard rather than by excluding token kinds globally."; }
    part rmReviewGateR1 : TestResult { :>> id = "0d8000a3-0814-60a3-9b3e-0000003000a3"; :>> outcome = VerdictKind::pass; :>> judgedAgainst = "3df2ef0"; :>> judgedAt = "2026-08-14"; :>> judgedBy = "claudeOpus5"; }

    verification rmCloseOutGate : Test { :>> id = "0d8000a4-0814-60a4-9b3e-0000003000a4"; :>> title = "Sprint 271 closeOut gate (autonomous, D0049)"; :>> createdAt = "2026-08-14"; :>> createdBy = "claudeOpus5"; :>> method = VerificationMethod::inspect; :>> procedureText = "Autonomous closeOut (D0049). dcParserReadBase carries a passing DoD TestResult; all six constructs read. parser-coverage 0 across 476 files. clippy clean; 161 tests; validate + all 27 guards + check-engine green. No gate bypassed."; }
    part rmCloseOutGateR1 : TestResult { :>> id = "0d8000a5-0814-60a5-9b3e-0000003000a5"; :>> outcome = VerdictKind::pass; :>> judgedAgainst = "3df2ef0"; :>> judgedAt = "2026-08-14"; :>> judgedBy = "claudeOpus5"; }

    verification rmRetroGate : Test { :>> id = "0d8000a6-0814-60a6-9b3e-0000003000a6"; :>> title = "Sprint 271 retro gate (autonomous, D0049)"; :>> createdAt = "2026-08-14"; :>> createdBy = "claudeOpus5"; :>> method = VerificationMethod::analyze; :>> procedureText = "Autonomous retro (D0049) under D0131's retroTrack. WELL: (1) one mechanism for five member forms rather than five branches, so they cannot drift; (2) the tolerant-body decision means widening what is read could not break what already parsed, verified by the repo staying clean throughout; (3) the attribute-exclusion was reasoned from issue081 rather than from convenience, and is recorded where the next reader will meet it. AVOIDABLE-ISSUE 1: descending into bodies made parser-coverage jump from 0 to 46 and then to 1, twice reporting TAILS (multiplicity brackets, a redefinition default) as unread statements. NO NEW ITEM, reason stated: this is the same category error the metric already had once and was corrected for in sprint 269, and the second correction generalised it properly — a silent tail-skip at the point of discard rather than a growing list of excluded token kinds. The recurrence is evidence the first fix was too narrow and the current one is structural. AVOIDABLE-ISSUE 2: two clippy pedantic failures in newly written code, a third consecutive sprint with that pattern. NO NEW ITEM: clippy is the control and catches it every time; the cost is one build cycle per sprint. Estimate 3 pts, delivered."; }
    part rmRetroGateR1 : TestResult { :>> id = "0d8000a7-0814-60a7-9b3e-0000003000a7"; :>> outcome = VerdictKind::pass; :>> judgedAgainst = "3df2ef0"; :>> judgedAt = "2026-08-14"; :>> judgedBy = "claudeOpus5"; }
}
