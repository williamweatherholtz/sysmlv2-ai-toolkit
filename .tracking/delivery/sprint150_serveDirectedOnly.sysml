// ProjectDeliveryS150 — Sprint 150: serveDirectedOnly (verifies sr17ServeDirectedNoChat) — the first
// serve-redesign sprint. Removes the free-form Agent tab + the un-recorded `investigate` action; the
// only AI action is now the directed, RECORDING Critique on a named element. Honors the human's
// "no ad-hoc AI terminal tab" requirement. EXECUTE (serve redesign). 3 pts. AUTONOMOUS (D0049).
package ProjectDeliveryS150 {
    private import EngineElement::*;
    private import EngineWork::*;
    private import EngineVerification::*;
    private import EngineRelationships::*;

    #CharteredBy dependency from serveDirectedOnlyStory to sr17ServeDirectedNoChat;

    part serveDirectedOnlyStory : Story {
        :>> id = "63940516-2c7d-4e8f-c150-51627384c001";
        :>> title = "Sprint 150: serveDirectedOnly (3 pts) — remove the free-form Agent tab + investigate; AI actions are directed + recorded (verifies sr17)";
        :>> createdAt = "2026-06-24"; :>> createdBy = "wweatherholtz"; :>> kind = WorkKind::code; :>> priority = WorkPriority::p2; :>> owner = "claudeOpus"; :>> estimatedPoints = 3;
    }

    action def DeliveryRunS150 {
        action storyServeDirectedOnly;
        verification storyServeDirectedOnlyDoD : Test { :>> id = "63940516-2c7d-4e8f-c150-51627384c002"; :>> method = VerificationMethod::inspect; :>> procedureText = "First serve-redesign sprint, satisfying sr17ServeDirectedNoChat (the anti-'ad-hoc AI terminal tab' requirement). FIX: removed from console.html the Agent TAB (free action+target runner), the `runAgent` function, and ALL Investigate ▶ buttons (modal item + task branches); the only AI action is now the modal Critique ▶ on a NAMED element, which records findings as Issues (element-critique skill). serve.rs: build_agent_prompt reduced to the critique prompt only; api_agent_stream now REJECTS any action != critique with a clear message (defense-in-depth so the bridge can't be driven to a non-recording action even by direct URL); the startup banner updated. VERIFIED (live): GET / has no '\"agent\",\"Agent\"' tab (grep 0); curl '/api/agent/stream?action=investigate&target=d0094' -> SSE error 'only the critique action is supported' (no claude spawned); clippy -D warnings green; cargo build release; keel validate + guard all (12) green. sr17Verify (#Verify -> sr17, method=inspect) records this; tier-satisfaction SR-verified ticks up (sr17 now verified). sr15/sr16/sr18/sr19 remain the honest unverified serve-redesign backlog."; }
        part storyServeDirectedOnlyDoDR1 : TestResult { :>> id = "63940516-2c7d-4e8f-c150-51627384c003"; :>> outcome = VerdictKind::pass; :>> judgedAgainst = "67273fa"; :>> judgedAt = "2026-06-24"; :>> judgedBy = "claudeOpus"; }
    }

    verification serveDirectedOnlyRefineGate : Test { :>> id = "63940516-2c7d-4e8f-c150-51627384c004"; :>> title = "Sprint 150 refine gate (DoR)"; :>> createdAt = "2026-06-24"; :>> createdBy = "claudeOpus"; :>> method = VerificationMethod::inspect; :>> procedureText = "DoR: serve now has requirements (S149); sr17 (directed-only) is the cleanest first build — a deletion that honors the human's explicit 'no ad-hoc AI terminal'. estimatedPoints=3. #CharteredBy sr17ServeDirectedNoChat. DoR met."; }
    part serveDirectedOnlyRefineGateR1 : TestResult { :>> id = "63940516-2c7d-4e8f-c150-51627384c005"; :>> outcome = VerdictKind::pass; :>> judgedAgainst = "67273fa"; :>> judgedAt = "2026-06-24"; :>> judgedBy = "claudeOpus"; }
    verification serveDirectedOnlyStandupGate : Test { :>> id = "63940516-2c7d-4e8f-c150-51627384c006"; :>> title = "Sprint 150 standup gate"; :>> createdAt = "2026-06-24"; :>> createdBy = "claudeOpus"; :>> method = VerificationMethod::inspect; :>> procedureText = "Approach: delete the Agent tab + runAgent + Investigate buttons in console.html; restrict the bridge to critique-only in serve.rs (reject others); verify live (no tab; investigate rejected); record sr17Verify. No blockers."; }
    part serveDirectedOnlyStandupGateR1 : TestResult { :>> id = "63940516-2c7d-4e8f-c150-51627384c007"; :>> outcome = VerdictKind::pass; :>> judgedAgainst = "67273fa"; :>> judgedAt = "2026-06-24"; :>> judgedBy = "claudeOpus"; }
    verification serveDirectedOnlyImplementGate : Test { :>> id = "63940516-2c7d-4e8f-c150-51627384c008"; :>> title = "Sprint 150 implement gate"; :>> createdAt = "2026-06-24"; :>> createdBy = "claudeOpus"; :>> method = VerificationMethod::inspect; :>> procedureText = "console.html: Agent tab + runAgent + Investigate removed; serve.rs: critique-only bridge + reject + banner. VERIFIED live (no tab; investigate -> error; serve killed after); clippy + build + validate + guard 12 green."; }
    part serveDirectedOnlyImplementGateR1 : TestResult { :>> id = "63940516-2c7d-4e8f-c150-51627384c009"; :>> outcome = VerdictKind::pass; :>> judgedAgainst = "67273fa"; :>> judgedAt = "2026-06-24"; :>> judgedBy = "claudeOpus"; }
    verification serveDirectedOnlyReviewGate : Test { :>> id = "63940516-2c7d-4e8f-c150-51627384c00a"; :>> title = "Sprint 150 review gate"; :>> createdAt = "2026-06-24"; :>> createdBy = "claudeOpus"; :>> method = VerificationMethod::inspect; :>> procedureText = "Diff reviewed. A clean deletion that makes the console's AI surface exactly what the human asked for: directed, recorded critique of named elements — no free-form chat (open a terminal for that). The server-side reject is the honest backstop (the UI can't be the only guard). First serve SR verified; the rest stay honest burndown gaps. Clean."; }
    part serveDirectedOnlyReviewGateR1 : TestResult { :>> id = "63940516-2c7d-4e8f-c150-51627384c00b"; :>> outcome = VerdictKind::pass; :>> judgedAgainst = "67273fa"; :>> judgedAt = "2026-06-24"; :>> judgedBy = "claudeOpus"; }
    verification serveDirectedOnlyCloseOutGate : Test { :>> id = "63940516-2c7d-4e8f-c150-51627384c00c"; :>> title = "Sprint 150 closeOut gate (autonomous, D0049)"; :>> createdAt = "2026-06-24"; :>> createdBy = "claudeOpus"; :>> method = VerificationMethod::inspect; :>> procedureText = "Autonomous closeOut (D0049): DoD pass; the directed-only console is live; sr17 verified. clippy + build + keel validate + guard all (12) green. Self-evidencing (D0051). tier-satisfaction SR-verified ticks up; sr15/sr16/sr18/sr19 remain the serve-redesign backlog."; }
    part serveDirectedOnlyCloseOutGateR1 : TestResult { :>> id = "63940516-2c7d-4e8f-c150-51627384c00d"; :>> outcome = VerdictKind::pass; :>> judgedAgainst = "67273fa"; :>> judgedAt = "2026-06-24"; :>> judgedBy = "claudeOpus"; }
    verification serveDirectedOnlyRetroGate : Test { :>> id = "63940516-2c7d-4e8f-c150-51627384c00e"; :>> title = "Sprint 150 retro gate (autonomous, D0049)"; :>> createdAt = "2026-06-24"; :>> createdBy = "claudeOpus"; :>> method = VerificationMethod::analyze; :>> procedureText = "Autonomous retro (D0049). WELL: the serve redesign's first sprint is a SUBTRACTION — removing the ad-hoc AI tab the human never wanted — and it verifies a real requirement (sr17), ticking tier-satisfaction up honestly (build a requirement -> verify it). The server-side reject means the directed-only contract holds even against a hand-crafted URL, not just the UI. AVOIDABLE-ISSUE SCAN: none new; the bridge is now single-purpose (critique), shrinking the AI attack/footprint surface. LESSON: a requirement met by DELETION is the cheapest quality win — the anti-requirement (sr17) was satisfied by removing code, not adding it. NON-blocking next serve SRs: sr15 (recency/timeline), sr16 (close the critique implement-loop), sr18 (section-local critique), sr19 (white-box boundary sweep). Estimate 3 pts held."; }
    part serveDirectedOnlyRetroGateR1 : TestResult { :>> id = "63940516-2c7d-4e8f-c150-51627384c00f"; :>> outcome = VerdictKind::pass; :>> judgedAgainst = "67273fa"; :>> judgedAt = "2026-06-24"; :>> judgedBy = "claudeOpus"; }
}
