// ProjectDeliveryS532 — Sprint 532: the hook set rendered a second time, as a plugin. EXECUTE. 2 pts.
package ProjectDeliveryS532 {
    private import EngineElement::*;
    private import EngineWork::*;
    private import EngineVerification::*;
    private import EngineRelationships::*;

    #CharteredBy dependency from pluginStory to d0296;

    part pluginStory : Story {
        :>> id = "3cfae7d0-d850-4cfe-8751-a9f3f869be06";
        :>> title = "Sprint 532: one generator, two renderings - the keel plugin at .engine/claude-plugin and its marketplace manifest, checked by sync-claude --check (2 pts)";
        :>> createdAt = "2026-09-03"; :>> createdBy = "claudeOpus5"; :>> kind = WorkKind::code; :>> priority = WorkPriority::p0; :>> owner = "claudeOpus5"; :>> estimatedPoints = 2;
    }

    action def DeliveryRunS532 {
        action storyPlugin;
        verification storyPluginDoD : Test { :>> id = "b3b0e8ed-dae2-42d6-92c8-7de5150a6fff"; :>> method = VerificationMethod::test; :>> procedureText = "DELIVERED BACKLOG ITEMS: dcKeelPluginHostsTheHooks. DONE: plugin_manifest, plugin_hooks (= keel_hooks, unchanged) and marketplace_manifest in claude_surface.rs; plugin_files is the one list the writer and the check both walk; sync-claude writes .engine/claude-plugin/.claude-plugin/plugin.json, hooks/hooks.json and .claude-plugin/marketplace.json, --check reports any of the three stale or missing. VERIFY: unit test asserts the plugin hook set equals the settings hook set and the write-then-check round trip; claude plugin validate passes both manifests; a nested session with --plugin-dir and no repo settings file fires every keel hook into the fire-ledger."; }
        // RAN: cargo test --release 458/0; clippy 0; claude plugin validate .engine/claude-plugin -> passed; claude plugin validate .claude-plugin/marketplace.json -> passed; claude -p --plugin-dir in a fresh git project without .claude/: hooks.jsonl user-prompt, post-edit, pre-bash x8, stop x2
        part storyPluginDoDR1 : TestResult { :>> id = "dbd9d0d0-4dc1-408a-87c4-1f7bea807def"; :>> outcome = VerdictKind::pass; :>> judgedAgainst = "c8e08f5"; :>> judgedAt = "2026-09-03"; :>> judgedBy = "claudeOpus5"; }
    }

    verification pluginRefineGate : Test { :>> id = "3d6dac64-8f3f-4c1b-89f0-a4ce64afd099"; :>> title = "Sprint 532 refine gate (DoR)"; :>> createdAt = "2026-09-03"; :>> createdBy = "claudeOpus5"; :>> method = VerificationMethod::inspect; :>> procedureText = "READY from D0296 run 1 (a --plugin-dir plugin fires in a nested session) and the shape of the superpowers plugin on this machine (hooks/hooks.json under a plugin root); the open question - where the plugin lives - was answered by the DoD's default, in the repository under .engine, because that is what sync-claude can regenerate and the drift guard can read."; }
    verification pluginStandupGate : Test { :>> id = "c1d80895-b1eb-42c7-b490-d70d593d9549"; :>> title = "Sprint 532 standup gate"; :>> createdAt = "2026-09-03"; :>> createdBy = "claudeOpus5"; :>> method = VerificationMethod::inspect; :>> procedureText = "ONE CHOICE: the plugin's hooks.json is keel_hooks() verbatim - no plugin-specific command variants - so the two renderings cannot diverge in meaning, only in presence. The commands already resolve the binary from KEEL_BIN then PATH, which is what a plugin needs. Second: the marketplace names the plugin by relative in-repo source, so a downstream project can add this repository as a marketplace without a registry."; }
    verification pluginImplementGate : Test { :>> id = "d84bceaa-0dd3-44c5-8871-73a156232a4d"; :>> title = "Sprint 532 implement gate"; :>> createdAt = "2026-09-03"; :>> createdBy = "claudeOpus5"; :>> method = VerificationMethod::test; :>> procedureText = "RAN: edit script through the Write tool (no heredoc); build clean first time; sync-claude --check reported the three files missing, sync wrote them, --check clean; claude plugin validate on both; the nested run needed a git init and an actor file for the fixture - the stop hook then told the nested agent its tree was un-migrated, which is the gate doing its job in the wrong room and irrelevant to the receipt."; }
    verification pluginReviewGate : Test { :>> id = "a15ae58a-4733-4077-87dc-e241a3a43e53"; :>> title = "Sprint 532 review gate — three passes per D0172"; :>> createdAt = "2026-09-03"; :>> createdBy = "claudeOpus5"; :>> method = VerificationMethod::inspect; :>> procedureText = "THREE PASSES. (1) CAN THE TWO RENDERINGS DISAGREE: only by one being stale, and the check names which; the test asserts equality of the hook objects. (2) IS THE PLUGIN REALLY ABOVE THE REPO: no - it lives IN the repo, so a commit can change it; what it is above is the repo-scope SETTINGS file, which cannot remove a merged hook list. The commit path is covered by the drift guard in CI and the launch path (dcLaunchPinsHooksOn, next) points --plugin-dir at it. Stated plainly in CLAUDE.md. (3) LINE ENDINGS: the check normalises CRLF before comparing, so a Windows checkout does not read as drift - the issue this repository already met as dcSurfaceDriftIgnoresLineEndings."; }
    verification pluginCloseOutGate : Test { :>> id = "dd3f7bf8-6948-4622-a5df-6b97bd916f24"; :>> title = "Sprint 532 closeOut gate (autonomous, D0049)"; :>> createdAt = "2026-09-03"; :>> createdBy = "claudeOpus5"; :>> method = VerificationMethod::inspect; :>> procedureText = "CLOSED. The plugin files are committed with this sprint; guards.md and CLAUDE.md carry the second rendering."; }
    verification pluginRetroGate : Test { :>> id = "de50d695-7624-4fd1-a79a-b43a67c9e5a7"; :>> title = "Sprint 532 retro gate (autonomous, D0049)"; :>> createdAt = "2026-09-03"; :>> createdBy = "claudeOpus5"; :>> method = VerificationMethod::analyze; :>> procedureText = "no new item - already tracked: the plugin alone changes nothing about who can silence the hooks (D0296 run 5: a key on disk at launch kills it) - its value arrives with dcLaunchPinsHooksOn and dcHookConfigChangeRestoresTheFile, both chartered by d0296 and next on the frontier; the review's honest finding that the plugin is in the repository, not above it, is d0296's stated limit, not a new one."; }
}
