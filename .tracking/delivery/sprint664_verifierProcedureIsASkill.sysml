// ProjectDeliveryS664 — Sprint 664: The D0425 verifier's procedure becomes the test-verify skill (D0438) instead of prompt text retyped every sprint. Two in-field Issues from sprint 663 are the charter: issue469, the verifier ran the touched set in the foreground and the harness's ten-minute cap killed it; issue471, a verifier told in prose to edit nothing hand-wrote two malformed triage statements onto red-yield obligations and reported a validate result from before its own edit, putting parser-coverage red (obligation01af4c5d). The skill states the mandate first - reads and runs, writes nothing, an owed write is an OWED WRITES line for the recorder - then the procedure in order: touched run detached with the launch epoch recorded, the gate set while it runs, the dispatch's probe pair by name, clippy with TIMEOUT reported under the build lock, the receipt read only after exit with outcome, at, stems, lib and head each its own line, and a fixed receipt shape. A dispatch names the skill, the binary, the receipt path, the probe pair and any expected red - nothing else about how to verify.. EXECUTE. 2 pts.
package ProjectDeliveryS664 {
    private import EngineElement::*;
    private import EngineWork::*;
    private import EngineVerification::*;
    private import EngineRelationships::*;

    #CharteredBy dependency from verifierProcedureIsASkillStory to d0438;

    part verifierProcedureIsASkillStory : Story {
        :>> id = "5a805320-95ec-4d9e-8496-c06fe6170687";
        :>> title = "Sprint 664: The D0425 verifier's procedure becomes the test-verify skill (D0438) instead of prompt text retyped every sprint. Two in-field Issues from sprint 663 are the charter: issue469, the verifier ran the touched set in the foreground and the harness's ten-minute cap killed it; issue471, a verifier told in prose to edit nothing hand-wrote two malformed triage statements onto red-yield obligations and reported a validate result from before its own edit, putting parser-coverage red (obligation01af4c5d). The skill states the mandate first - reads and runs, writes nothing, an owed write is an OWED WRITES line for the recorder - then the procedure in order: touched run detached with the launch epoch recorded, the gate set while it runs, the dispatch's probe pair by name, clippy with TIMEOUT reported under the build lock, the receipt read only after exit with outcome, at, stems, lib and head each its own line, and a fixed receipt shape. A dispatch names the skill, the binary, the receipt path, the probe pair and any expected red - nothing else about how to verify. (2 pts)";
        :>> createdAt = "2026-09-11"; :>> createdBy = "claudeOpus5"; :>> kind = WorkKind::code; :>> priority = WorkPriority::p0; :>> owner = "claudeOpus5"; :>> estimatedPoints = 2;
    }

    action def DeliveryRunS664 {
        action storyVerifierProcedureIsASkill;
        verification storyVerifierProcedureIsASkillDoD : Test { :>> id = "7cafea34-32fb-4d08-acbe-c8ee54726cb8"; :>> method = VerificationMethod::test; :>> procedureText = "The skill file carries each step by name (probe664: 17/17 on the working tree, 2/17 on HEAD's v0.1.0); a verifier dispatched with the skill alone and this sprint's inputs completes a detached run exceeding ten minutes and reports it from its own receipt with at after its launch; git status after the verifier's run lists exactly the paths it listed before (the issue471 case); keel sync-claude --check is clean with the skill deployed; validate, check-engine and guard --no-receipt are green on the verifier's own run; the push lands and CI's conclusion is success."; }
        // RAN: keel validate . -> 758 tracking file(s) validated clean.; exit=0; keel check-engine . -> .engine instance files validated clean (kernel-free; D0112 phase 2).; exit=0; keel guard --no-receipt . -> PASS 51; exit=0; keel sync-claude --check . -> claude-surface: keel-owned subset matches this binary(s) generator (46 registry skill(s)); exit=0; cargo clippy --release --all-targets -- -D warnings -> pass; exit=0; probe pair positive 17/17 names present negative 2/17 names present (exit 0 / 1); touched receipt outcome=empty stems=[] at=1789094703 launch=1789094698 at>launch ok; suite receipt outcome=pass passed=720 failed=0 duration 896 s; STATUS BEFORE/AFTER identical 7 dirty M paths + 2 untracked
        part storyVerifierProcedureIsASkillDoDR1 : TestResult { :>> id = "bf4fff85-1c3c-4bb7-8591-2d8fefdcb42f"; :>> outcome = VerdictKind::pass; :>> judgedAgainst = "24dbcfb"; :>> judgedAt = "2026-09-10"; :>> judgedBy = "claudeOpus5"; }
    }

    verification verifierProcedureIsASkillRefineGate : Test { :>> id = "05b6fd42-59aa-404a-b429-f1d381493b63"; :>> title = "Sprint 664 refine gate (DoR)"; :>> createdAt = "2026-09-11"; :>> createdBy = "claudeOpus5"; :>> method = VerificationMethod::inspect; :>> procedureText = "Chartered by D0438 (proposed, process-change: a skill is a process definition under the keystone lock, so the commit carries the marked Decision and the human's word is what accepts it). Sized 2 points: one skill rewritten in place, its registry, one CLAUDE.md rule, one Decision, and a live dispatch of the verifier under the skill as the DoD's own test. The three High-class items were moved to the frontier's head first (D0311: 46 inversions read from show priority, 0 after the move); this one leads because it resolves two of the three in-field Issues."; }
    part verifierProcedureIsASkillRefineGateR1 : TestResult { :>> id = "88551244-faba-4384-b6e7-d3199b2ec096"; :>> outcome = VerdictKind::proposed; :>> judgedAgainst = "24dbcfb"; :>> judgedAt = "2026-09-10"; :>> judgedBy = "claudeOpus5"; }
    verification verifierProcedureIsASkillStandupGate : Test { :>> id = "b9d08c07-2f4a-4827-8002-d49efb06d243"; :>> title = "Sprint 664 standup gate"; :>> createdAt = "2026-09-11"; :>> createdBy = "claudeOpus5"; :>> method = VerificationMethod::inspect; :>> procedureText = "Order: read the DoD and issue469/471 for the exact failure each names; write the skill with the mandate as its first section; patch the registry purpose and trigger through textpatch; record D0438 from a draft file with the process-change marker; sync-claude and diff the deployed copy; doc-sync CLAUDE.md sec 4; write the probe pair and run it on both known cases BEFORE the verifier is dispatched; then dispatch the verifier naming only the skill, keel-serve.exe, the receipt path, probe664's two cases and the full suite for the ten-minute case (no keel-cli/src moved, so the touched set is empty by construction); the recorder writes the ceremony from that receipt."; }
    part verifierProcedureIsASkillStandupGateR1 : TestResult { :>> id = "a6975a62-b3cb-4f59-8f78-739b8e62b59c"; :>> outcome = VerdictKind::proposed; :>> judgedAgainst = "24dbcfb"; :>> judgedAt = "2026-09-10"; :>> judgedBy = "claudeOpus5"; }
    verification verifierProcedureIsASkillImplementGate : Test { :>> id = "02ff5ceb-c4bc-4619-85ed-049b46eec9b0"; :>> title = "Sprint 664 implement gate"; :>> createdAt = "2026-09-11"; :>> createdBy = "claudeOpus5"; :>> method = VerificationMethod::test; :>> procedureText = ".engine/skills/test-verify/SKILL.md rewritten (v0.1.0 -> 0.2.0): Mandate table, then steps 1-6 - detached touched launch with .keel/metrics/verify-launch.epoch, the empty-set and full-suite clauses, the gate set, the probe pair, clippy with TIMEOUT, the receipt checks table (outcome/at/stems/lib/passed/head), the receipt shape - and seven anti-patterns each citing the Issue it happened as. registry.sysml purpose and triggerCondition rewritten. .engine/decisions/0438-verifierProcedureIsTheTestVerifySkill.sysml recorded proposed (marker process-change; write path reported OUTSIDE standing consent, D0337). CLAUDE.md sec 4 D0425 rule gains the paragraph naming the skill as the procedure. .claude/skills/test-verify/SKILL.md redeployed by sync-claude, byte-identical. backlog.sysml: dcVerifierProcedureIsASkill, dcMarkerTextWithoutMarkerHolds, dcGuardReadsTheWorkingTreeOutsideTheHook moved above dcSetJudgmentWritePath. No Rust changed."; }
    // RAN: keel validate . -> 758 tracking file(s) validated clean.; exit=0; keel check-engine . -> .engine instance files validated clean (kernel-free; D0112 phase 2).; exit=0; keel guard --no-receipt . -> PASS 51; exit=0; keel sync-claude --check . -> claude-surface: keel-owned subset matches this binary(s) generator (46 registry skill(s)); exit=0; cargo clippy --release --all-targets -- -D warnings -> pass; exit=0; probe pair positive 17/17 names present negative 2/17 names present (exit 0 / 1); touched receipt outcome=empty stems=[] at=1789094703 launch=1789094698 at>launch ok; suite receipt outcome=pass passed=720 failed=0 duration 896 s; STATUS BEFORE/AFTER identical 7 dirty M paths + 2 untracked
    part verifierProcedureIsASkillImplementGateR1 : TestResult { :>> id = "035a3592-2113-4b5c-81bc-76bcfa544a24"; :>> outcome = VerdictKind::pass; :>> judgedAgainst = "24dbcfb"; :>> judgedAt = "2026-09-10"; :>> judgedBy = "claudeOpus5"; }
    verification verifierProcedureIsASkillReviewGate : Test { :>> id = "9af4f03d-532d-44f8-8977-78a1f6a67bd1"; :>> title = "Sprint 664 review gate — three passes per D0172"; :>> createdAt = "2026-09-11"; :>> createdBy = "claudeOpus5"; :>> method = VerificationMethod::inspect; :>> procedureText = "Delivered: the verifier's procedure is one file that can be corrected once, the mandate is its first section, and the honesty checks a receipt owes are a table rather than a memory. The DoD's live case is this sprint's own verification: the dispatch carries the skill name and the sprint's inputs only, and the receipt it produces is what the recorder writes from. Not delivered: no harness-level control refuses a tree write from a read-only subagent - D0438's rationale names that as what would change it, and it would be a CHANGE to the Agent tool set, not a skill. The recorder's mandate (dcDelegatedCeremonyIsASkill, Low) is the other half and stays where the frontier has it."; }
    part verifierProcedureIsASkillReviewGateR1 : TestResult { :>> id = "051b9930-f8cd-4586-9e0e-a584e0dc7c26"; :>> outcome = VerdictKind::proposed; :>> judgedAgainst = "24dbcfb"; :>> judgedAt = "2026-09-10"; :>> judgedBy = "claudeOpus5"; }
    verification verifierProcedureIsASkillCloseOutGate : Test { :>> id = "f1a536a8-4152-47ae-8d85-fe7b21d39600"; :>> title = "Sprint 664 closeOut gate (autonomous, D0049)"; :>> createdAt = "2026-09-11"; :>> createdBy = "claudeOpus5"; :>> method = VerificationMethod::inspect; :>> procedureText = "Sprint 664 closes on the verifier's receipt only (D0425): validate, check-engine, guard --no-receipt, sync-claude --check, clippy, probe664 on both cases, the touched receipt (empty stems, no keel-cli/src change) and the full suite receipt (720 passed, outcome pass, written 896 s after its start stamp - past the 600 s cap), and the verifier's own STATUS BEFORE / STATUS AFTER blocks compared line for line for the issue471 case (identical; the primary's md5 compare of the six authored files agreed). Gate and DoD results appended by the recorder from that receipt."; }
    part verifierProcedureIsASkillCloseOutGateR1 : TestResult { :>> id = "7851b845-f235-4257-8a64-f38433fd463e"; :>> outcome = VerdictKind::proposed; :>> judgedAgainst = "24dbcfb"; :>> judgedAt = "2026-09-10"; :>> judgedBy = "claudeOpus5"; }
    verification verifierProcedureIsASkillRetroGate : Test { :>> id = "3274502f-1279-4e90-9eae-41d8f89e2594"; :>> title = "Sprint 664 retro gate (autonomous, D0049)"; :>> createdAt = "2026-09-11"; :>> createdBy = "claudeOpus5"; :>> method = VerificationMethod::analyze; :>> procedureText = "AVOIDABLE-ISSUE SCAN: one new Issue this sprint - issue472 (Medium, in field): the suite receipt's at is the run's START (suite.rs:301 writes at: started) while the touched receipt's at is its END (touched.rs:342), so the verifier's '<at>launch: ok' on a one-second gap proved the receipt was this run's and not that the run finished; the primary read the duration from the receipt file's mtime (896 s) - tracked home dcReceiptAtMeansTheSameInBothReceipts, placed fourth by class. Avoidable: the skill's SUITE clause was written from the touched receipt's semantics without reading suite.rs; the check that caught it was the primary's own read of at against launch, which is D0388's rule applied to the verifier's row. The skill now names which stamp each receipt carries. FINDING 1: the DoD's ten-minute clause could not be met by the touched set because this sprint moved no Rust - the skill gained the full-suite clause so the case is exercised for real rather than deferred to the next Rust sprint, and the receipt's at/launch compare is what proves the run outlived the cap. FINDING 2: the probe pair was a scratchpad script run on HEAD's copy as the negative before the tree was read by the verifier (D0388), discarded rather than kept: the check is one-shot, its two cases are named in the DoD. FINDING 3, priority: the priority lens read 46 inversions before this sprint - three High items declared below twenty none-class ones - and the discharge was six moved lines; refineAssessPriority is a step the Refine ceremony owes every sprint, and the step's cost was under a minute."; }
    part verifierProcedureIsASkillRetroGateR1 : TestResult { :>> id = "d1e757f5-0d20-4558-b4a2-59154c676245"; :>> outcome = VerdictKind::proposed; :>> judgedAgainst = "24dbcfb"; :>> judgedAt = "2026-09-10"; :>> judgedBy = "claudeOpus5"; }
}
