// ProjectDeliveryS352 — Sprint 352: the human's D0159 acceptance asked for viewpoints to be switchable
// like processes. D0164 gives the activation contract a second namespace. CHANGE (§3a). 5 pts.
package ProjectDeliveryS352 {
    private import EngineElement::*;
    private import EngineWork::*;
    private import EngineVerification::*;
    private import EngineRelationships::*;

    #CharteredBy dependency from viewpointActivationStory to d0164;

    part viewpointActivationStory : Story {
        :>> id = "0d8005b0-0814-65b0-9b3e-0000003005b0";
        :>> title = "Sprint 352: viewpoints are activatable like processes (D0164) + the write-path regression I caught by round trip (issue156, 5 pts)";
        :>> createdAt = "2026-08-19"; :>> createdBy = "claudeOpus5"; :>> kind = WorkKind::code; :>> priority = WorkPriority::p0; :>> owner = "claudeOpus5"; :>> estimatedPoints = 5;
    }

    action def DeliveryRunS352 {
        action storyViewpointActivation;
        verification storyViewpointActivationDoD : Test { :>> id = "0d8005b1-0814-65b1-9b3e-0000003005b1"; :>> method = VerificationMethod::test; :>> procedureText = "THE HUMAN'S ACCEPTANCE OF D0159 CARRIED A REQUIREMENT BEYOND THE DECISION IT SIGNED: 'viewpoints should be activateable/disableable just like processes.' The gap was real and had already been measured while answering a different question (issue149): activation governs GUARDS, so `keel deactivate` reached 6 of 18 processes and NO viewpoint at all, while this repository declares 32. A project could refuse a process it did not want and could not refuse a LENS. DELIVERED under D0164 by dcViewpointActivation: `.engine/contracts/activation.toml` gains a `[viewpoints]` section read by the same loader under the same rule - absent means all active, declared-but-empty means none, so presence is matched rather than emptiness. Observed in `surfaces_json`, the ONE derivation behind both the console navigation and the act-surface obligation bar, and in the `viewpoint-renderer` guard which now skips an inactive lens exactly as a deactivated process's guards are skipped. `keel activation` lists all 32 with their state; `keel activate`/`deactivate` resolve a name in either namespace and REFUSE an ambiguous one. VERIFIED BY ROUND TRIP rather than by the command's own report: deactivate archDriftVP, `keel activation` shows INACTIVE, the manifest carries both sections with all six active processes preserved, /api/surfaces stops mentioning it (grep 1 -> 0); reactivate and delete the manifest to restore. validate 380 clean; check-engine clean; 36 guards ALL PASS; 191 tests; clippy clean."; }
        part storyViewpointActivationDoDR1 : TestResult { :>> id = "0d8005b2-0814-65b2-9b3e-0000003005b2"; :>> outcome = VerdictKind::pass; :>> judgedAgainst = "93b9447"; :>> judgedAt = "2026-08-19"; :>> judgedBy = "claudeOpus5"; }
    }

    verification vaRefineGate : Test { :>> id = "0d8005b3-0814-65b3-9b3e-0000003005b3"; :>> title = "Sprint 352 refine gate (DoR)"; :>> createdAt = "2026-08-19"; :>> createdBy = "claudeOpus5"; :>> method = VerificationMethod::inspect; :>> procedureText = "DoR. Their acceptance record carried THREE ideas and only the first is a bounded requirement: viewpoints switchable like processes. The other two - 'business ideas (like roles?)' and 'a composeable idea or kind of SDK that could drive other extensions' - describe a general extension mechanism of which process- and viewpoint-activation would be two instances. Scoped to the first, with the other two recorded as explicitly out of scope rather than absorbed: folding a speculative SDK into a Decision that implements one clear sentence is how draft 1 of D0161 went wrong. estimatedPoints=5."; }
    part vaRefineGateR1 : TestResult { :>> id = "0d8005b4-0814-65b4-9b3e-0000003005b4"; :>> outcome = VerdictKind::pass; :>> judgedAgainst = "93b9447"; :>> judgedAt = "2026-08-19"; :>> judgedBy = "claudeOpus5"; }

    verification vaStandupGate : Test { :>> id = "0d8005b5-0814-65b5-9b3e-0000003005b5"; :>> title = "Sprint 352 standup gate"; :>> createdAt = "2026-08-19"; :>> createdBy = "claudeOpus5"; :>> method = VerificationMethod::inspect; :>> procedureText = "APPLIED RATHER THAN HELD FOR ACCEPTANCE, which reverses what sprints 341, 345 and 348 did, and the distinction is stated so it can be disagreed with: those changed a process DEFINITION or asked for an exception to a stated invariant, and neither had been requested in the human's own words. This implements a sentence they wrote in an acceptance record, using a mechanism that mirrors a contract they have already accepted (D0138), and it adds no invariant and no exception. Their standing instruction is that a needed signature is not a blocker. If they reject the mechanism it comes out, and D0164 states the removal path. Approach: TWO namespaces in one contract rather than making viewpoints into units - a unit bundles guards and activation switches enforcement, while a viewpoint is a lens and switching it changes what the project looks at; forcing the second into the first would mean inventing a guard per viewpoint to give it something to switch. No blockers."; }
    part vaStandupGateR1 : TestResult { :>> id = "0d8005b6-0814-65b6-9b3e-0000003005b6"; :>> outcome = VerdictKind::pass; :>> judgedAgainst = "93b9447"; :>> judgedAt = "2026-08-19"; :>> judgedBy = "claudeOpus5"; }

    verification vaImplementGate : Test { :>> id = "0d8005b7-0814-65b7-9b3e-0000003005b7"; :>> title = "Sprint 352 implement gate"; :>> createdAt = "2026-08-19"; :>> createdBy = "claudeOpus5"; :>> method = VerificationMethod::test; :>> procedureText = "THE DESIGN CHOICE I WOULD DEFEND HARDEST IS WHAT DOES *NOT* OBSERVE ACTIVATION. `concern-coverage` still reports a deactivated viewpoint's concern, deliberately: its whole purpose is to audit which stakeholder concerns are SERVED, so suppressing inactive lenses would let a project reach full concern coverage by switching off the concerns it was failing - the Goodhart failure §1.7 warns about, reachable in one command. An inactive lens is a deliberate choice and must stay visible as one; hiding it would convert a choice into an invisible gap. issue156, MY OWN REGRESSION, AND HOW IT WAS CAUGHT: extending `write_activation` to emit both sections I changed its first parameter from the repo root to a pre-joined directory and dropped the `.engine/contracts` join, while every caller kept passing the root - so the manifest landed at `<root>/activation.toml`, where the loader never looks. `keel deactivate` printed `deactivated viewpoint` and changed nothing, and THE OUTPUT WAS IDENTICAL IN THE WORKING AND BROKEN CASE. What caught it was checking the EFFECT rather than the report: /api/surfaces still mentioned the viewpoint when it had to be gone. Restored the join inside the function so callers pass a root and the function owns the path, and re-ran the round trip after the clippy refactor that extracted `switch_viewpoint`, because a lint fix that moves code is exactly when a path regression sneaks back. THE WRITER EMITS BOTH SECTIONS ALWAYS: absence means everything active, so writing only the edited section would silently re-activate every process the project had turned off - a data-loss bug, not a convenience."; }
    part vaImplementGateR1 : TestResult { :>> id = "0d8005b8-0814-65b8-9b3e-0000003005b8"; :>> outcome = VerdictKind::pass; :>> judgedAgainst = "93b9447"; :>> judgedAt = "2026-08-19"; :>> judgedBy = "claudeOpus5"; }

    verification vaReviewGate : Test { :>> id = "0d8005b9-0814-65b9-9b3e-0000003005b9"; :>> title = "Sprint 352 review gate"; :>> createdAt = "2026-08-19"; :>> createdBy = "claudeOpus5"; :>> method = VerificationMethod::inspect; :>> procedureText = "Reviewed. THE ADOPTION ARGUMENT IS THE REAL ONE and it is D0054's: a downstream project taking keel inherited all 32 of THIS project's declared lenses whether or not any described a concern it held, and every one of them appeared in its console navigation. That is precisely the authoring-and-adoption friction D0054 names as the dominant MBSE failure mode, and it was invisible from inside a repository that wants all 32. The human found it from the position of someone thinking about other people using this - the same position that found the last five console defects. WHAT I LEFT OUT ON PURPOSE: roles, a composable extension SDK, and any per-actor scoping. Their acceptance note raised all three and they are a larger design; recorded as explicitly out of scope in D0164 rather than sketched, because a sketch inside an implementing Decision becomes the design by default. ONE HONEST NOTE ON PROCESS: this sprint APPLIED a proposed Decision, which the three sprints before it deliberately did not. The reason is stated in the standup gate and is narrow - their own words, a mirror of an accepted contract, no new invariant - and if that reasoning is wrong then the right correction is to revert the code, not to reinterpret the record."; }
    part vaReviewGateR1 : TestResult { :>> id = "0d8005ba-0814-65ba-9b3e-0000003005ba"; :>> outcome = VerdictKind::pass; :>> judgedAgainst = "93b9447"; :>> judgedAt = "2026-08-19"; :>> judgedBy = "claudeOpus5"; }

    verification vaCloseOutGate : Test { :>> id = "0d8005bb-0814-65bb-9b3e-0000003005bb"; :>> title = "Sprint 352 closeOut gate (autonomous, D0049)"; :>> createdAt = "2026-08-19"; :>> createdBy = "claudeOpus5"; :>> method = VerificationMethod::inspect; :>> procedureText = "Autonomous closeOut (D0049). D0159 is ACCEPTED by the human and their acceptance is committed alone, attributed to them, never mixed with my work. D0164 is PROPOSED AND APPLIED, with its reasoning for applying stated rather than assumed. issue156 recorded and resolved. Doc-sync rode along: CLAUDE.md section 4 now states that adoption is declared for processes AND viewpoints, what deactivating a lens does, and why concern-coverage still reports it. THE REPOSITORY IS UNCHANGED IN BEHAVIOUR: `.engine/contracts/activation.toml` does not exist here, so everything remains active - my round-trip test created it, exercised it, and deleted it. pendingAcceptances d0161, d0162, d0163, d0164. validate 380 clean; check-engine clean; 36 guards ALL PASS; 191 tests; clippy clean."; }
    part vaCloseOutGateR1 : TestResult { :>> id = "0d8005bc-0814-65bc-9b3e-0000003005bc"; :>> outcome = VerdictKind::pass; :>> judgedAgainst = "93b9447"; :>> judgedAt = "2026-08-19"; :>> judgedBy = "claudeOpus5"; }

    verification vaRetroGate : Test { :>> id = "0d8005bd-0814-65bd-9b3e-0000003005bd"; :>> title = "Sprint 352 retro gate (autonomous, D0049)"; :>> createdAt = "2026-08-19"; :>> createdBy = "claudeOpus5"; :>> method = VerificationMethod::analyze; :>> procedureText = "Autonomous retro (D0049) under D0131's retroTrack. AVOIDABLE-ISSUE: I broke the manifest's write path while extending it, and the command reported success either way. The specific error - repointing a parameter from a root to a pre-joined directory while leaving callers alone - is the kind a type system cannot catch because both are `&Path`, and it produced a command that lied. THE LESSON IS THE ONE THIS SESSION KEEPS TEACHING: verify the EFFECT, not the report. That is now four separate occasions - the fingerprint instrument reading rather than the wall clock, the request log rather than my reading of the source, the guard failing on a reintroduced defect rather than passing on a clean tree, and today /api/surfaces rather than `deactivated viewpoint`. In every case the report was available and agreeable and the effect was the only thing that settled it. WELL: (1) the round trip was written before trusting the command, which is the only reason this is a footnote; (2) it was re-run after a lint refactor moved the code, because that is when path bugs return; (3) `concern-coverage` was deliberately left observing ALL viewpoints, closing a one-command route to fake concern coverage that the obvious implementation would have opened; (4) the human's two larger ideas were recorded as out of scope rather than half-designed; (5) the decision to APPLY rather than hold was argued explicitly against the three prior sprints that held, so it can be judged rather than merely noticed. Estimate 5 pts, delivered."; }
    part vaRetroGateR1 : TestResult { :>> id = "0d8005be-0814-65be-9b3e-0000003005be"; :>> outcome = VerdictKind::pass; :>> judgedAgainst = "93b9447"; :>> judgedAt = "2026-08-19"; :>> judgedBy = "claudeOpus5"; }
}
