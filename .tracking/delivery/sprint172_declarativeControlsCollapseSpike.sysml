// ProjectDeliveryS172 — Sprint 172: declarativeControlsCollapseSpike (RESEARCH spike).
// De-risk D0105 (proposed) BEFORE committing to the guard->rule migration: express the 3 hardest guards
// (ceremony, charter, sprint-coverage — git-temporal/grandfathered/keyword) as declared rules and judge
// whether the vocabulary stays bounded (critique C4). DOGFOODS issue055: a WorkKind::research Story
// #CharteredBy a status=proposed Decision (D0105) — the charter the guard already permits. EXECUTE. 1 pt. AUTONOMOUS (D0049).
package ProjectDeliveryS172 {
    private import EngineElement::*;
    private import EngineWork::*;
    private import EngineVerification::*;
    private import EngineRelationships::*;

    #CharteredBy dependency from declarativeControlsCollapseSpikeStory to d0105;

    part declarativeControlsCollapseSpikeStory : Story {
        :>> id = "63940516-2c7d-4e8f-c172-51627384c001";
        :>> title = "Sprint 172: declarativeControlsCollapseSpike (1 pt) - de-risk D0105's 8-of-14 collapse against the 3 hardest guards";
        :>> createdAt = "2026-07-01"; :>> createdBy = "claudeOpus"; :>> kind = WorkKind::research; :>> priority = WorkPriority::p2; :>> owner = "claudeOpus"; :>> estimatedPoints = 1;
    }

    action def DeliveryRunS172 {
        action storyCollapseSpike;
        verification storyCollapseSpikeDoD : Test { :>> id = "63940516-2c7d-4e8f-c172-51627384c002"; :>> method = VerificationMethod::analyze; :>> procedureText = "De-risk spike for D0105 (critique C4): read the real implementations (guards.rs/algo.rs) of the 3 hardest guards and express each as a declared rule. FINDING: the collapse HOLDS but D0105's scope was understated. charter = EdgeRule(Story->#CharteredBy) + scope newlyAdded(git-diff) + numeric cutoff sprintNum>=38; sprint-coverage = EdgeRule(done Action<-covered-by<-Story) - CLEANER than today's text-contains if coverage becomes a typed edge - + scope status=done + exemption set; ceremony = (a) gate-ordering = a THIRD rule kind (succession-conformance, reads the workflow first..then at instance level) + (b) retro-scan = ElementRule matchesPattern(retro.text,{avoidable,...}) + exemption set. VERDICT: predicates stay small; complexity migrates into 3 BOUNDED, reusable additions - a ~4-predicate SCOPE sub-language (the real inner-platform danger zone), a third OrderingRule kind, and a declared exemption mechanism. Vocabulary does NOT become a general language. D0105 PROCEEDS with scope corrected upward (3 rule kinds + scope sub-language + exemptions, not 2 shapes + 8 predicates); re-validate 'flat code' against that surface; parity gate governs cutover. Recorded in docs/proposals/2026-06-30-declarative-controls-issue054.md sec 10."; }
        part storyCollapseSpikeDoDR1 : TestResult { :>> id = "63940516-2c7d-4e8f-c172-51627384c003"; :>> outcome = VerdictKind::pass; :>> judgedAgainst = "fabe838"; :>> judgedAt = "2026-07-01"; :>> judgedBy = "claudeOpus"; }
    }

    verification collapseSpikeRefineGate : Test { :>> id = "63940516-2c7d-4e8f-c172-51627384c004"; :>> title = "Sprint 172 refine gate (DoR)"; :>> createdAt = "2026-07-01"; :>> createdBy = "claudeOpus"; :>> method = VerificationMethod::inspect; :>> procedureText = "DoR: critique C4 (the biggest, unvalidated risk in D0105) — is the 8-of-14 guard collapse real once the messy guards are expressed as rules? A research spike (analysis, no frozen-core code) chartered to D0105 (proposed). estimatedPoints=1. #CharteredBy d0105. DoR met. NOTE: this is the FIRST research spike chartered to a proposed Decision — dogfoods issue055 (the charter guard already permits it)."; }
    part collapseSpikeRefineGateR1 : TestResult { :>> id = "63940516-2c7d-4e8f-c172-51627384c005"; :>> outcome = VerdictKind::pass; :>> judgedAgainst = "fabe838"; :>> judgedAt = "2026-07-01"; :>> judgedBy = "claudeOpus"; }
    verification collapseSpikeStandupGate : Test { :>> id = "63940516-2c7d-4e8f-c172-51627384c006"; :>> title = "Sprint 172 standup gate"; :>> createdAt = "2026-07-01"; :>> createdBy = "claudeOpus"; :>> method = VerificationMethod::inspect; :>> procedureText = "Approach: read guards.rs/algo.rs for ceremony/charter/sprint-coverage; map each to EdgeRule/ElementRule/ordering; enumerate the NEW capabilities each demands; judge whether the vocabulary stays bounded. No blockers; analysis only."; }
    part collapseSpikeStandupGateR1 : TestResult { :>> id = "63940516-2c7d-4e8f-c172-51627384c007"; :>> outcome = VerdictKind::pass; :>> judgedAgainst = "fabe838"; :>> judgedAt = "2026-07-01"; :>> judgedBy = "claudeOpus"; }
    verification collapseSpikeImplementGate : Test { :>> id = "63940516-2c7d-4e8f-c172-51627384c008"; :>> title = "Sprint 172 implement gate (the analysis)"; :>> createdAt = "2026-07-01"; :>> createdBy = "claudeOpus"; :>> method = VerificationMethod::analyze; :>> procedureText = "Analysis complete + recorded (proposal doc sec 10 + the DoD): collapse holds; complexity migrates into a bounded scope sub-language + a third OrderingRule kind + a declared exemption mechanism; D0105 scope corrected upward. The scope sub-language is the inner-platform danger zone -> cap it via a meta-rule."; }
    part collapseSpikeImplementGateR1 : TestResult { :>> id = "63940516-2c7d-4e8f-c172-51627384c009"; :>> outcome = VerdictKind::pass; :>> judgedAgainst = "fabe838"; :>> judgedAt = "2026-07-01"; :>> judgedBy = "claudeOpus"; }
    verification collapseSpikeReviewGate : Test { :>> id = "63940516-2c7d-4e8f-c172-51627384c00a"; :>> title = "Sprint 172 review gate"; :>> createdAt = "2026-07-01"; :>> createdBy = "claudeOpus"; :>> method = VerificationMethod::inspect; :>> procedureText = "Reviewed. The spike did its job: it CONFIRMED D0105's direction while FALSIFYING my initial 'two shapes + 8 predicates' scope — an honest de-risk outcome, not a rubber-stamp. The finding is actionable (correct D0105's scope; cap the scope vocabulary) and the risk is now named + bounded rather than latent. Clean."; }
    part collapseSpikeReviewGateR1 : TestResult { :>> id = "63940516-2c7d-4e8f-c172-51627384c00b"; :>> outcome = VerdictKind::pass; :>> judgedAgainst = "fabe838"; :>> judgedAt = "2026-07-01"; :>> judgedBy = "claudeOpus"; }
    verification collapseSpikeCloseOutGate : Test { :>> id = "63940516-2c7d-4e8f-c172-51627384c00c"; :>> title = "Sprint 172 closeOut gate (autonomous, D0049)"; :>> createdAt = "2026-07-01"; :>> createdBy = "claudeOpus"; :>> method = VerificationMethod::inspect; :>> procedureText = "Autonomous closeOut (D0049): DoD pass; the C4 risk is de-risked (collapse holds, scope corrected upward + bounded). Design artifact updated (proposal sec 10). keel validate + guard all green. Self-evidencing (D0051)."; }
    part collapseSpikeCloseOutGateR1 : TestResult { :>> id = "63940516-2c7d-4e8f-c172-51627384c00d"; :>> outcome = VerdictKind::pass; :>> judgedAgainst = "fabe838"; :>> judgedAt = "2026-07-01"; :>> judgedBy = "claudeOpus"; }
    verification collapseSpikeRetroGate : Test { :>> id = "63940516-2c7d-4e8f-c172-51627384c00e"; :>> title = "Sprint 172 retro gate (autonomous, D0049)"; :>> createdAt = "2026-07-01"; :>> createdBy = "claudeOpus"; :>> method = VerificationMethod::analyze; :>> procedureText = "Autonomous retro (D0049). WELL: the spike falsified an over-claim BEFORE it cost a migration — de-risking a proposed decision is cheaper than discovering the scope gap mid-implementation; and it dogfooded issue055 (first research spike chartered to a proposed Decision, charter green). AVOIDABLE-ISSUE SCAN: the avoidable issue was MINE — I asserted the 8-of-14 collapse as 'two shapes + 8 predicates' without stress-testing the git-temporal/grandfathered/ordering guards; LESSON: a reduction claim must be tested against the WORST cases before it's presented as settled, and big design claims deserve a de-risk spike, not just prose. Estimate 1 pt held. The scope sub-language is now the named risk to watch (process improvement: cap it via a meta-rule)."; }
    part collapseSpikeRetroGateR1 : TestResult { :>> id = "63940516-2c7d-4e8f-c172-51627384c00f"; :>> outcome = VerdictKind::pass; :>> judgedAgainst = "fabe838"; :>> judgedAt = "2026-07-01"; :>> judgedBy = "claudeOpus"; }
}
