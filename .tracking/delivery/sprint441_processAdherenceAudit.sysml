// ProjectDeliveryS441 — Sprint 441: keel audit-adherence (D0209 clause 1): CI re-derives from the tree that no control was disarmed unsigned - rigor around the AI, not the human. EXECUTE. 2 pts.
package ProjectDeliveryS441 {
    private import EngineElement::*;
    private import EngineWork::*;
    private import EngineVerification::*;
    private import EngineRelationships::*;

    #CharteredBy dependency from processAdherenceAuditStory to d0209;

    part processAdherenceAuditStory : Story {
        :>> id = "d0df6176-fdf3-4019-b6ba-bb662f05993e";
        :>> title = "Sprint 441: the tree proves the agent followed the process (2 pts)";
        :>> createdAt = "2026-08-24"; :>> createdBy = "claudeFable5"; :>> kind = WorkKind::code; :>> priority = WorkPriority::p0; :>> owner = "claudeFable5"; :>> estimatedPoints = 2;
    }

    action def DeliveryRunS441 {
        action storyProcessAdherenceAudit;
        verification storyProcessAdherenceAuditDoD : Test { :>> id = "ccda2351-0249-4928-9e09-d13b33df6518"; :>> method = VerificationMethod::test; :>> procedureText = "DELIVERED: dcProcessAdherenceAudit (D0209 clause 1, the manager-inversion panel's unanimous #1). keel audit-adherence [--since REF]: re-derives the ENFORCEMENT SIGNATURE (every rule's severity + every guard-constraint binding) from each commit's tree via git show - no checkout, CI-fast - and flags any commit where a severity WEAKENED or a rule/binding VANISHED versus its parent WITHOUT a co-committed #ProspectiveChange/#SafetyChange Decision (the keystone, re-derived from the tree). It is a GATE (exit 1 on violation), unlike audit-history's report, because a silently-disarmed control is not honest state - it is a lie the tree can prove. Wired into ci.yml so it runs on infra the agent cannot touch. This is the direct answer to the human's ask ('rigor around AI following processes'): the one checker the agent cannot run on itself or fake, catching the exact issue236 self-modification class EVEN WHEN THE COMMIT HOOK IS BYPASSED. VERIFIED: the real 12-commit history PASSes; a hook-bypassed (--no-verify, hooksPath=/dev/null) unsigned flip of a blocking rule to warning in a throwaway worktree returned exit 1 naming the rule ('capabilityRootednessRule: blocking/bound -> warning ... the keystone was bypassed'); the clean history passes; unit tests pin the severity ranking. D0209 chartered the remaining clauses (freeze the enforcement surface, process cursor, proactive post-edit) as follow-on; the opt-in orchestrator stays deferred."; }
        part storyProcessAdherenceAuditDoDR1 : TestResult { :>> id = "d45c0d06-3295-4178-be7a-fca06f317890"; :>> outcome = VerdictKind::pass; :>> judgedAgainst = "be3e4c1692b29e9502e3047bc866a27259b3e2fe"; :>> judgedAt = "2026-08-24"; :>> judgedBy = "claudeFable5"; }
    }

    verification processAdherenceAuditRefineGate : Test { :>> id = "6a18a4b4-4c24-43aa-8710-00df5588bcc8"; :>> title = "Sprint 441 refine gate (DoR)"; :>> createdAt = "2026-08-24"; :>> createdBy = "claudeFable5"; :>> method = VerificationMethod::inspect; :>> procedureText = "DoR. Delivers clause 1 of D0209, the panel's unanimous first build and the human's explicit ask (rigor around the AI). Scope: the audit + its CI wiring + probes. The other clauses are chartered separately. 2 points."; }
    part processAdherenceAuditRefineGateR1 : TestResult { :>> id = "edeeeefe-2331-44c0-b6e3-f48f7ed54dbc"; :>> outcome = VerdictKind::pass; :>> judgedAgainst = "be3e4c1692b29e9502e3047bc866a27259b3e2fe"; :>> judgedAt = "2026-08-24"; :>> judgedBy = "claudeFable5"; }
    verification processAdherenceAuditStandupGate : Test { :>> id = "b51e7f05-2910-45b5-b4d9-ec2ebe646755"; :>> title = "Sprint 441 standup gate"; :>> createdAt = "2026-08-24"; :>> createdBy = "claudeFable5"; :>> method = VerificationMethod::inspect; :>> procedureText = "Approach: extend the audit-history pattern (re-derive from the tree, trust no committed claim) but CHEAPLY - read severities via git show, not a full checkout+gate per commit - so it can gate in CI on every push; make it a GATE not a report because a disarmed control is a provable lie, not merely unflattering state; the keystone (signed decision) is the sanctioned exception, re-derived from the same tree. No blockers."; }
    part processAdherenceAuditStandupGateR1 : TestResult { :>> id = "e3404f21-0ec9-4230-93d2-834384f5f8cc"; :>> outcome = VerdictKind::pass; :>> judgedAgainst = "be3e4c1692b29e9502e3047bc866a27259b3e2fe"; :>> judgedAt = "2026-08-24"; :>> judgedBy = "claudeFable5"; }
    verification processAdherenceAuditImplementGate : Test { :>> id = "a31a00ff-9db7-4537-a636-971ae8766ab4"; :>> title = "Sprint 441 implement gate"; :>> createdAt = "2026-08-24"; :>> createdBy = "claudeFable5"; :>> method = VerificationMethod::test; :>> procedureText = "Verified by running: audit-adherence over HEAD~12 PASS on real history; the hook-bypassed negative probe (git commit --no-verify with hooksPath=/dev/null, the exact issue116 bypass) returned exit 1 with the weakened rule named; cargo test (severity-rank unit tests) green; workspace clippy clean; the ci.yml step added after audit-history. NOT covered by this clause (stated): gate-of-record and evidence-resolvability are already audit-history's job; guard-set monotonicity was the one missing piece and is what this adds."; }
    part processAdherenceAuditImplementGateR1 : TestResult { :>> id = "548e5da9-4fb0-4e28-b9bc-e27f030bbcdd"; :>> outcome = VerdictKind::pass; :>> judgedAgainst = "be3e4c1692b29e9502e3047bc866a27259b3e2fe"; :>> judgedAt = "2026-08-24"; :>> judgedBy = "claudeFable5"; }
    verification processAdherenceAuditReviewGate : Test { :>> id = "d05cdff6-4a05-45f2-ae91-60c3b721e01f"; :>> title = "Sprint 441 review gate — three passes per D0172"; :>> createdAt = "2026-08-24"; :>> createdBy = "claudeFable5"; :>> method = VerificationMethod::inspect; :>> procedureText = "PASS 1, CLAIMS: the exit-1 negative probe and the PASS on real history are quoted read-backs. PASS 2, BOUNDARY: the audit's TCB is CI's pinned keel binary + the signed rules it reads (the formal-methods lens's De Bruijn point) - a compromised CI binary defeats it, which is why clause 2 (freeze the enforcement surface, incl. CI workflow files) is chartered next; stated, not hidden. Also: it checks SEVERITY monotonicity and binding-presence, not that a guard's LOGIC wasn't gutted while keeping its name/severity - a rule kept 'blocking' but rewritten to check nothing would pass; that residual belongs to code review + the control-eval's recurring attack, noted. PASS 3, OWN DIFF: two negative probes read false-PASS first - the first because the local hook correctly REFUSED the sneaky commit (so nothing landed to catch), the second because --since HEAD~1 gave a 1-commit range with nothing to compare; the real test needed the hook BYPASSED and the parent IN range, which is exactly the threat model - the probe design taught the threat model. WHAT A REVIEWER SHOULD ATTACK: the --since HEAD~50 default in CI - a push deeper than 50 commits past the merge-base would under-scan; github.event.before covers the normal case."; }
    part processAdherenceAuditReviewGateR1 : TestResult { :>> id = "57e705f0-cd18-40e3-a0af-0cb4ea972246"; :>> outcome = VerdictKind::pass; :>> judgedAgainst = "be3e4c1692b29e9502e3047bc866a27259b3e2fe"; :>> judgedAt = "2026-08-24"; :>> judgedBy = "claudeFable5"; }
    verification processAdherenceAuditCloseOutGate : Test { :>> id = "a288ab0d-d7d0-4bf3-8598-89fe7ae207ad"; :>> title = "Sprint 441 closeOut gate (autonomous, D0049)"; :>> createdAt = "2026-08-24"; :>> createdBy = "claudeFable5"; :>> method = VerificationMethod::inspect; :>> procedureText = "Autonomous closeOut (D0049). D0209 clause 1 delivered; the panel dossier + knowledge record committed; validate + all 48 guards + the new audit green; the remaining D0209 clauses are on the frontier."; }
    part processAdherenceAuditCloseOutGateR1 : TestResult { :>> id = "fd5411cf-fbe1-46b5-95e8-27d30ab40099"; :>> outcome = VerdictKind::pass; :>> judgedAgainst = "be3e4c1692b29e9502e3047bc866a27259b3e2fe"; :>> judgedAt = "2026-08-24"; :>> judgedBy = "claudeFable5"; }
    verification processAdherenceAuditRetroGate : Test { :>> id = "03ee815f-3741-416d-8ca1-590c8949bbf1"; :>> title = "Sprint 441 retro gate (autonomous, D0049)"; :>> createdAt = "2026-08-24"; :>> createdBy = "claudeFable5"; :>> method = VerificationMethod::analyze; :>> procedureText = "Autonomous retro (D0049). AVOIDABLE-ISSUE SCAN under rcRecurrence: the negative-probe-reads-false-PASS class recurred (as in the control eval) - a probe that does not reproduce the exact threat state (hook bypassed, parent in range) reports a false negative, which for a CONTROL is the dangerous direction; the durable rule, now twice-learned: a control's negative probe must reproduce the real bypass, not a blocked attempt. WELL: the human asked for rigor around the AI and got, same session, a CI gate that catches the AI disarming its own controls even with the commit hook bypassed - honesty architecture taking its first real step toward control architecture, exactly where the two panels said the leverage was. Estimate 2 pts, delivered 2."; }
    part processAdherenceAuditRetroGateR1 : TestResult { :>> id = "997e3735-62ab-47e7-ad43-2f2ba362e5ea"; :>> outcome = VerdictKind::pass; :>> judgedAgainst = "be3e4c1692b29e9502e3047bc866a27259b3e2fe"; :>> judgedAt = "2026-08-24"; :>> judgedBy = "claudeFable5"; }
}
