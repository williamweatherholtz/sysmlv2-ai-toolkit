// ProjectDeliveryS297 — Sprint 297: a process becomes a MOVABLE unit — list/search/show/export/import
// (keelProcessPortability, D0128). EXECUTE. 8 pts.
package ProjectDeliveryS297 {
    private import EngineElement::*;
    private import EngineWork::*;
    private import EngineVerification::*;
    private import EngineRelationships::*;

    #CharteredBy dependency from portabilityStory to d0144;

    part portabilityStory : Story {
        :>> id = "0d80023f-0814-623f-9b3e-00000030023f";
        :>> title = "Sprint 297: keel process — the catalogue, and a unit that actually moves (8 pts)";
        :>> createdAt = "2026-08-15"; :>> createdBy = "claudeOpus5"; :>> kind = WorkKind::code; :>> priority = WorkPriority::p0; :>> owner = "claudeOpus5"; :>> estimatedPoints = 8;
    }

    action def DeliveryRunS297 {
        action storyPortability;
        verification storyPortabilityDoD : Test { :>> id = "0d800240-0814-6240-9b3e-000000300240"; :>> method = VerificationMethod::demo; :>> procedureText = "Delivers keelProcessPortability; satisfies srPortCatalogExchange and srPortModularProcessUnit (D0128). `activate`/`deactivate`/`activation` already toggled enforcement by unit (D0138); what was missing is the half that PROVES a unit is self-contained — taking one out and putting it into another project. DELIVERED `keel process list | search <term> | show <name> | export <name> --out <dir> | import <dir>`. THE EXPORT FOUND A REAL DEFECT IN THE UNIT MODEL: `units_from_model` hardcoded `skills: Vec::new()`, so every unit carried only its GUARDS, and the first export copied the process definition and LEFT THE DEPLOYING SKILL BEHIND — precisely the failure srPortModularProcessUnit names, 'without leaving its enforcement behind'. Fixed by deriving the skill from the skill registry using the SAME convention the `process-skill` guard already enforces (a deploying skill's purpose names the `.engine/processes/<name>.sysml` it deploys), rather than inventing a second mapping that could disagree with the guard. VERIFIED BY FULL ROUND TRIP between two projects: `export doc-sync` produced 2 files + a `unit.toml` naming the 1 guard the receiver must activate; a separate `keel init` project with doc-sync REMOVED imported it, and `process show` there lists both the definition and the SKILL; the receiver's own gate stays green (validate clean, 31 guards exit 0); a second import REFUSES on the name collision rather than overwriting. The manifest is what makes it a unit rather than loose files: importing the files installs the process, and the named guards are what the receiver must activate for the enforcement to travel. NOT BUILT, and stated: 'opt-in popularity' appears in the backlog item's prose but in NO requirement — srPortCatalogExchange stops at palette plus BYO — and it would send usage data outward, which is a human's decision rather than a detail of this command. clippy clean; 137 lib tests."; }
        part storyPortabilityDoDR1 : TestResult { :>> id = "0d800241-0814-6241-9b3e-000000300241"; :>> outcome = VerdictKind::pass; :>> judgedAgainst = "76635b4"; :>> judgedAt = "2026-08-15"; :>> judgedBy = "claudeOpus5"; }
    }

    verification ppRefineGate : Test { :>> id = "0d800242-0814-6242-9b3e-000000300242"; :>> title = "Sprint 297 refine gate (DoR)"; :>> createdAt = "2026-08-15"; :>> createdBy = "claudeOpus5"; :>> method = VerificationMethod::inspect; :>> procedureText = "DoR. CONSUMER CHECK (dorConsumer, D0144): the consumer of an exported unit is ANOTHER PROJECT, which is why the acceptance test had to be a round trip into a second `keel init` tree rather than an inspection of the output directory. Reading the requirement statements first also narrowed the scope honestly — the item's prose lists 'opt-in popularity', and neither open requirement asks for it. estimatedPoints=8. DoR met."; }
    part ppRefineGateR1 : TestResult { :>> id = "0d800243-0814-6243-9b3e-000000300243"; :>> outcome = VerdictKind::pass; :>> judgedAgainst = "76635b4"; :>> judgedAt = "2026-08-15"; :>> judgedBy = "claudeOpus5"; }

    verification ppStandupGate : Test { :>> id = "0d800244-0814-6244-9b3e-000000300244"; :>> title = "Sprint 297 standup gate"; :>> createdAt = "2026-08-15"; :>> createdBy = "claudeOpus5"; :>> method = VerificationMethod::inspect; :>> procedureText = "Approach: build export first and RUN it, because an export is the only honest test of self-containment — a diagram of a unit's parts proves nothing about whether the parts travel. That ordering is what surfaced the missing skill on the very first export. No blockers."; }
    part ppStandupGateR1 : TestResult { :>> id = "0d800245-0814-6245-9b3e-000000300245"; :>> outcome = VerdictKind::pass; :>> judgedAgainst = "76635b4"; :>> judgedAt = "2026-08-15"; :>> judgedBy = "claudeOpus5"; }

    verification ppImplementGate : Test { :>> id = "0d800246-0814-6246-9b3e-000000300246"; :>> title = "Sprint 297 implement gate"; :>> createdAt = "2026-08-15"; :>> createdBy = "claudeOpus5"; :>> method = VerificationMethod::test; :>> procedureText = "The skill derivation reuses the `process-skill` guard's convention deliberately. A second mapping — say, assuming `.engine/skills/<process-name>/` — would work today for every process here and would silently diverge the moment a skill directory were named differently, with the guard passing and the export dropping the file. Reading the registry the guard reads means the two cannot disagree. RULES are NOT carried in the bundle, and that is recorded rather than quietly skipped: a rule lives in a shared file alongside other processes' rules, so exporting it would either copy other processes' rules or require splitting the file, which is a schema-shaped change and not an export detail. The manifest names them instead."; }
    part ppImplementGateR1 : TestResult { :>> id = "0d800247-0814-6247-9b3e-000000300247"; :>> outcome = VerdictKind::pass; :>> judgedAgainst = "76635b4"; :>> judgedAt = "2026-08-15"; :>> judgedBy = "claudeOpus5"; }

    verification ppReviewGate : Test { :>> id = "0d800248-0814-6248-9b3e-000000300248"; :>> title = "Sprint 297 review gate"; :>> createdAt = "2026-08-15"; :>> createdBy = "claudeOpus5"; :>> method = VerificationMethod::inspect; :>> procedureText = "Reviewed. `import` says NOT YET ENFORCED and tells the receiver to run `keel activate`, which is the honest reading of what an import does: it installs a process, it does not adopt one. Silently activating on import would have been friendlier and would have made adoption implicit — the exact defect D0138 was written to remove (issues 089 and 090 were both 'what has this project adopted?' answered by inference). The collision refusal borrows D0108's reasoning: two processes of one name are not a merge, they are a collision, and a non-owner never overwrites in place."; }
    part ppReviewGateR1 : TestResult { :>> id = "0d800249-0814-6249-9b3e-000000300249"; :>> outcome = VerdictKind::pass; :>> judgedAgainst = "76635b4"; :>> judgedAt = "2026-08-15"; :>> judgedBy = "claudeOpus5"; }

    verification ppCloseOutGate : Test { :>> id = "0d80024a-0814-624a-9b3e-00000030024a"; :>> title = "Sprint 297 closeOut gate (autonomous, D0049)"; :>> createdAt = "2026-08-15"; :>> createdBy = "claudeOpus5"; :>> method = VerificationMethod::inspect; :>> procedureText = "Autonomous closeOut (D0049). keelProcessPortability carries a passing DoD TestResult; srPortCatalogExchange and srPortModularProcessUnit are both satisfied and edge-linked. Round trip demonstrated between two projects; the unit-model defect found and fixed. clippy clean; 137 lib tests; validate 320 clean; check-engine clean; 31 guards green. No gate bypassed."; }
    part ppCloseOutGateR1 : TestResult { :>> id = "0d80024b-0814-624b-9b3e-00000030024b"; :>> outcome = VerdictKind::pass; :>> judgedAgainst = "76635b4"; :>> judgedAt = "2026-08-15"; :>> judgedBy = "claudeOpus5"; }

    verification ppRetroGate : Test { :>> id = "0d80024c-0814-624c-9b3e-00000030024c"; :>> title = "Sprint 297 retro gate (autonomous, D0049)"; :>> createdAt = "2026-08-15"; :>> createdBy = "claudeOpus5"; :>> method = VerificationMethod::analyze; :>> procedureText = "Autonomous retro (D0049) under D0131's retroTrack. WELL: (1) building EXPORT first and running it immediately found that units carried no skill — a defect that had sat in `units_from_model` as a hardcoded empty vector since activation was built, invisible because nothing had ever tried to move a unit; (2) the round trip went into a SECOND project rather than a directory listing, which is the only test that means anything for portability; (3) 'opt-in popularity' was dropped with the reason stated — it is in the item's prose and in no requirement, and it sends data outward. AVOIDABLE-ISSUE 1: I wrote a 156-line command function and clippy blocked it, then shrank `main` past its own limit in the same pass. Both are style limits doing their job, but the underlying habit is real: a match arm that grows a body instead of calling a named function makes the dispatcher unreadable and hides where behaviour lives. NO NEW ITEM, reason stated: the lint IS the control and it fired both times before commit. What is worth carrying forward is the shape — a subcommand arm should be one line calling `cmd_<verb>`, which is now true for every arm this sprint touched. Estimate 8 pts, delivered."; }
    part ppRetroGateR1 : TestResult { :>> id = "0d80024d-0814-624d-9b3e-00000030024d"; :>> outcome = VerdictKind::pass; :>> judgedAgainst = "76635b4"; :>> judgedAt = "2026-08-15"; :>> judgedBy = "claudeOpus5"; }
}
