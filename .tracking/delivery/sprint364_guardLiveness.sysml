// ProjectDeliveryS364 — Sprint 364: hardening round 4. Three guards reported 0 scanned while enforcing;
// the in-loop hook could wedge the build it gates. EXECUTE. 5 pts.
package ProjectDeliveryS364 {
    private import EngineElement::*;
    private import EngineWork::*;
    private import EngineVerification::*;
    private import EngineRelationships::*;

    #CharteredBy dependency from guardLivenessStory to d0169;

    part guardLivenessStory : Story {
        :>> id = "0d800670-0814-6670-9b3e-000000300670";
        :>> title = "Sprint 364: guard liveness is readable, and a hook can no longer wedge the build (5 pts)";
        :>> createdAt = "2026-08-20"; :>> createdBy = "claudeOpus5"; :>> kind = WorkKind::code; :>> priority = WorkPriority::p0; :>> owner = "claudeOpus5"; :>> estimatedPoints = 5;
    }

    action def DeliveryRunS364 {
        action storyGuardLiveness;
        verification storyGuardLivenessDoD : Test { :>> id = "0d800671-0814-6671-9b3e-000000300671"; :>> method = VerificationMethod::test; :>> procedureText = "DELIVERED BACKLOG ITEMS: dcGuardScanCount, dcHookBoundedLife. Clears issue180 and issue181 under D0169. ISSUE180: three guards - critic-independence, edge-endpoints, requirement-rootedness - hardcoded `scanned: 0` while finding real violations, and requirement-rootedness destructured its own count into a discard binding `Ok(Some((_scanned, gaps)))`. PROVED THEY STILL ENFORCE rather than assuming: a deliberately dangling #Resolves edge made edge-endpoints FAIL printing `0 scanned, 0 warning(s), 1 violation(s)`, which contradicts itself. Now 10120 / 8208 / 3 scanned respectively. THE CONTROL IS IN THE RUNNER, not a test: `GuardReport::print` warns when violations are reported against a zero scan, so it holds for every guard added later without anyone remembering. ISSUE181: `keel hook` blocked on an unbounded stdin read, so an orphaned hook held a Windows lock on target/release/keel.exe and wedged EVERY later build with `Access is denied` - observed three times in this one turn, each needing a kill by PID. A 120s watchdog now exits 0, because D0134 says a hook never fails a turn. validate 396 clean; check-engine clean; 38 guards ALL PASS; 196 tests; clippy clean."; }
        part storyGuardLivenessDoDR1 : TestResult { :>> id = "0d800672-0814-6672-9b3e-000000300672"; :>> outcome = VerdictKind::pass; :>> judgedAgainst = "da56c38"; :>> judgedAt = "2026-08-20"; :>> judgedBy = "claudeOpus5"; }
    }

    verification glRefineGate : Test { :>> id = "0d800673-0814-6673-9b3e-000000300673"; :>> title = "Sprint 364 refine gate (DoR)"; :>> createdAt = "2026-08-20"; :>> createdBy = "claudeOpus5"; :>> method = VerificationMethod::inspect; :>> procedureText = "DoR. Pass 4 attacked the guard layer itself - the thing every other finding is enforced by. The entry point was a scan-count census, and it produced NINE candidates of which only THREE are real: charter and process-change scan CHANGED files, and base-first-justification, doc-sync, retro-backlog and ownership each have a genuine computed site and hardcode zero only on error or rule-absent paths. Reporting nine would have been metrics theater and would have sent a successor after six non-problems. The second finding was found by the work rather than by the audit: a stray keel.exe blocked three rebuilds mid-sprint. estimatedPoints=5."; }
    part glRefineGateR1 : TestResult { :>> id = "0d800674-0814-6674-9b3e-000000300674"; :>> outcome = VerdictKind::pass; :>> judgedAgainst = "da56c38"; :>> judgedAt = "2026-08-20"; :>> judgedBy = "claudeOpus5"; }

    verification glStandupGate : Test { :>> id = "0d800675-0814-6675-9b3e-000000300675"; :>> title = "Sprint 364 standup gate"; :>> createdAt = "2026-08-20"; :>> createdBy = "claudeOpus5"; :>> method = VerificationMethod::inspect; :>> procedureText = "Approach: prove enforcement BEFORE touching the reporting, because `0 scanned` has two possible meanings and only one of them is a bug. Constructing a real violation - a dangling edge - settled it in one run: the guard fired, so enforcement was never the problem and the fix is confined to the signal. Then put the invariant in the RUNNER rather than in a test, so it covers guards nobody has written yet. No blockers."; }
    part glStandupGateR1 : TestResult { :>> id = "0d800676-0814-6676-9b3e-000000300676"; :>> outcome = VerdictKind::pass; :>> judgedAgainst = "da56c38"; :>> judgedAt = "2026-08-20"; :>> judgedBy = "claudeOpus5"; }

    verification glImplementGate : Test { :>> id = "0d800677-0814-6677-9b3e-000000300677"; :>> title = "Sprint 364 implement gate"; :>> createdAt = "2026-08-20"; :>> createdBy = "claudeOpus5"; :>> method = VerificationMethod::test; :>> procedureText = "THIRD OVERSTATED FINDING IN FOUR PASSES, and I am recording the pattern rather than just the instance. issue178 said 13 routes and meant 3. issue180 said nine guards and means three. Both came from reading a SUMMARY NUMBER - nine zeroes in a column, five endpoint groups in a JSON blob - instead of the mechanism behind it. The corrections are written into the issues themselves, so a successor sees the 13 and the 9 that were wrong. THE DECISIVE TEST WAS CHEAP AND I ALMOST SKIPPED IT: adding one dangling edge and running the guard took thirty seconds and separated `mis-aimed` from `mis-reporting`, which no amount of reading the function would have settled as certainly. THE SECOND FINDING WAS HANDED TO ME BY THE WORK: three builds failed with `failed to remove file ... Access is denied (os error 5)`, which names cargo and a file permission and reads as antivirus. It was `keel hook` blocked forever on stdin, holding a lock on the binary. CLAUDE.md already warns that `keel serve` holds the binary; nothing warned about the hook, because nobody had noticed. The watchdog exits 0 rather than nonzero - a hook that gave up waiting must be indistinguishable from a hook with nothing to say, or D0134's never-fail-a-turn rule breaks."; }
    part glImplementGateR1 : TestResult { :>> id = "0d800678-0814-6678-9b3e-000000300678"; :>> outcome = VerdictKind::pass; :>> judgedAgainst = "da56c38"; :>> judgedAt = "2026-08-20"; :>> judgedBy = "claudeOpus5"; }

    verification glReviewGate : Test { :>> id = "0d800679-0814-6679-9b3e-000000300679"; :>> title = "Sprint 364 review gate"; :>> createdAt = "2026-08-20"; :>> createdBy = "claudeOpus5"; :>> method = VerificationMethod::inspect; :>> procedureText = "Reviewed. THE LEGITIMATELY-EMPTY LIST IS THE PART A REVIEWER SHOULD ATTACK. `the_guards_that_report_a_population_still_do` excludes six guards BY NAME rather than allowing zero generally, so a guard going quiet cannot hide behind them - but the list is my judgment, and if `ownership` is quiet because it is mis-aimed rather than because nobody edited another actor's item, the list conceals exactly what it was built to reveal. It is six names in one place, which is the most reviewable form I could give it. WHAT I WOULD DEFEND: proving enforcement before fixing reporting. `0 scanned` could have meant a dead guard, and if it had, the fix would have been completely different - the difference between `this number is wrong` and `this guard does nothing` is the difference between a cosmetic sprint and an emergency. THE UNCOMFORTABLE OBSERVATION: the engine left a lingering process that blocked its own builds, while CLAUDE.md instructs me not to leave lingering processes. The rule was written for me and the violation was in the binary."; }
    part glReviewGateR1 : TestResult { :>> id = "0d80067a-0814-667a-9b3e-00000030067a"; :>> outcome = VerdictKind::pass; :>> judgedAgainst = "da56c38"; :>> judgedAt = "2026-08-20"; :>> judgedBy = "claudeOpus5"; }

    verification glCloseOutGate : Test { :>> id = "0d80067b-0814-667b-9b3e-00000030067b"; :>> title = "Sprint 364 closeOut gate (autonomous, D0049)"; :>> createdAt = "2026-08-20"; :>> createdBy = "claudeOpus5"; :>> method = VerificationMethod::inspect; :>> procedureText = "Autonomous closeOut (D0049). issue180 and issue181 cleared. Four passes complete: 11 findings recorded, 11 cleared, 6 permanent controls added of which one lives in the guard runner rather than in a test. issue180's description carries its own correction from nine to three. validate 396 clean; check-engine clean; 38 guards ALL PASS; 196 tests; clippy clean."; }
    part glCloseOutGateR1 : TestResult { :>> id = "0d80067c-0814-667c-9b3e-00000030067c"; :>> outcome = VerdictKind::pass; :>> judgedAgainst = "da56c38"; :>> judgedAt = "2026-08-20"; :>> judgedBy = "claudeOpus5"; }

    verification glRetroGate : Test { :>> id = "0d80067d-0814-667d-9b3e-00000030067d"; :>> title = "Sprint 364 retro gate (autonomous, D0049)"; :>> createdAt = "2026-08-20"; :>> createdBy = "claudeOpus5"; :>> method = VerificationMethod::analyze; :>> procedureText = "Autonomous retro (D0049) under D0131's retroTrack. WELL: (1) enforcement was PROVEN before reporting was touched, by constructing a real violation, which took thirty seconds and decided between two completely different sprints; (2) the nine-to-three correction happened before the fix rather than after, so no work was done against six non-problems; (3) the invariant went into the runner, so it covers guards not yet written; (4) the six legitimately-empty guards are excluded by NAME, and the review gate says plainly that the list is the weak point; (5) the hook watchdog exits 0, preserving D0134 rather than trading one invariant for another. AVOIDABLE-ISSUE: THE THIRD OVERSTATED FINDING IN FOUR PASSES. Both overstatements came from trusting a summary number over the mechanism - nine zeroes in a column, five endpoint groups in a blob. The rule is not `check your numbers`; it is that a COLUMN OF ZEROES IS NOT A FINDING UNTIL ONE OF THEM IS EXPLAINED, because the explanation is where the count comes from. SECOND AVOIDABLE-ISSUE: the same doubled-quote bug when rewriting an issue description in place - my replacement text ends with a quote and the retained tail supplies another. It broke the fast gate, exactly as it did two sprints ago, and I had not made it impossible. THIRD: I killed three stray processes by PID before asking WHY a process was stray, which delayed finding issue181 by twenty minutes. A recurring `Access is denied` is a symptom, not an obstacle. Estimate 5 pts, delivered."; }
    part glRetroGateR1 : TestResult { :>> id = "0d80067e-0814-667e-9b3e-00000030067e"; :>> outcome = VerdictKind::pass; :>> judgedAgainst = "da56c38"; :>> judgedAt = "2026-08-20"; :>> judgedBy = "claudeOpus5"; }
}
