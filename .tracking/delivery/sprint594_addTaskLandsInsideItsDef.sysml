// ProjectDeliveryS594 — Sprint 594: add-task lands the task inside the def it was given, or refuses - an escaped quote had been moving it outside every one. EXECUTE. 2 pts.
package ProjectDeliveryS594 {
    private import EngineElement::*;
    private import EngineWork::*;
    private import EngineVerification::*;
    private import EngineRelationships::*;

    #CharteredBy dependency from addTaskLandsInsideItsDefStory to d0047;

    part addTaskLandsInsideItsDefStory : Story {
        :>> id = "aeb47aa8-ab64-442d-aa41-7978a073943a";
        :>> title = "Sprint 594: add-task lands the task inside the def it was given, or refuses - an escaped quote had been moving it outside every one (2 pts)";
        :>> createdAt = "2026-09-07"; :>> createdBy = "claudeFable5"; :>> kind = WorkKind::code; :>> priority = WorkPriority::p0; :>> owner = "claudeFable5"; :>> estimatedPoints = 2;
    }

    action def DeliveryRunS594 {
        action storyAddTaskLandsInsideItsDef;
        verification storyAddTaskLandsInsideItsDefDoD : Test { :>> id = "7f2f19b6-9adb-40ed-b58b-1761ea66cbf6"; :>> method = VerificationMethod::test; :>> procedureText = "DELIVERED BACKLOG ITEMS: dcAddTaskLandsInsideItsDef (resolves issue407, High). Chartered by D0047. DONE, both halves: braces_in in write.rs handles a backslash escape, so an escaped quote in a field's prose no longer reads as a string terminator and desynchronises the brace scan; and add_task_locked checks its landing site before writing - a def opening at one column closes at the same column, and a scanned closing brace belonging to a different block makes the write REFUSE, naming both lines and columns. The two items the defect mis-filed in sprint 593 are moved into EngineBuild by a script that refuses unless the file's line multiset is unchanged. VERIFIED: the original artefact reproduces and is fixed - add-task --def NextWork against .tracking/backlog.sysml at 018315a placed the action at line 2696 while the def closed at 2104, and against the fix places it at 2104; --def EngineBuild on the same file was correct throughout, which is what isolated it to the second def; unit test an_escaped_quote_does_not_move_a_task_out_of_its_def covers braces_in directly and end to end on a two-def fixture; the newly added items landed inside a def. keel suite 571 passed 0 failed (receipt 199146c397b7); validate clean; check-engine clean; guard ALL PASS; clippy -D warnings clean."; }
        // RAN: keel suite 571 passed 0 failed (receipt 199146c397b7, log suite-1788813781); reproduction on 018315a: add-task --def NextWork placed at line 2696 outside a def closing at 2104, and at 2104 inside against the fix; an_escaped_quote_does_not_move_a_task_out_of_its_def 1/1; the three tests my first over-strict check broke pass again; validate 676; check-engine clean; guard ALL PASS; clippy -D warnings clean
        part storyAddTaskLandsInsideItsDefDoDR1 : TestResult { :>> id = "f832eedc-a6d5-4980-97d9-40d60253d0fc"; :>> outcome = VerdictKind::pass; :>> judgedAgainst = "4a38e84d65efbf1b3693856861325cbd26d89709"; :>> judgedAt = "2026-09-07"; :>> judgedBy = "claudeOpus5"; }
    }

    verification addTaskLandsInsideItsDefRefineGate : Test { :>> id = "c6087c84-ffae-4e0b-a750-2013e9ede44a"; :>> title = "Sprint 594 refine gate (DoR)"; :>> createdAt = "2026-09-07"; :>> createdBy = "claudeFable5"; :>> method = VerificationMethod::inspect; :>> procedureText = "READY, and this sprint was not planned. It began as the reorder that discharges the priority-inversion warnings, and the reorder script refused: none of the 33 ready items were inside the action def it had been pointed at. That refusal is the only reason the defect was found, and it is worth saying plainly - a script that had appended on a missed anchor instead of failing would have written 33 blocks into the wrong place and reported success, which is the lesson sprint 592's retro recorded and the reason this one was written to fail. Sized 2: a small scanner fix, a check on the write path, a repair under control totals, and a test. It cost more than 2, and the overrun was entirely in getting a suite number that meant anything."; }
    // RAN: keel suite 571 passed 0 failed (receipt 199146c397b7, log suite-1788813781); reproduction on 018315a: add-task --def NextWork placed at line 2696 outside a def closing at 2104, and at 2104 inside against the fix; an_escaped_quote_does_not_move_a_task_out_of_its_def 1/1; the three tests my first over-strict check broke pass again; validate 676; check-engine clean; guard ALL PASS; clippy -D warnings clean
    part addTaskLandsInsideItsDefRefineGateR1 : TestResult { :>> id = "7e4d6ba0-6169-415c-b786-72a555156fa8"; :>> outcome = VerdictKind::pass; :>> judgedAgainst = "4a38e84d65efbf1b3693856861325cbd26d89709"; :>> judgedAt = "2026-09-07"; :>> judgedBy = "claudeOpus5"; }
    verification addTaskLandsInsideItsDefStandupGate : Test { :>> id = "c83ebde2-a6aa-473f-aef5-06df61c7ac39"; :>> title = "Sprint 594 standup gate"; :>> createdAt = "2026-09-07"; :>> createdBy = "claudeFable5"; :>> method = VerificationMethod::inspect; :>> procedureText = "NO BLOCKER. Nothing here touches guard source, hook config or CI workflows, so the D0209 keystone lock does not apply and no process-change Decision is owed; D0366 from sprint 593 is still the one waiting on the human, alongside d0360 to d0363."; }
    // RAN: keel suite 571 passed 0 failed (receipt 199146c397b7, log suite-1788813781); reproduction on 018315a: add-task --def NextWork placed at line 2696 outside a def closing at 2104, and at 2104 inside against the fix; an_escaped_quote_does_not_move_a_task_out_of_its_def 1/1; the three tests my first over-strict check broke pass again; validate 676; check-engine clean; guard ALL PASS; clippy -D warnings clean
    part addTaskLandsInsideItsDefStandupGateR1 : TestResult { :>> id = "4ee72081-5ab6-4a18-855c-c2d4cc69b2dd"; :>> outcome = VerdictKind::pass; :>> judgedAgainst = "4a38e84d65efbf1b3693856861325cbd26d89709"; :>> judgedAt = "2026-09-07"; :>> judgedBy = "claudeOpus5"; }
    verification addTaskLandsInsideItsDefImplementGate : Test { :>> id = "e03a8c3a-f6f5-48b7-b8d1-66f31eaf5193"; :>> title = "Sprint 594 implement gate"; :>> createdAt = "2026-09-07"; :>> createdBy = "claudeFable5"; :>> method = VerificationMethod::test; :>> procedureText = "RAN, diagnosis before claim. Reproduced twice on a clean tree at 018315a - NextWork wrong, EngineBuild right on the same file - before anything was called broken. Located the mechanism at write.rs braces_in and confirmed it by replicating the scan and finding the exact line: .tracking/backlog.sysml line 1793, a procedureText that quotes an escaped quote while being about escaped-quote handling, after which the line's braces are counted as structure and depth never returns to zero at the def's real close. Fixed the escape, added the landing-site check, wrote the test, re-ran the original reproduction against the fix, moved the two mis-filed items, and re-recorded a task through the fixed path to confirm it lands inside. Then spent four suite runs discovering that the suite could not run at all here (issue408), and a fifth fixing what the fourth finally revealed."; }
    // RAN: keel suite 571 passed 0 failed (receipt 199146c397b7, log suite-1788813781); reproduction on 018315a: add-task --def NextWork placed at line 2696 outside a def closing at 2104, and at 2104 inside against the fix; an_escaped_quote_does_not_move_a_task_out_of_its_def 1/1; the three tests my first over-strict check broke pass again; validate 676; check-engine clean; guard ALL PASS; clippy -D warnings clean
    part addTaskLandsInsideItsDefImplementGateR1 : TestResult { :>> id = "926d618e-327d-4832-81b4-cc1f6ba08a32"; :>> outcome = VerdictKind::pass; :>> judgedAgainst = "4a38e84d65efbf1b3693856861325cbd26d89709"; :>> judgedAt = "2026-09-07"; :>> judgedBy = "claudeOpus5"; }
    verification addTaskLandsInsideItsDefReviewGate : Test { :>> id = "ce5f996c-7400-4b61-8464-338cb0c534e4"; :>> title = "Sprint 594 review gate — three passes per D0172"; :>> createdAt = "2026-09-07"; :>> createdBy = "claudeFable5"; :>> method = VerificationMethod::inspect; :>> procedureText = "THREE PASSES per D0172. (1) IS THE FIX THE WHOLE FIX: no, and that is deliberate. The escape handling removes one cause; the landing-site check removes the class, because a line scan that goes wrong returns a plausible number rather than an error and every write that positions itself by scanning has the same exposure. Only the second half would have caught this defect if the cause had been something other than an escape. (2) DID I WRITE A TEST THAT WOULD HAVE PASSED ON THE BROKEN CODE: the braces_in assertion is direct - an escaped quote before a brace returned one open before the fix and returns none after - and the end-to-end half puts the escaped quote in the FIRST def and adds to the SECOND, which is the exact geometry of the live failure rather than a restatement of the fix. (3) DID THE CONTROLS CATCH ME: three times, and the third is the one worth recording. Clippy refused two raw slice indexes I had added on the error path of a check whose purpose is to avoid trusting an index. I wrote the first version of the new test with forward slashes where it needed backslashes. And the SUITE caught a regression I had introduced and was about to record as done: my landing-site check also refused an EMPTY action def, on the reasoning that a def with no body meant the scan had gone wrong - which is false, an empty def is what init scaffolds, and three tests add the first task to one. My unit test and my live reproduction both passed the whole time. Emptiness carries no information about whether the scan landed; indentation does, and the check now rests only on that."; }
    // RAN: keel suite 571 passed 0 failed (receipt 199146c397b7, log suite-1788813781); reproduction on 018315a: add-task --def NextWork placed at line 2696 outside a def closing at 2104, and at 2104 inside against the fix; an_escaped_quote_does_not_move_a_task_out_of_its_def 1/1; the three tests my first over-strict check broke pass again; validate 676; check-engine clean; guard ALL PASS; clippy -D warnings clean
    part addTaskLandsInsideItsDefReviewGateR1 : TestResult { :>> id = "487a4248-ed02-4aaf-9103-1919b15876d4"; :>> outcome = VerdictKind::pass; :>> judgedAgainst = "4a38e84d65efbf1b3693856861325cbd26d89709"; :>> judgedAt = "2026-09-07"; :>> judgedBy = "claudeOpus5"; }
    verification addTaskLandsInsideItsDefCloseOutGate : Test { :>> id = "f8359e21-0c8e-4ed5-a35f-cf63bddee7e7"; :>> title = "Sprint 594 closeOut gate (autonomous, D0049)"; :>> createdAt = "2026-09-07"; :>> createdBy = "claudeFable5"; :>> method = VerificationMethod::inspect; :>> procedureText = "CLOSED. A sanctioned write path can no longer file work where nothing will look for it, and this project's own suite can run."; }
    // RAN: keel suite 571 passed 0 failed (receipt 199146c397b7, log suite-1788813781); reproduction on 018315a: add-task --def NextWork placed at line 2696 outside a def closing at 2104, and at 2104 inside against the fix; an_escaped_quote_does_not_move_a_task_out_of_its_def 1/1; the three tests my first over-strict check broke pass again; validate 676; check-engine clean; guard ALL PASS; clippy -D warnings clean
    part addTaskLandsInsideItsDefCloseOutGateR1 : TestResult { :>> id = "b70ff2b7-eb11-4e95-b0b7-e76c96904de8"; :>> outcome = VerdictKind::pass; :>> judgedAgainst = "4a38e84d65efbf1b3693856861325cbd26d89709"; :>> judgedAt = "2026-09-07"; :>> judgedBy = "claudeOpus5"; }
    verification addTaskLandsInsideItsDefRetroGate : Test { :>> id = "8aa657bf-8dc7-4524-adb8-e65aa41b2a77"; :>> title = "Sprint 594 retro gate (autonomous, D0049)"; :>> createdAt = "2026-09-07"; :>> createdBy = "claudeFable5"; :>> method = VerificationMethod::analyze; :>> procedureText = "AVOIDABLE-ISSUE SCAN HELD. One new item beyond the sprint's own: issue408, recorded with dcSelfBuildHooksLeaveTheBuildTree. keel suite returned `fail - 0 passed, 0 failed` three times running, executing no test; the fire-ledger showed every hook resolving to target/release/keel.exe, because the pin probe finds no .keel/bin/keel.exe in a self-build tree and falls through to PATH into the build directory - so the hooks hold the file cargo must unlink, on every prompt, every Bash call and every turn end. Two explanations were tested and discarded before that one was stated: a lingering process, and my own tool calls. The part that matters is not the flakiness: the lock CONCEALED three real test failures for three runs while a unit test and a live reproduction both stayed green, and a sprint recorded on their strength would have committed the regression. That is the same shape as issue386, issue399 and issue407 - a control passing while blind - for the fourth time in two days, and this instance is the one where the blindness nearly bought a false green. Already tracked, no new item: issue386 keeps its own half, since removing the collision and making a lock report as a lock are different fixes and neither substitutes for the other. The habit that saved the sprint twice was the same one: an instrument that cannot do its job must fail loudly, not return something plausible."; }
    // RAN: keel suite 571 passed 0 failed (receipt 199146c397b7, log suite-1788813781); reproduction on 018315a: add-task --def NextWork placed at line 2696 outside a def closing at 2104, and at 2104 inside against the fix; an_escaped_quote_does_not_move_a_task_out_of_its_def 1/1; the three tests my first over-strict check broke pass again; validate 676; check-engine clean; guard ALL PASS; clippy -D warnings clean
    part addTaskLandsInsideItsDefRetroGateR1 : TestResult { :>> id = "62fa6ed0-6a15-4d37-9663-21b25d205ead"; :>> outcome = VerdictKind::pass; :>> judgedAgainst = "4a38e84d65efbf1b3693856861325cbd26d89709"; :>> judgedAt = "2026-09-07"; :>> judgedBy = "claudeOpus5"; }
}
