// ProjectDeliveryS330 — Sprint 330: critique pass 6 — five viewer/authoring SystemRequirements. EXECUTE. 3 pts.
package ProjectDeliveryS330 {
    private import EngineElement::*;
    private import EngineWork::*;
    private import EngineVerification::*;
    private import EngineRelationships::*;

    #CharteredBy dependency from critPass6Story to d0080;

    part critPass6Story : Story {
        :>> id = "0d800450-0814-6450-9b3e-000000300450";
        :>> title = "Sprint 330: critique pass 6 — 5 viewer/authoring SRs x Core-3, 10 fail / 5 pass (3 pts)";
        :>> createdAt = "2026-08-17"; :>> createdBy = "claudeOpus5"; :>> kind = WorkKind::modeling; :>> priority = WorkPriority::p0; :>> owner = "claudeOpus5"; :>> estimatedPoints = 3;
    }

    action def DeliveryRunS330 {
        action storyCritPass6;
        verification storyCritPass6DoD : Test { :>> id = "0d800451-0814-6451-9b3e-000000300451"; :>> method = VerificationMethod::analyze; :>> procedureText = "Pass 6: srViewerAuthoringSurface, srViewerBaselineCompare, srViewerChangeImpact, srViewerConfigurableSlice, srViewerContextActions. 10 fail, 5 pass. THREE FINDINGS WORTH THE PASS. (1) srViewerAuthoringSurface's generative clause quietly makes it satisfiable by offering almost nothing: it demands the full authoring set and then requires each action only 'iff the endpoint is advertised', so advertising two endpoints satisfies every word — and 'create an item of a declared type' has no generic endpoint to advertise, since `keel record` takes exactly two verbs. The ambitious clause and the safety clause point opposite ways, and the safety clause wins silently. (2) srViewerContextActions generates its menu from the advertised contract, which genuinely exists (/api/version returns readEndpoints and writeEndpoints) — but those are hardcoded arrays whose guarding test, api_version_contract_is_self_consistent, asserts only that they CONTAIN entries, never that they MATCH the router. The failure directions are asymmetric: an unlisted route fails CLOSED and is safe, while a REMOVED route left listed fails OPEN — the viewer offers an action that 404s. (3) srViewerBaselineCompare says 'an element predating one point reads as added since' without saying which point, and the more literal reading is the wrong one: an element predating the EARLIER point is pre-existing, and reporting it as added would mark most of the model as new. READ BACK: SystemRequirement coverage 10 -> 15 of 72."; }
        part storyCritPass6DoDR1 : TestResult { :>> id = "0d800452-0814-6452-9b3e-000000300452"; :>> outcome = VerdictKind::pass; :>> judgedAgainst = "27b4c15"; :>> judgedAt = "2026-08-17"; :>> judgedBy = "claudeOpus5"; }
    }

    verification c6RefineGate : Test { :>> id = "0d800453-0814-6453-9b3e-000000300453"; :>> title = "Sprint 330 refine gate (DoR)"; :>> createdAt = "2026-08-17"; :>> createdBy = "claudeOpus5"; :>> method = VerificationMethod::inspect; :>> procedureText = "DoR. Five SRs across architect-sure and keel-viewer. Two mechanisms were read before being judged: /api/version's endpoint arrays and the test that guards them, and view.rs's element_neighbourhood / need_slice, which are live and which I had once assumed retired. estimatedPoints=3."; }
    part c6RefineGateR1 : TestResult { :>> id = "0d800454-0814-6454-9b3e-000000300454"; :>> outcome = VerdictKind::pass; :>> judgedAgainst = "27b4c15"; :>> judgedAt = "2026-08-17"; :>> judgedBy = "claudeOpus5"; }

    verification c6StandupGate : Test { :>> id = "0d800455-0814-6455-9b3e-000000300455"; :>> title = "Sprint 330 standup gate"; :>> createdAt = "2026-08-17"; :>> createdBy = "claudeOpus5"; :>> method = VerificationMethod::inspect; :>> procedureText = "Approach: for each requirement asking that something be GENERATED rather than hardcoded, follow the generation source to its own source and ask whether IT can drift — that is where two of this batch's findings came from. No blockers."; }
    part c6StandupGateR1 : TestResult { :>> id = "0d800456-0814-6456-9b3e-000000300456"; :>> outcome = VerdictKind::pass; :>> judgedAgainst = "27b4c15"; :>> judgedAt = "2026-08-17"; :>> judgedBy = "claudeOpus5"; }

    verification c6ImplementGate : Test { :>> id = "0d800457-0814-6457-9b3e-000000300457"; :>> title = "Sprint 330 implement gate"; :>> createdAt = "2026-08-17"; :>> createdBy = "claudeOpus5"; :>> method = VerificationMethod::analyze; :>> procedureText = "DECOMPOSITION EITHER FIXES A NEED'S GAP OR CARRIES IT, and this batch shows both outcomes side by side, which is the most useful comparison the pass produced. srViewerChangeImpact FIXED three of its Need's defects — it added configurable edge selection, grouping by distance, and cycles-shown-once, each answering a real objection — and earns a correctness pass for being a better statement than the Need it decomposes. srViewerConfigurableSlice and srViewerBaselineCompare CARRIED theirs unchanged: the slice-boundary question (what happens to an edge whose far end is excluded) and the undefined meaning of BASELINE both survive into the requirement that was supposed to make the Need buildable. Baseline is the worse of the two, because the requirement adds 'dates or baselines' as alternatives and thereby implies a baseline is something other than a date without saying what — a decomposition that made its parent less clear."; }
    part c6ImplementGateR1 : TestResult { :>> id = "0d800458-0814-6458-9b3e-000000300458"; :>> outcome = VerdictKind::pass; :>> judgedAgainst = "27b4c15"; :>> judgedAt = "2026-08-17"; :>> judgedBy = "claudeOpus5"; }

    verification c6ReviewGate : Test { :>> id = "0d800459-0814-6459-9b3e-000000300459"; :>> title = "Sprint 330 review gate"; :>> createdAt = "2026-08-17"; :>> createdBy = "claudeOpus5"; :>> method = VerificationMethod::inspect; :>> procedureText = "Reviewed. THE SAME UNWRITTEN TEST IS NOW NAMED BY THREE REQUIREMENTS AND TWO NEEDS: change the declared model or the advertised contract, and require the surface to change with NO code edit. It would verify nServeReuseModel, nViewerGenerativeUi, srViewerContextActions, srEncodingModular and srEncodingSchemaSemantics, and it is the test that would have caught VIEW_SUBCOMMANDS' drift. Five elements, one fixture, nobody has written it — recorded inside the critiques so an implementer meets it rather than in a sprint note. I did NOT raise it as an Issue: the elements are human-owned and the fixture is work nobody has chartered, so inventing a backlog item for it would be scheduling someone else's decision."; }
    part c6ReviewGateR1 : TestResult { :>> id = "0d80045a-0814-645a-9b3e-00000030045a"; :>> outcome = VerdictKind::pass; :>> judgedAgainst = "27b4c15"; :>> judgedAt = "2026-08-17"; :>> judgedBy = "claudeOpus5"; }

    verification c6CloseOutGate : Test { :>> id = "0d80045b-0814-645b-9b3e-00000030045b"; :>> title = "Sprint 330 closeOut gate (autonomous, D0049)"; :>> createdAt = "2026-08-17"; :>> createdBy = "claudeOpus5"; :>> method = VerificationMethod::inspect; :>> procedureText = "Autonomous closeOut (D0049). SystemRequirement coverage 10 -> 15 of 72; 15 critiquable SRs and 22 critiquable Decisions remain. Zero open issues; ready frontier empty; D0159 queued. validate clean; check-engine clean; 35 guards ALL PASS; no code changed."; }
    part c6CloseOutGateR1 : TestResult { :>> id = "0d80045c-0814-645c-9b3e-00000030045c"; :>> outcome = VerdictKind::pass; :>> judgedAgainst = "27b4c15"; :>> judgedAt = "2026-08-17"; :>> judgedBy = "claudeOpus5"; }

    verification c6RetroGate : Test { :>> id = "0d80045d-0814-645d-9b3e-00000030045d"; :>> title = "Sprint 330 retro gate (autonomous, D0049)"; :>> createdAt = "2026-08-17"; :>> createdBy = "claudeOpus5"; :>> method = VerificationMethod::analyze; :>> procedureText = "Autonomous retro (D0049) under D0131's retroTrack. WELL: (1) following each generate-from-a-contract claim to the contract's OWN source produced two findings that reading the requirement alone could not — the advertised endpoint arrays and the test that only checks containment; (2) the pass/fail split tracks the evidence rather than a target, and srViewerChangeImpact earned a correctness PASS for improving on its Need, which is worth recording because a critic that never passes anything is not measuring; (3) the recurring one-fixture-five-elements observation was put inside the critiques where an implementer will meet it. AVOIDABLE-ISSUE: none. PROCESS NOTE: the land script introduced last pass gated, committed, stamped, re-validated and landed in one call, and it refuses to continue if nothing was stamped — which removes the stale-HEAD stamping error this session made twice by hand. Estimate 3 pts, delivered."; }
    part c6RetroGateR1 : TestResult { :>> id = "0d80045e-0814-645e-9b3e-00000030045e"; :>> outcome = VerdictKind::pass; :>> judgedAgainst = "27b4c15"; :>> judgedAt = "2026-08-17"; :>> judgedBy = "claudeOpus5"; }
}
