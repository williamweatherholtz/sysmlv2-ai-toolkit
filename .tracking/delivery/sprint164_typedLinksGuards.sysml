// ProjectDeliveryS164 — Sprint 164: D0102 (CHANGE) — typed links not prose. (1) NEW decision-requirement-link
// WARNING guard (an accepted Decision naming a Need/SR in prose with no typed edge is flagged, visible every
// commit, non-blocking). (2) critique_suspect honors ACCEPT-RISK/DISMISS dispositions via a typed #DependsOn
// finding->critique link (clears d0098). Both D0047 corrections from the A2 critique campaign (issue052 + d0098
// quirk). EXECUTE (CHANGE). 3 pts. AUTONOMOUS ceremony (D0049); D0102 carries the human acceptance.
package ProjectDeliveryS164 {
    private import EngineElement::*;
    private import EngineWork::*;
    private import EngineVerification::*;
    private import EngineRelationships::*;

    #CharteredBy dependency from typedLinksStory to d0102;

    part typedLinksStory : Story {
        :>> id = "63940516-2c7d-4e8f-c164-51627384c001";
        :>> title = "Sprint 164: D0102 typed-links — decision-requirement-link warning guard + critique_suspect honors dispositions";
        :>> createdAt = "2026-06-25"; :>> createdBy = "wweatherholtz"; :>> kind = WorkKind::code; :>> priority = WorkPriority::p2; :>> owner = "claudeOpus"; :>> estimatedPoints = 3;
    }

    action def DeliveryRunS164 {
        action storyTypedLinks;
        verification storyTypedLinksDoD : Test { :>> id = "63940516-2c7d-4e8f-c164-51627384c002"; :>> method = VerificationMethod::test; :>> procedureText = "CHANGE per D0102 (accepted by wweatherholtz: 'Warning first' + 'Yes — fix it too'; kernel-validated 118/118). The user directive: 'prevent this from happening in the future' (issue052 — a Decision descoping a requirement, linked only in prose). DELIVERED: (1) view::decision_requirement_prose_links + contains_token (exact-identifier match) + guards::decision_requirement_link (WARNING-only; added to GUARD_NAMES 12->13 so it runs every commit but never blocks) — flags an accepted Decision naming a Need/SR in its text with no typed edge. (2) view::critique_suspect_set now SKIPS a fail critique whose finding Issue is dispositioned acceptRisk/dismiss, via the typed `#DependsOn` finding->critique edge; backfilled `#DependsOn issue050 -> d0098CorrectnessCritique`. doc-sync: CLAUDE.md §5 (13 guards: 12 hard + decision-requirement-link warning; critique_suspect-honors-dispositions) + the element-critique skill (the finding->critique link convention). VERIFIED LIVE: `keel guard decision-requirement-link` = 6 prose-only references surfaced as warnings (d0083/d0084/d0088->FastStart, d0102->sr19), 0 violations; `keel suspect` critique_suspect [] (d0098 cleared); D0100->sr19 NOT flagged (now linked). clippy -D warnings + cargo test (68 lib) + keel validate (177) + guard all (13 ALL PASS) green; contains_token unit test."; }
        part storyTypedLinksDoDR1 : TestResult { :>> id = "63940516-2c7d-4e8f-c164-51627384c003"; :>> outcome = VerdictKind::pass; :>> judgedAgainst = "9864d5f"; :>> judgedAt = "2026-06-25"; :>> judgedBy = "claudeOpus"; }
    }

    verification typedLinksRefineGate : Test { :>> id = "63940516-2c7d-4e8f-c164-51627384c004"; :>> title = "Sprint 164 refine gate (DoR)"; :>> createdAt = "2026-06-25"; :>> createdBy = "claudeOpus"; :>> method = VerificationMethod::inspect; :>> procedureText = "DoR: the human directed 'prevent this' (issue052 class) -> D0047 automated control. Design accepted as D0102 (warning-level link guard + critique_suspect honors dispositions). CHANGE: new guard + view logic (alters what critique_suspect MEANS -> CHANGE). estimatedPoints=3. #CharteredBy d0102. DoR met."; }
    part typedLinksRefineGateR1 : TestResult { :>> id = "63940516-2c7d-4e8f-c164-51627384c005"; :>> outcome = VerdictKind::pass; :>> judgedAgainst = "9864d5f"; :>> judgedAt = "2026-06-25"; :>> judgedBy = "claudeOpus"; }
    verification typedLinksStandupGate : Test { :>> id = "63940516-2c7d-4e8f-c164-51627384c006"; :>> title = "Sprint 164 standup gate"; :>> createdAt = "2026-06-25"; :>> createdBy = "claudeOpus"; :>> method = VerificationMethod::inspect; :>> procedureText = "Approach: view::decision_requirement_prose_links + contains_token (TDD the token boundary); guards::decision_requirement_link warning-only in GUARD_NAMES; critique_suspect_set skips accept-risk/dismiss findings via #DependsOn; backfill issue050 link; D0102 + kernel-validate; doc-sync CLAUDE.md + element-critique skill. No blockers."; }
    part typedLinksStandupGateR1 : TestResult { :>> id = "63940516-2c7d-4e8f-c164-51627384c007"; :>> outcome = VerdictKind::pass; :>> judgedAgainst = "9864d5f"; :>> judgedAt = "2026-06-25"; :>> judgedBy = "claudeOpus"; }
    verification typedLinksImplementGate : Test { :>> id = "63940516-2c7d-4e8f-c164-51627384c008"; :>> title = "Sprint 164 implement gate"; :>> createdAt = "2026-06-25"; :>> createdBy = "claudeOpus"; :>> method = VerificationMethod::test; :>> procedureText = "Implemented both. LIVE: guard decision-requirement-link surfaces 6 prose-only refs (warnings, 0 violations); critique_suspect [] (d0098 cleared via the issue050 #DependsOn link + accept-risk); D0100->sr19 not flagged. clippy + cargo test (68 lib) + keel validate (177) + guard all (13) green; D0102 kernel 118/118."; }
    part typedLinksImplementGateR1 : TestResult { :>> id = "63940516-2c7d-4e8f-c164-51627384c009"; :>> outcome = VerdictKind::pass; :>> judgedAgainst = "9864d5f"; :>> judgedAt = "2026-06-25"; :>> judgedBy = "claudeOpus"; }
    verification typedLinksReviewGate : Test { :>> id = "63940516-2c7d-4e8f-c164-51627384c00a"; :>> title = "Sprint 164 review gate"; :>> createdAt = "2026-06-25"; :>> createdBy = "claudeOpus"; :>> method = VerificationMethod::inspect; :>> procedureText = "Reviewed. The two fixes embody the same principle the human championed — a governing/derivation relationship is a TYPED edge, not prose. The link guard is warning-first (honest: surfaces 6 real cases without flooding/blocking; exact-identifier match keeps noise low; promotable to hard). The critique_suspect fix is honest (a fail critique stays suspect UNLESS the finding was consciously dispositioned — and via a typed path, not prose-matching, which would have been the very antipattern). Clean."; }
    part typedLinksReviewGateR1 : TestResult { :>> id = "63940516-2c7d-4e8f-c164-51627384c00b"; :>> outcome = VerdictKind::pass; :>> judgedAgainst = "9864d5f"; :>> judgedAt = "2026-06-25"; :>> judgedBy = "claudeOpus"; }
    verification typedLinksCloseOutGate : Test { :>> id = "63940516-2c7d-4e8f-c164-51627384c00c"; :>> title = "Sprint 164 closeOut gate (autonomous, D0049)"; :>> createdAt = "2026-06-25"; :>> createdBy = "claudeOpus"; :>> method = VerificationMethod::inspect; :>> procedureText = "Autonomous closeOut (D0049): DoD pass; the issue052 defect class is now PREVENTED by an automated control (decision-requirement-link guard) + the critique_suspect quirk fixed. clippy + cargo test (68 lib) + keel validate (177) + guard all (13) + D0102 kernel 118/118 green. Self-evidencing (D0051). suspect fully clean (drift 0, critique_suspect 0); assured READY. The guard surfaces 6 existing prose-only refs as a non-blocking burndown to clean up over time."; }
    part typedLinksCloseOutGateR1 : TestResult { :>> id = "63940516-2c7d-4e8f-c164-51627384c00d"; :>> outcome = VerdictKind::pass; :>> judgedAgainst = "9864d5f"; :>> judgedAt = "2026-06-25"; :>> judgedBy = "claudeOpus"; }
    verification typedLinksRetroGate : Test { :>> id = "63940516-2c7d-4e8f-c164-51627384c00e"; :>> title = "Sprint 164 retro gate (autonomous, D0049)"; :>> createdAt = "2026-06-25"; :>> createdBy = "claudeOpus"; :>> method = VerificationMethod::analyze; :>> procedureText = "Autonomous retro (D0049). WELL: the user's 'prevent this' became TWO durable controls (a guard + a computed-view fix), both expressing one principle (typed links not prose) — and the guard immediately earned its keep by surfacing 6 pre-existing prose-only references. Warning-first (per the human) avoided flooding while making the signal visible every commit. The critique_suspect fix was resolved the RIGHT way (a typed finding->critique edge) rather than prose-matching, which would have re-committed the antipattern. AVOIDABLE-ISSUE SCAN: no avoidable defect; clippy caught 3 first-pass lints (indexing-may-panic x2, doc-paragraph) BEFORE done (the localGateMatchesCi 1.96 toolchain working). LESSON (reusable): when a Decision changes a requirement's scope, link it typed in the SAME change — now guard-surfaced. Estimate 3 pts held. NEXT: 6 prose-only refs to backfill (burndown, non-urgent); B1/B2 hygiene; then releaseTag010."; }
    part typedLinksRetroGateR1 : TestResult { :>> id = "63940516-2c7d-4e8f-c164-51627384c00f"; :>> outcome = VerdictKind::pass; :>> judgedAgainst = "9864d5f"; :>> judgedAt = "2026-06-25"; :>> judgedBy = "claudeOpus"; }
}
