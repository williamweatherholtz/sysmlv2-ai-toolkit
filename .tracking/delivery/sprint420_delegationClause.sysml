// ProjectDeliveryS420 — Sprint 420: D0192 OPTION A applied: srK06 superseded with the delegation clause, the delegation declared in the attestation policy, and the quote-substance check live in the confirmation-authenticity guard. EXECUTE. 2 pts.
package ProjectDeliveryS420 {
    private import EngineElement::*;
    private import EngineWork::*;
    private import EngineVerification::*;
    private import EngineRelationships::*;

    #CharteredBy dependency from delegationClauseStory to d0192;

    part delegationClauseStory : Story {
        :>> id = "51788377-4b8b-4dde-b24b-ba036157a57e";
        :>> title = "Sprint 420: the delegation becomes policy (2 pts)";
        :>> createdAt = "2026-08-22"; :>> createdBy = "claudeFable5"; :>> kind = WorkKind::code; :>> priority = WorkPriority::p0; :>> owner = "claudeFable5"; :>> estimatedPoints = 2;
    }

    action def DeliveryRunS420 {
        action storyDelegationClause;
        verification storyDelegationClauseDoD : Test { :>> id = "147eab94-baad-4f11-8d1f-b9ac3c772df8"; :>> method = VerificationMethod::test; :>> procedureText = "DELIVERED: dcHumanChannelDelegationRule (resolves issue204, critique pass 1's High finding). wweatherholtz chose OPTION A - their words, verbatim: 'option A is fine. this hasn't been a real issue to date' - after an ELI5 of both options; the earlier deck tap (uid 5b1d2b0e) had signaled accept but could not bind without the option. APPLIED, all three clauses of option A: (1) srK06HumanChannel SUPERSEDED (claudeOpus5's item, D0108 - never edited) by srK06aDelegatedRecording: human-judgment records come from a human-held channel OR a declared, quote-carrying delegation; satisfy/DerivedFrom/allocate edges mirrored to nPavedWritePath, ehz3, and ceServeJudgment/ceWriteApi/ceGuards. (2) the delegation DECLARED in attestation-policy.toml [decisionAcceptance] (delegatedRecording = d0192, mirroring the D0165 findingDisposition entry, with the withdraw path stated). (3) the confirmation-authenticity guard gained the substance half: rule-sourced from the new delegatedAcceptanceSubstanceRule (predicate acceptQuotesDelegatedWords, forward-only from 2026-08-22 per issue068), demanding a verbatim single-quoted span or a cited human gesture on every acceptance recorded under the delegation - and the guard warns if the policy declares a delegation whose substance rule is missing. THE STATED LIMIT travels in every surface (D0192's own words): a fabricated quote defeats the check; the protections behind it are the human reading their own queue and the audit trail."; }
        part storyDelegationClauseDoDR1 : TestResult { :>> id = "1c175541-cbe5-492a-a011-8707c7751923"; :>> outcome = VerdictKind::pass; :>> judgedAgainst = "247805778bb52b3ac8a1e9a5b96be6da2c6bb36b"; :>> judgedAt = "2026-08-22"; :>> judgedBy = "claudeFable5"; }
    }

    verification delegationClauseRefineGate : Test { :>> id = "c74fbf7e-1961-49f3-a3ae-6f8ce408e53e"; :>> title = "Sprint 420 refine gate (DoR)"; :>> createdAt = "2026-08-22"; :>> createdBy = "claudeFable5"; :>> method = VerificationMethod::inspect; :>> procedureText = "DoR. Chartered by d0192, signed this morning with OPTION A chosen in chat. In scope: the requirement supersession, the policy declaration, the guard substance check, doc-sync. Out of scope: any change to WHO may judge (kinds stay human-only for acceptance - the delegation covers recording, never judging). 2 points."; }
    part delegationClauseRefineGateR1 : TestResult { :>> id = "e20bf6a1-9641-4f82-9094-b8f2447e78d7"; :>> outcome = VerdictKind::pass; :>> judgedAgainst = "247805778bb52b3ac8a1e9a5b96be6da2c6bb36b"; :>> judgedAt = "2026-08-22"; :>> judgedBy = "claudeFable5"; }
    verification delegationClauseStandupGate : Test { :>> id = "dbd74b74-7349-4f82-b91c-bf4243420fd3"; :>> title = "Sprint 420 standup gate"; :>> createdAt = "2026-08-22"; :>> createdBy = "claudeFable5"; :>> method = VerificationMethod::inspect; :>> procedureText = "Approach: supersede-not-edit for the SR (D0108); declare the delegation in the same contract file that already records the D0165 disposition delegation so ALL delegations live in one policy home (ending the asymmetry D0192 named); source the guard check from a declared ElementRule (CONTRACT pattern) so a project adopts it by declaring it; forward-only cutoff per issue068. One collision found and fixed mid-sprint: the sequential rule-id pattern collided with researchSpikeCharterRule's r008 (caught by duplicate-identity on the init scaffold's own test) - new rules take real UUIDs."; }
    part delegationClauseStandupGateR1 : TestResult { :>> id = "8d8bf78d-cd7d-4623-9f30-4d4390ebf52f"; :>> outcome = VerdictKind::pass; :>> judgedAgainst = "247805778bb52b3ac8a1e9a5b96be6da2c6bb36b"; :>> judgedAt = "2026-08-22"; :>> judgedBy = "claudeFable5"; }
    verification delegationClauseImplementGate : Test { :>> id = "82b69703-a6dd-4bc5-b473-eba1bc5cc910"; :>> title = "Sprint 420 implement gate"; :>> createdAt = "2026-08-22"; :>> createdBy = "claudeFable5"; :>> method = VerificationMethod::test; :>> procedureText = "Verified by running: the NEGATIVE probe - a temporary accepted Decision whose acceptance text carried no quote and no gesture turned confirmation-authenticity RED with the exact d0192 message, and removing it turned the guard green again (the control demonstrably fires); the real model passes with the D0192 acceptance itself satisfying the check it created; unit test pins the quote/gesture boundary (verbatim span passes, 'ok' apostrophe artifact fails, deck/console gestures pass); full suite green including init_smoke over the fresh scaffold; clippy pedantic+nursery clean; validate 464 clean; check-engine clean."; }
    part delegationClauseImplementGateR1 : TestResult { :>> id = "0881a917-7dc7-4840-9c83-33e5bb8a5a4e"; :>> outcome = VerdictKind::pass; :>> judgedAgainst = "247805778bb52b3ac8a1e9a5b96be6da2c6bb36b"; :>> judgedAt = "2026-08-22"; :>> judgedBy = "claudeFable5"; }
    verification delegationClauseReviewGate : Test { :>> id = "a49d31ab-6ef9-43cc-9f32-8a9f0cb54243"; :>> title = "Sprint 420 review gate — three passes per D0172"; :>> createdAt = "2026-08-22"; :>> createdBy = "claudeFable5"; :>> method = VerificationMethod::inspect; :>> procedureText = "PASS 1, CLAIMS: the negative-probe transcript (RED with the new message, green after removal) is quoted tool output from this session. PASS 2, BOUNDARY: the check is TEXT-SHAPE, not authentication - D0192 says so and every surface restates it; also the gesture allowance (any text containing deck/console passes) is deliberately loose so deck-tapped acceptances never false-fail, which means a delegated record could cite a fictitious gesture - same trust boundary as the fabricated quote, same stated protections. PASS 3, OWN DIFF: the first rule id followed the r00N convention and collided; the guard against it caught it in the scaffold smoke test, not in review - the control worked, the convention is retired for new rules. WHAT A REVIEWER SHOULD ATTACK: the 10-char quoted-span threshold is a judgment call; a one-word human verdict ('approved') recorded delegated would fail the check and correctly force either a fuller quote or their own gesture - that is the intended pressure, stated here so nobody discovers it as a surprise refusal."; }
    part delegationClauseReviewGateR1 : TestResult { :>> id = "0c122fd9-ae85-4dd7-ad65-f75d06e28c5e"; :>> outcome = VerdictKind::pass; :>> judgedAgainst = "247805778bb52b3ac8a1e9a5b96be6da2c6bb36b"; :>> judgedAt = "2026-08-22"; :>> judgedBy = "claudeFable5"; }
    verification delegationClauseCloseOutGate : Test { :>> id = "5a13ff00-bcd8-46e2-b921-e359fcdcb115"; :>> title = "Sprint 420 closeOut gate (autonomous, D0049)"; :>> createdAt = "2026-08-22"; :>> createdBy = "claudeFable5"; :>> method = VerificationMethod::inspect; :>> procedureText = "Autonomous closeOut (D0049). issue204 resolves via dcHumanChannelDelegationRule (edge pre-existing); the DoD flip carries the human's verbatim option choice; srK06's failing completeness critique now points at a superseded requirement whose successor states the delegation; validate + all guards green."; }
    part delegationClauseCloseOutGateR1 : TestResult { :>> id = "5fb415e4-d9bd-4a51-8ef3-6b5038523c0b"; :>> outcome = VerdictKind::pass; :>> judgedAgainst = "247805778bb52b3ac8a1e9a5b96be6da2c6bb36b"; :>> judgedAt = "2026-08-22"; :>> judgedBy = "claudeFable5"; }
    verification delegationClauseRetroGate : Test { :>> id = "8c31b74b-5344-44a1-98e3-f0b321b73835"; :>> title = "Sprint 420 retro gate (autonomous, D0049)"; :>> createdAt = "2026-08-22"; :>> createdBy = "claudeFable5"; :>> method = VerificationMethod::analyze; :>> procedureText = "Autonomous retro (D0049). AVOIDABLE-ISSUE SCAN under rcRecurrence: the rule-id collision is the recurrable class this sprint surfaced - sequential vanity ids invite collision and the duplicate-identity guard caught it; new rules use UUIDs, no new control needed (the existing one fired). WELL: the fork-choice pipeline built LAST sprint (issue223) was exercised THIS sprint end to end - the human's chat choice bound where the deck tap could not, and the ELI5-then-choose exchange is exactly the deciding-context practice the acceptance-request memory asks for. Estimate 2 pts, delivered 2."; }
    part delegationClauseRetroGateR1 : TestResult { :>> id = "84edad2b-b40b-4238-9c6f-e522087ed580"; :>> outcome = VerdictKind::pass; :>> judgedAgainst = "247805778bb52b3ac8a1e9a5b96be6da2c6bb36b"; :>> judgedAt = "2026-08-22"; :>> judgedBy = "claudeFable5"; }
}
