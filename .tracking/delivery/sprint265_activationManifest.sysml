// ProjectDeliveryS265 — Sprint 265: adoption becomes a DECLARED fact (srPortActivationManifest, D0138
// PROPOSED). Subsumes the issue089/090 presence-inference. EXECUTE. 5 pts.
package ProjectDeliveryS265 {
    private import EngineElement::*;
    private import EngineWork::*;
    private import EngineVerification::*;
    private import EngineRelationships::*;

    #CharteredBy dependency from activationStory to d0128;

    part activationStory : Story {
        :>> id = "0d800024-0814-6024-9b3e-000000300024";
        :>> title = "Sprint 265: process activation manifests — declared adoption, core guards immune (5 pts)";
        :>> createdAt = "2026-08-14"; :>> createdBy = "claudeOpus5"; :>> kind = WorkKind::code; :>> priority = WorkPriority::p0; :>> owner = "claudeOpus5"; :>> estimatedPoints = 5;
    }

    action def DeliveryRunS265 {
        action storyActivation;
        verification storyActivationDoD : Test { :>> id = "0d800025-0814-6025-9b3e-000000300025"; :>> method = VerificationMethod::demo; :>> procedureText = "Delivers dcActivationManifest / srPortActivationManifest (nProcessPortability, D0128). Issues 089 and 090 both answered 'what has this project adopted?' by INFERENCE from file presence, which cannot express intent and makes DELETING A FILE indistinguishable from legitimate non-adoption. DELIVERED: `.engine/contracts/process-units.toml` (engine fact — each process's skills, declared rules and guards), `.engine/contracts/activation.toml` (project choice), `keel activation|activate|deactivate`, keel-cli/src/activation.rs, activation-awareness in guards::run_all, the hard `activation-manifest` guard, and `inactive_processes` in orient's JSON. VERIFIED END-TO-END ON A FRESH `keel init` PROJECT, every DoD criterion measured: (1) passes with NO manifest, exit 0; (2) passes WITH a manifest, exit 0; (3) subset activation enforces only the active set and REPORTS each inactive control as NOT ACTIVE — never silently dropped; (4) activation genuinely changes enforcement, proven by holding the model constant — the same untriaged Issue yields full-gate exit 0 while issue-resolution is inactive and exit 1 the moment it is activated; (5) deactivating is visible in guard output and in orient's inactive_processes; (6) ADVERSARIAL — a hostile `active = []` still hard-fails on a duplicate id at exit 1, so core integrity is not deactivatable; (7) a typo in EITHER contract file fails loud at exit 1. Also fixed en route: `keel guard <name>` run by name reported FAIL and exit 1 for an inactive guard while the full gate passed — the single-guard exit now agrees with the enforced gate, since a script wired to the one-guard form must not block on a control the project deliberately does not enforce. 4 unit tests cover both invariants plus fail-loud typos; 161 tests total; clippy clean; validate + all 25 guards + check-engine green at da8b8de. This repo declares no manifest, so its own gate is unchanged."; }
        part storyActivationDoDR1 : TestResult { :>> id = "0d800026-0814-6026-9b3e-000000300026"; :>> outcome = VerdictKind::pass; :>> judgedAgainst = "da8b8de"; :>> judgedAt = "2026-08-14"; :>> judgedBy = "claudeOpus5"; }
    }

    verification amRefineGate : Test { :>> id = "0d800027-0814-6027-9b3e-000000300027"; :>> title = "Sprint 265 refine gate (DoR)"; :>> createdAt = "2026-08-14"; :>> createdBy = "claudeOpus5"; :>> method = VerificationMethod::inspect; :>> procedureText = "DoR: frontier top after dcReleaseAssetVerification cleared, and the item the human had steered toward ('the answer should be through defining portable processes, no?'). The DoR question that mattered was whether this needed a frozen-algebra CHANGE: there is NO process-to-rules linkage in the model, so 'activate a process as a unit' would need a new edge marker — except D0097 already established declared TOML contracts as the home for policy, which resolves it with no schema edit. estimatedPoints=5. DoR met."; }
    part amRefineGateR1 : TestResult { :>> id = "0d800028-0814-6028-9b3e-000000300028"; :>> outcome = VerdictKind::pass; :>> judgedAgainst = "da8b8de"; :>> judgedAt = "2026-08-14"; :>> judgedBy = "claudeOpus5"; }

    verification amStandupGate : Test { :>> id = "0d800029-0814-6029-9b3e-000000300029"; :>> title = "Sprint 265 standup gate"; :>> createdAt = "2026-08-14"; :>> createdBy = "claudeOpus5"; :>> method = VerificationMethod::inspect; :>> procedureText = "Approach: split the two claims into two files (engine fact vs project choice) so the engine's own structure is not editable as project config; decide the core-vs-process-bound split FIRST, since it is the whole safety property; then verify on a fresh init project rather than this repo, because this repo has no manifest and would exercise none of it. No blockers."; }
    part amStandupGateR1 : TestResult { :>> id = "0d80002a-0814-602a-9b3e-00000030002a"; :>> outcome = VerdictKind::pass; :>> judgedAgainst = "da8b8de"; :>> judgedAt = "2026-08-14"; :>> judgedBy = "claudeOpus5"; }

    verification amImplementGate : Test { :>> id = "0d80002b-0814-602b-9b3e-00000030002b"; :>> title = "Sprint 265 implement gate"; :>> createdAt = "2026-08-14"; :>> createdBy = "claudeOpus5"; :>> method = VerificationMethod::test; :>> procedureText = "Implemented at da8b8de. Three decisions carried the design. (1) A guard is CORE unless a process demonstrably owns it — default-to-enforced, so guards with no clean owner (requirement-rootedness, charter) stay on rather than being force-fitted into a unit to satisfy the taxonomy. (2) A first `activate`/`deactivate` write MATERIALISES the current effective state before applying the change, because absence means everything-active and a naive write of just the named process would silently deactivate the rest — the opposite of what the caller asked. (3) A declared-but-EMPTY `active` list is distinguished from an absent key, since 'activate nothing' and 'no manifest' are different claims with opposite meanings."; }
    part amImplementGateR1 : TestResult { :>> id = "0d80002c-0814-602c-9b3e-00000030002c"; :>> outcome = VerdictKind::pass; :>> judgedAgainst = "da8b8de"; :>> judgedAt = "2026-08-14"; :>> judgedBy = "claudeOpus5"; }

    verification amReviewGate : Test { :>> id = "0d80002d-0814-602d-9b3e-00000030002d"; :>> title = "Sprint 265 review gate"; :>> createdAt = "2026-08-14"; :>> createdBy = "claudeOpus5"; :>> method = VerificationMethod::inspect; :>> procedureText = "Reviewed. The feature is only safe because of what it REFUSES to do: a manifest able to switch off any guard would be the issue081 all-or-nothing bypass rebuilt, and worse for being sanctioned by a config file. Splitting core from process-bound is the whole of the safety argument, and it was tested adversarially rather than asserted. Two things left open deliberately: the process-to-controls mapping lives in TOML rather than as typed edges in the model, so it cannot be traced TO — acceptable under the D0097 precedent and worth revisiting if traceability is ever wanted; and the mapping currently covers six units, so a project authoring its own processes gets no unit for them and their controls default to core, which is the safe direction but means custom processes cannot yet be activated as units. D0138 is PROPOSED, not accepted, because it widens the meaning of `keel guard`."; }
    part amReviewGateR1 : TestResult { :>> id = "0d80002e-0814-602e-9b3e-00000030002e"; :>> outcome = VerdictKind::pass; :>> judgedAgainst = "da8b8de"; :>> judgedAt = "2026-08-14"; :>> judgedBy = "claudeOpus5"; }

    verification amCloseOutGate : Test { :>> id = "0d80002f-0814-602f-9b3e-00000030002f"; :>> title = "Sprint 265 closeOut gate (autonomous, D0049)"; :>> createdAt = "2026-08-14"; :>> createdBy = "claudeOpus5"; :>> method = VerificationMethod::inspect; :>> procedureText = "Autonomous closeOut (D0049). dcActivationManifest carries a passing DoD TestResult at da8b8de. All seven DoD criteria measured on a fresh init project, including the adversarial empty-active case and the constant-model proof that activation changes enforcement. 25 guards (19 hard, 6 warning-only); 161 tests; clippy clean; validate + guard + check-engine green. D0138 recorded as PROPOSED and surfaced to the human for acceptance — the gate-meaning widening is not self-acceptable, and the item is DELIVERED while that sign-off is outstanding."; }
    part amCloseOutGateR1 : TestResult { :>> id = "0d800030-0814-6030-9b3e-000000300030"; :>> outcome = VerdictKind::pass; :>> judgedAgainst = "da8b8de"; :>> judgedAt = "2026-08-14"; :>> judgedBy = "claudeOpus5"; }

    verification amRetroGate : Test { :>> id = "0d800031-0814-6031-9b3e-000000300031"; :>> title = "Sprint 265 retro gate (autonomous, D0049)"; :>> createdAt = "2026-08-14"; :>> createdBy = "claudeOpus5"; :>> method = VerificationMethod::analyze; :>> procedureText = "Autonomous retro (D0049) under D0131's retroTrack. WELL: (1) the safety property was decided BEFORE the file format, and it turned out to be the only part that mattered — a manifest able to disable any guard would have been a sanctioned rebuild of issue081; (2) it was verified on a FRESH init project rather than this repo, which declares no manifest and would have exercised none of the new behaviour, so testing here would have proved nothing while appearing to; (3) the enforcement claim was proven by holding the model CONSTANT and toggling only activation (exit 0 -> exit 1), rather than by reading the config back, which would only have confirmed the file said what I wrote. AVOIDABLE-ISSUE 1: I hit a Python escaping error editing a Rust format string and asserted my way into a failed patch that left the source uncompilable mid-edit — recovered by switching to the Edit tool with exact source text. NO NEW ITEM, reason stated: the assertion is what caught it immediately and the build error was unambiguous, so the cost was one round trip and the existing guidance (prefer the Edit tool over regex patching for exact source) already covers it; this is a tooling-choice slip, not a process gap. AVOIDABLE-ISSUE 2: I discovered only while testing that `keel guard <name>` run by name contradicted the full gate for an inactive guard — FAIL/exit 1 against ALL PASS/exit 0. Found by luck, in that I happened to run the single-guard form during verification; had I only tested the full gate it would have shipped as a live inconsistency for any script using the one-guard form. NO NEW ITEM, reason stated: the fix landed in this sprint and the general lesson — a feature that changes enforcement must be checked through EVERY entry point that reports enforcement, not just the aggregate one — is now recorded here and in D0138's consequences. Estimate 5 pts, delivered."; }
    part amRetroGateR1 : TestResult { :>> id = "0d800032-0814-6032-9b3e-000000300032"; :>> outcome = VerdictKind::pass; :>> judgedAgainst = "da8b8de"; :>> judgedAt = "2026-08-14"; :>> judgedBy = "claudeOpus5"; }
}
