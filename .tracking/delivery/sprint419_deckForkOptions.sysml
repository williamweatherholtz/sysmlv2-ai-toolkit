// ProjectDeliveryS419 — Sprint 419: fork Decisions get per-option sign buttons on the deck - a bare Sign on d0192 solicited a tap that could not bind (issue223). EXECUTE. 1 pts.
package ProjectDeliveryS419 {
    private import EngineElement::*;
    private import EngineWork::*;
    private import EngineVerification::*;
    private import EngineRelationships::*;

    #CharteredBy dependency from deckForkOptionsStory to d0047;

    part deckForkOptionsStory : Story {
        :>> id = "81df4c05-8248-44d2-848f-1c29c11db4fa";
        :>> title = "Sprint 419: the fork becomes tappable (1 pts)";
        :>> createdAt = "2026-08-22"; :>> createdBy = "claudeFable5"; :>> kind = WorkKind::code; :>> priority = WorkPriority::p0; :>> owner = "claudeFable5"; :>> estimatedPoints = 1;
    }

    action def DeliveryRunS419 {
        action storyDeckForkOptions;
        verification storyDeckForkOptionsDoD : Test { :>> id = "1f5420d7-bf18-4942-971b-58d8c7ae0057"; :>> method = VerificationMethod::test; :>> procedureText = "DELIVERED: dcDeckForkOptions (resolves issue223). THE DEFECT: d0192 enumerates OPTION A / OPTION B and states 'accepting this Decision means choosing ONE', yet the deck rendered it as one bare Sign button; wweatherholtz tapped it (inbox row uid 5b1d2b0e, At 2026-08-22T06:54:40Z) and the gesture could not be recorded - solicited and wasted, the D0054 friction class. THE CONTROL (D0047): fork_options() scans a pending acceptance's decision file for two-or-more 'OPTION X (label)' enumerations; a fork card renders one full-width sign button per option ('Sign A - amend the requirement' / 'Sign B - close the path'); the chosen option is stamped into the note on BOTH transports (local /api/decision/accept body and the remote inbox row's Note cell), so the recorded acceptance CARRIES the choice; tapping a different option switches instead of clearing (data-opt-chosen tracked alongside data-verdict). VERIFIED: unit test pins the D0192 text shape plus the one-option and no-option negatives; the emitted-JS parse test still passes; the regenerated deck shows exactly 1 waiting item with both data-opt buttons (read back by grep); full suite 280+ green, clippy pedantic+nursery clean. The republished deck (same URL) now offers the human the choice their last tap could not express."; }
        part storyDeckForkOptionsDoDR1 : TestResult { :>> id = "bfb55770-9a39-411a-be88-90ebcbb4737e"; :>> outcome = VerdictKind::pass; :>> judgedAgainst = "0a5d84be7185612dba5cb078845014a5777185c1"; :>> judgedAt = "2026-08-22"; :>> judgedBy = "claudeFable5"; }
    }

    verification deckForkOptionsRefineGate : Test { :>> id = "bab69145-e678-43b2-9842-f80a83abf567"; :>> title = "Sprint 419 refine gate (DoR)"; :>> createdAt = "2026-08-22"; :>> createdBy = "claudeFable5"; :>> method = VerificationMethod::inspect; :>> procedureText = "DoR. Correction-becomes-control (D0047) for issue223, found this morning when the 2026-08-22 inbox batch carried a d0192 accept tap that could not bind. In scope: the deck generator and its emitted JS. Out of scope: the acceptance API (a note is already a first-class field on both transports). 1 point."; }
    part deckForkOptionsRefineGateR1 : TestResult { :>> id = "7d29f3f9-28cd-4b01-9992-2e009c623856"; :>> outcome = VerdictKind::pass; :>> judgedAgainst = "0a5d84be7185612dba5cb078845014a5777185c1"; :>> judgedAt = "2026-08-22"; :>> judgedBy = "claudeFable5"; }
    verification deckForkOptionsStandupGate : Test { :>> id = "287725db-4348-4a85-b1d3-de70d1e9fe16"; :>> title = "Sprint 419 standup gate"; :>> createdAt = "2026-08-22"; :>> createdBy = "claudeFable5"; :>> method = VerificationMethod::inspect; :>> procedureText = "Approach: parse the fork structurally from the decision text's own OPTION X (label) convention rather than special-casing d0192; thread the choice through the existing note field rather than adding a column or endpoint - zero schema change, zero new write path. No blockers."; }
    part deckForkOptionsStandupGateR1 : TestResult { :>> id = "07a8002c-7327-49ba-9c79-8bad7c5533f7"; :>> outcome = VerdictKind::pass; :>> judgedAgainst = "0a5d84be7185612dba5cb078845014a5777185c1"; :>> judgedAt = "2026-08-22"; :>> judgedBy = "claudeFable5"; }
    verification deckForkOptionsImplementGate : Test { :>> id = "f48981ca-0684-47b2-b875-600dd941e6b9"; :>> title = "Sprint 419 implement gate"; :>> createdAt = "2026-08-22"; :>> createdBy = "claudeFable5"; :>> method = VerificationMethod::test; :>> procedureText = "Verified by running: cargo test -p keel-cli --lib deck (6 pass, including the new fork_options_parse_the_d0192_shape and the emitted-JS parse check); full workspace suite green; clippy clean after two machine-caught lints (drop_non_drop, format_collect); keel deck regenerated and grep read back data-opt=OPTION A / OPTION B and both button labels; the artifact republished to the SAME url (1b5ba2eb) so their bookmark still works."; }
    part deckForkOptionsImplementGateR1 : TestResult { :>> id = "d778ab7c-d063-42e5-903c-d327dd209949"; :>> outcome = VerdictKind::pass; :>> judgedAgainst = "0a5d84be7185612dba5cb078845014a5777185c1"; :>> judgedAt = "2026-08-22"; :>> judgedBy = "claudeFable5"; }
    verification deckForkOptionsReviewGate : Test { :>> id = "e3c64e29-d729-49ce-bbf8-a3938b06e398"; :>> title = "Sprint 419 review gate — three passes per D0172"; :>> createdAt = "2026-08-22"; :>> createdBy = "claudeFable5"; :>> method = VerificationMethod::inspect; :>> procedureText = "PASS 1, CLAIMS: the button labels and data-opt values quoted above are grep output from the generated page, not intent. PASS 2, BOUNDARY: the OPTION-enumeration convention is a TEXT convention, not schema - a decision that words its fork differently gets the old bare Sign button; that boundary is stated in fork_options' doc and the failure mode is the status quo, never a wrong recording. PASS 3, OWN DIFF: my first DoD text cited issue224 before the write returned issue223 - the issue212 lesson (cite the number the write RETURNS) recurred in draft and was caught before commit; both surfaces swept. WHAT A REVIEWER SHOULD ATTACK: the toggle semantics on a fork card (data-opt-chosen) are hand-verified JS, covered only by the parse check - a behavioral JS test rig remains the deck's known verification gap (issue191's residual)."; }
    part deckForkOptionsReviewGateR1 : TestResult { :>> id = "8b406f51-2031-4bb8-9ee7-68572bb7c1c4"; :>> outcome = VerdictKind::pass; :>> judgedAgainst = "0a5d84be7185612dba5cb078845014a5777185c1"; :>> judgedAt = "2026-08-22"; :>> judgedBy = "claudeFable5"; }
    verification deckForkOptionsCloseOutGate : Test { :>> id = "9d5dbc46-cb78-46f6-b219-a837cd2abee5"; :>> title = "Sprint 419 closeOut gate (autonomous, D0049)"; :>> createdAt = "2026-08-22"; :>> createdBy = "claudeFable5"; :>> method = VerificationMethod::inspect; :>> procedureText = "Autonomous closeOut (D0049). issue223 resolves via dcDeckForkOptions (edge recorded at issue creation); DoD flipped on the read-backs; validate + guards green; the deck artifact is live with the fork choice as the sole waiting card."; }
    part deckForkOptionsCloseOutGateR1 : TestResult { :>> id = "59b6ad53-f230-4357-9b2c-049dc7e97fe6"; :>> outcome = VerdictKind::pass; :>> judgedAgainst = "0a5d84be7185612dba5cb078845014a5777185c1"; :>> judgedAt = "2026-08-22"; :>> judgedBy = "claudeFable5"; }
    verification deckForkOptionsRetroGate : Test { :>> id = "e1bcd061-3992-449b-96f7-69791c877f76"; :>> title = "Sprint 419 retro gate (autonomous, D0049)"; :>> createdAt = "2026-08-22"; :>> createdBy = "claudeFable5"; :>> method = VerificationMethod::analyze; :>> procedureText = "Autonomous retro (D0049). AVOIDABLE-ISSUE SCAN under rcRecurrence: issue223 is itself the scan's product - the wasted-gesture class was caught on its FIRST occurrence and became a control the same day, which is the D0047 loop working at its intended latency. WELL: the fix rode existing rails end to end (note field, existing endpoints, existing inbox columns) - no new truth surface. WATCH: the OPTION text convention now carries meaning; if record decision ever gains a structured options field, fork_options should read that instead. Estimate 1 pt, delivered 1."; }
    part deckForkOptionsRetroGateR1 : TestResult { :>> id = "286892ce-949b-4ef7-ba74-bbab1518c91d"; :>> outcome = VerdictKind::pass; :>> judgedAgainst = "0a5d84be7185612dba5cb078845014a5777185c1"; :>> judgedAt = "2026-08-22"; :>> judgedBy = "claudeFable5"; }
}
