// ProjectDeliveryS272 — Sprint 272: process-to-controls moves from TOML into the MODEL as base SysML v2
// `assert constraint` (D0139(D)). process-units.toml retired. EXECUTE. 5 pts.
package ProjectDeliveryS272 {
    private import EngineElement::*;
    private import EngineWork::*;
    private import EngineVerification::*;
    private import EngineRelationships::*;

    #CharteredBy dependency from assertConstraintsStory to d0139;

    part assertConstraintsStory : Story {
        :>> id = "0d8000a9-0814-60a9-9b3e-0000003000a9";
        :>> title = "Sprint 272: process-to-controls as `assert constraint` in the model; retire process-units.toml (5 pts)";
        :>> createdAt = "2026-08-14"; :>> createdBy = "claudeOpus5"; :>> kind = WorkKind::code; :>> priority = WorkPriority::p0; :>> owner = "claudeOpus5"; :>> estimatedPoints = 5;
    }

    action def DeliveryRunS272 {
        action storyAssertConstraints;
        verification storyAssertConstraintsDoD : Test { :>> id = "0d8000aa-0814-60aa-9b3e-0000003000aa"; :>> method = VerificationMethod::demo; :>> procedureText = "Covers dcProcessAssertsConstraints — the first real base-first CONVERSION, and the one that corrects my own sprint-265 choice. The process-to-controls mapping lived in `.engine/contracts/process-units.toml`, a table no `keel trace`, declared view or viewpoint could reach, so an ENGINE FACT sat outside the model that is supposed to hold every engine fact. CLAUDE.md §1.7 already held that the guards ARE the constraint layer, so `assert constraint` states exactly what was meant. DELIVERED: (1) instance bodies now capture member features, so `assert constraint c : Ok;` inside a `part x : Process { }` is read and its type resolved — the enabler, since sprint 271 had only covered type-DEF bodies; (2) `.engine/rules/guard-constraints.sysml` declares each of the 14 process-bound guards as a `constraint def`, named in camelCase so `sprintCoverage` recovers `sprint-coverage` by one mechanical rule with no lookup table to drift; (3) 14 `assert constraint` members attached to the SPECIFIC parts that enforce them — ceremony and sprint-coverage on `standupGate`, retro-backlog on `retroTrack`, priority-inversion and verification-trace on `refineLink` — which is strictly more informative than the flat file-level list the TOML held; (4) `units_from_model` reads the mapping from `.engine/processes/`, keyed by FILE, as the union of asserts across its parts; (5) process-units.toml DELETED, no tombstone. VERIFIED — five properties, each measured on a fresh `keel init` project: `keel activation` output is IDENTICAL to the TOML version (6 units, same guard counts), so the conversion is behaviour-preserving; a fresh project passes its own gate; subset activation still ENFORCES (exit 1 with issue-resolution active) and REPORTS `NOT ACTIVE` (exit 0 inactive); the ADVERSARIAL `active = []` still hard-fails on a duplicate id, so core guards remain immune; and a typo in a constraint name is now an UNRESOLVED TYPE caught by `check-engine`, which is strictly stronger than the TOML, where a misspelling was only ever caught by a name-list check. clippy clean; 161 tests including three rewritten from the TOML fixture plus a new camel-to-kebab test; validate + all 27 guards + check-engine green."; }
        part storyAssertConstraintsDoDR1 : TestResult { :>> id = "0d8000ab-0814-60ab-9b3e-0000003000ab"; :>> outcome = VerdictKind::pass; :>> judgedAgainst = "5b1aea4"; :>> judgedAt = "2026-08-14"; :>> judgedBy = "claudeOpus5"; }
    }

    verification acRefineGate : Test { :>> id = "0d8000ac-0814-60ac-9b3e-0000003000ac"; :>> title = "Sprint 272 refine gate (DoR)"; :>> createdAt = "2026-08-14"; :>> createdBy = "claudeOpus5"; :>> method = VerificationMethod::inspect; :>> procedureText = "DoR: dcParserReadBase completed in sprint 271, so `assert constraint` is finally READ and RESOLVED — the precondition this conversion was blocked on since D0139 was accepted. Doing it earlier would have produced asserts that parsed clean and mapped nothing. estimatedPoints=5, larger than the parser sprints because it touches parser, schema, six process files, the activation reader and its tests. DoR met."; }
    part acRefineGateR1 : TestResult { :>> id = "0d8000ad-0814-60ad-9b3e-0000003000ad"; :>> outcome = VerdictKind::pass; :>> judgedAgainst = "5b1aea4"; :>> judgedAt = "2026-08-14"; :>> judgedBy = "claudeOpus5"; }

    verification acStandupGate : Test { :>> id = "0d8000ae-0814-60ae-9b3e-0000003000ae"; :>> title = "Sprint 272 standup gate"; :>> createdAt = "2026-08-14"; :>> createdBy = "claudeOpus5"; :>> method = VerificationMethod::inspect; :>> procedureText = "Approach: prove behaviour-preservation by diffing `keel activation` output before and after rather than by reasoning about it, then re-run all four D0138 safety properties on a fresh project — the conversion must not weaken the core-guard immunity that made activation safe in the first place. No blockers."; }
    part acStandupGateR1 : TestResult { :>> id = "0d8000af-0814-60af-9b3e-0000003000af"; :>> outcome = VerdictKind::pass; :>> judgedAgainst = "5b1aea4"; :>> judgedAt = "2026-08-14"; :>> judgedBy = "claudeOpus5"; }

    verification acImplementGate : Test { :>> id = "0d8000b0-0814-60b0-9b3e-0000003000b0"; :>> title = "Sprint 272 implement gate"; :>> createdAt = "2026-08-14"; :>> createdBy = "claudeOpus5"; :>> method = VerificationMethod::test; :>> procedureText = "Two design points. (1) A unit is a FILE, and its guards are the UNION of asserts across every part in it. `agile-workflow.sysml` holds 21 Process/ProcessStep parts and no single root, so a file-level assert had nowhere natural to live; attaching each assert to the step that actually enforces it is both the only workable shape and better modelling than the TOML's flat list. (2) The constraint def name is the camelCase form of the guard name, converted mechanically. A lookup table would have been more explicit and would have been a second place for the mapping to drift — the exact failure this sprint exists to remove."; }
    part acImplementGateR1 : TestResult { :>> id = "0d8000b1-0814-60b1-9b3e-0000003000b1"; :>> outcome = VerdictKind::pass; :>> judgedAgainst = "5b1aea4"; :>> judgedAt = "2026-08-14"; :>> judgedBy = "claudeOpus5"; }

    verification acReviewGate : Test { :>> id = "0d8000b2-0814-60b2-9b3e-0000003000b2"; :>> title = "Sprint 272 review gate"; :>> createdAt = "2026-08-14"; :>> createdBy = "claudeOpus5"; :>> method = VerificationMethod::inspect; :>> procedureText = "Reviewed. This is the first conversion that actually reduces the bespoke surface the human objected to, and it does so with a base construct the KERNEL accepts, not merely one our parser tolerates. The typo result is the clearest evidence it was worth doing: under the TOML a misspelled guard name was caught only because a guard happened to check the name list, whereas now it is an unresolved constraint TYPE — the model itself refuses it. That is the general argument of D0139 made concrete. NOT claimed: this does not shrink the marker count, which D0140 settled separately; it moves one mapping from config into the model."; }
    part acReviewGateR1 : TestResult { :>> id = "0d8000b3-0814-60b3-9b3e-0000003000b3"; :>> outcome = VerdictKind::pass; :>> judgedAgainst = "5b1aea4"; :>> judgedAt = "2026-08-14"; :>> judgedBy = "claudeOpus5"; }

    verification acCloseOutGate : Test { :>> id = "0d8000b4-0814-60b4-9b3e-0000003000b4"; :>> title = "Sprint 272 closeOut gate (autonomous, D0049)"; :>> createdAt = "2026-08-14"; :>> createdBy = "claudeOpus5"; :>> method = VerificationMethod::inspect; :>> procedureText = "Autonomous closeOut (D0049). dcProcessAssertsConstraints carries a passing DoD TestResult; D0139 clause (D) is DELIVERED. process-units.toml deleted with no tombstone. Doc-sync: the activation module header, the dead-reference error message, and guards.md's adoption section. clippy clean; 161 tests; validate + all 27 guards + check-engine green. No gate bypassed."; }
    part acCloseOutGateR1 : TestResult { :>> id = "0d8000b5-0814-60b5-9b3e-0000003000b5"; :>> outcome = VerdictKind::pass; :>> judgedAgainst = "5b1aea4"; :>> judgedAt = "2026-08-14"; :>> judgedBy = "claudeOpus5"; }

    verification acRetroGate : Test { :>> id = "0d8000b6-0814-60b6-9b3e-0000003000b6"; :>> title = "Sprint 272 retro gate (autonomous, D0049)"; :>> createdAt = "2026-08-14"; :>> createdBy = "claudeOpus5"; :>> method = VerificationMethod::analyze; :>> procedureText = "Autonomous retro (D0049) under D0131's retroTrack. WELL: (1) behaviour-preservation was demonstrated by diffing the actual `keel activation` output rather than argued, and it was identical — the cheapest possible proof that a conversion changed representation and not meaning; (2) all four D0138 safety properties were re-run on a fresh project rather than assumed to survive, including the adversarial empty-active case; (3) the typo case turned out STRONGER after conversion, which is the concrete evidence D0139's portability argument was not merely aesthetic. AVOIDABLE-ISSUE 1: my scripted patch targeted `: Process` parts and silently reported three MISSING parts in agile-workflow, which are `: ProcessStep`. The script printed the misses, so nothing was lost — but I had assumed a single root Process per file without checking, and the file has 21 parts and no root. NO NEW ITEM, reason stated: the script reported its own failure and I acted on it, which is the behaviour wanted; the transferable point is that assuming a container's shape is a measurement, and one grep would have settled it before writing the patch. AVOIDABLE-ISSUE 2: three activation tests failed after the conversion because they were written against the TOML fixture. NO NEW ITEM: this is tests doing their job — a fixture describing a retired mechanism SHOULD fail — and they were rewritten against the model, plus a new test pinning the camel-to-kebab rule that the conversion now depends on. Estimate 5 pts, delivered."; }
    part acRetroGateR1 : TestResult { :>> id = "0d8000b7-0814-60b7-9b3e-0000003000b7"; :>> outcome = VerdictKind::pass; :>> judgedAgainst = "5b1aea4"; :>> judgedAt = "2026-08-14"; :>> judgedBy = "claudeOpus5"; }
}
