// ProjectDeliveryS395 — Sprint 395: the two admitted enforcement gaps get their guards (D0191) - and guard 43 catches two real defects on its first run. EXECUTE. 2 pts.
package ProjectDeliveryS395 {
    private import EngineElement::*;
    private import EngineWork::*;
    private import EngineVerification::*;
    private import EngineRelationships::*;

    #CharteredBy dependency from admittedGapsGuardsStory to d0191;

    part admittedGapsGuardsStory : Story {
        :>> id = "b2596ae2-43d9-4e35-9d78-0acfe0eb5ef5";
        :>> title = "Sprint 395: the admitted gaps are guarded (2 pts)";
        :>> createdAt = "2026-08-21"; :>> createdBy = "claudeFable5"; :>> kind = WorkKind::code; :>> priority = WorkPriority::p0; :>> owner = "claudeFable5"; :>> estimatedPoints = 2;
    }

    action def DeliveryRunS395 {
        action storyAdmittedGapsGuards;
        verification storyAdmittedGapsGuardsDoD : Test { :>> id = "1acc7a82-c79f-45b9-b23d-a67b4446d517"; :>> method = VerificationMethod::test; :>> procedureText = "DELIVERED (D0191, accepted on their words 'agreed. proceed' to the presented plan): guards 43 and 44, both WARNING tier per the guided profile, both unit-owned via the D0139(D) assert-constraint declaration so unadopted processes are not gated. GUARD 43 release-recorded (deploy unit): every v-prefixed tag has a Release item naming it whose recorded commit matches the tag's; FIRST RUN CAUGHT BOTH DEFECT SHAPES IT EXISTS FOR - v0.1.0 had NO Release item (backfilled as release010 with the commit read from the tag itself: recorded, not invented) and v0.2.0's tag sits at e2c812f, two housekeeping commits past its recorded 425145d (git rev-list counted; the warning STANDS - the Release item is claudeOpus5's authored fact and D0108 forbids a non-owner overwrite; theirs or the human's to reconcile). GUARD 44 enrollment-binding (actor-enrollment unit): a machine binding must resolve to a registered Person or a kind-carrying Actor - until now NOTHING validated .keel/actor and a bad name surfaced only when a downstream write refused; scans this machine's real binding (1, clean). The two satisfied UNDER-GUARDED entries left process-enforcement.toml in the same commit (no tombstones); constraint defs added to guard-constraints.sysml; imports added to both unit files; guards.md + CLAUDE.md count 42 -> 44 in the same commit (doc-sync). Deliberately NOT taken: distributedCollaboration and migration - visible in the same lens read, excluded from the plan the human accepted, still recorded admitted gaps."; }
        part storyAdmittedGapsGuardsDoDR1 : TestResult { :>> id = "5af37a38-fc16-4cbc-bce0-a23d7980f26e"; :>> outcome = VerdictKind::pass; :>> judgedAgainst = "1d84acd"; :>> judgedAt = "2026-08-21"; :>> judgedBy = "claudeFable5"; }
    }

    verification admittedGapsGuardsRefineGate : Test { :>> id = "79735b1e-e4e3-4c08-af99-65389ce770f7"; :>> title = "Sprint 395 refine gate (DoR)"; :>> createdAt = "2026-08-21"; :>> createdBy = "claudeFable5"; :>> method = VerificationMethod::inspect; :>> procedureText = "DoR. Chartered by d0191, accepted this session on the human's verbatim 'agreed. proceed' to the plan naming exactly these two gaps. Both contracts already admitted the claims are checkable text properties, so the work is the predicate + ownership + contract cleanup. 2 points."; }
    part admittedGapsGuardsRefineGateR1 : TestResult { :>> id = "e3e07e7b-9d42-4d55-a8cb-cb235f7f88da"; :>> outcome = VerdictKind::pass; :>> judgedAgainst = "1d84acd"; :>> judgedAt = "2026-08-21"; :>> judgedBy = "claudeFable5"; }
    verification admittedGapsGuardsStandupGate : Test { :>> id = "260ab735-a027-425e-98ae-b4a3de1b4dee"; :>> title = "Sprint 395 standup gate"; :>> createdAt = "2026-08-21"; :>> createdBy = "claudeFable5"; :>> method = VerificationMethod::inspect; :>> procedureText = "Approach: guards first (run them against the real tree before recording anything), unit ownership via the model's assert-constraint mechanism rather than any new registry, contract entries deleted rather than annotated, and whatever the first run catches gets triaged as facts - which turned out to be the sprint's real payload. No blockers."; }
    part admittedGapsGuardsStandupGateR1 : TestResult { :>> id = "9b00becd-9fe9-4f86-a43a-d740c2f5e37f"; :>> outcome = VerdictKind::pass; :>> judgedAgainst = "1d84acd"; :>> judgedAt = "2026-08-21"; :>> judgedBy = "claudeFable5"; }
    verification admittedGapsGuardsImplementGate : Test { :>> id = "369d8b43-9abd-4c23-9e21-b2910a32255a"; :>> title = "Sprint 395 implement gate"; :>> createdAt = "2026-08-21"; :>> createdBy = "claudeFable5"; :>> method = VerificationMethod::test; :>> procedureText = "Verified by running, not reading: guard 43 scans 5 tags and warned twice on first run (the missing v0.1.0 item, the v0.2.0 commit skew - confirmed by git rev-list: recorded 425145d IS an ancestor, 2 commits behind tag e2c812f); after the backfill it warns once, accurately. Guard 44 scans this machine's live binding clean. check-engine clean after the constraint defs + imports landed (its 2 unresolved-reference diagnostics were machine-caught and fixed). cargo test 278 passed incl. the dispatch-parity and population meta-tests; clippy pedantic+nursery clean; validate 432 clean."; }
    part admittedGapsGuardsImplementGateR1 : TestResult { :>> id = "6bf68b2c-bbbc-4839-abbb-845124791c3e"; :>> outcome = VerdictKind::pass; :>> judgedAgainst = "1d84acd"; :>> judgedAt = "2026-08-21"; :>> judgedBy = "claudeFable5"; }
    verification admittedGapsGuardsReviewGate : Test { :>> id = "44a0c35e-9dc3-4528-b838-281478c22654"; :>> title = "Sprint 395 review gate — three passes per D0172"; :>> createdAt = "2026-08-21"; :>> createdBy = "claudeFable5"; :>> method = VerificationMethod::inspect; :>> procedureText = "PASS 1, CLAIMS: every count above is tool output from this session; the v0.2.0 skew is git-verified ancestry, not inference. PASS 2, BOUNDARY: the deactivatability boundary is the deliberate design - both guards are unit-owned so deactivating the process removes its guard, which is CORRECT for process-specific claims and is exactly why the actors guard was NOT moved into the enrollment unit (identity integrity must survive process deactivation). PASS 3, OWN DIFF: the guards395 fix script carried three self-escaping bugs (literal backslash-n where newlines were meant) caught by re-reading before running - the authoring-mangling family again, this time caught pre-execution; and GUARD_NAMES' array length was machine-caught by the compiler. WHAT A REVIEWER SHOULD ATTACK: the standing v0.2.0 warning is a permanent WARN until someone reconciles it - if it normalizes warning-blindness, the right move is the owner-side supersede, not a guard exemption; and release-recorded matches tags to Release items by title substring, so a title naming two tags would satisfy both - acceptable while titles are one-version by convention, named here so the assumption is on record."; }
    part admittedGapsGuardsReviewGateR1 : TestResult { :>> id = "f3957352-d324-48d1-b9ab-930d8fda327f"; :>> outcome = VerdictKind::pass; :>> judgedAgainst = "1d84acd"; :>> judgedAt = "2026-08-21"; :>> judgedBy = "claudeFable5"; }
    verification admittedGapsGuardsCloseOutGate : Test { :>> id = "495ca564-7623-497d-8165-ecfff48baad8"; :>> title = "Sprint 395 closeOut gate (autonomous, D0049)"; :>> createdAt = "2026-08-21"; :>> createdBy = "claudeFable5"; :>> method = VerificationMethod::inspect; :>> procedureText = "Autonomous closeOut (D0049). Hardening lens read back after: the undeclared bucket drops to four (two remaining admitted gaps + two declared-false entries) and deploy/actorEnrollment report their guards. validate + check-engine + all 44 guards green (one accurate standing warning)."; }
    part admittedGapsGuardsCloseOutGateR1 : TestResult { :>> id = "e3ad8c7c-f720-4a75-9c47-02e8755bd475"; :>> outcome = VerdictKind::pass; :>> judgedAgainst = "1d84acd"; :>> judgedAt = "2026-08-21"; :>> judgedBy = "claudeFable5"; }
    verification admittedGapsGuardsRetroGate : Test { :>> id = "f2827afa-fd83-47a7-a0d2-ee7072b0b45e"; :>> title = "Sprint 395 retro gate (autonomous, D0049)"; :>> createdAt = "2026-08-21"; :>> createdBy = "claudeFable5"; :>> method = VerificationMethod::analyze; :>> procedureText = "Autonomous retro (D0049). AVOIDABLE-ISSUE SCAN under rcRecurrence: none new - the escape-mangling family appeared and was caught pre-execution by the review-before-run practice the standing rule prescribes. WELL: run-the-guard-before-recording turned the sprint from bookkeeping into detection - guard 43 found a missing authored fact and a tag/record skew that four releases of manual discipline had not. The two remaining admitted gaps (distributedCollaboration: the existing ownership guard needs only its unit declaration; migration: the census is a view, not a guard) are one Decision away and were deliberately left outside this sprint's accepted scope. Estimate 2 pts, delivered 2."; }
    part admittedGapsGuardsRetroGateR1 : TestResult { :>> id = "68f4f914-76f4-4a52-8532-2b891f5076b9"; :>> outcome = VerdictKind::pass; :>> judgedAgainst = "1d84acd"; :>> judgedAt = "2026-08-21"; :>> judgedBy = "claudeFable5"; }
}
