// ProjectDeliveryS264 — Sprint 264: a release is published only once a downloaded asset reports the
// tagged version (issue092, D0137). CHANGE route — human-accepted before application. 1 pt.
package ProjectDeliveryS264 {
    private import EngineElement::*;
    private import EngineWork::*;
    private import EngineVerification::*;
    private import EngineRelationships::*;

    #CharteredBy dependency from releaseAssetStory to d0137;

    part releaseAssetStory : Story {
        :>> id = "0d800013-0814-6013-9b3e-000000300013";
        :>> title = "Sprint 264: relTagPublish requires running a downloaded asset; D0137 (1 pt)";
        :>> createdAt = "2026-08-14"; :>> createdBy = "claudeOpus5"; :>> kind = WorkKind::decision; :>> priority = WorkPriority::p0; :>> owner = "claudeOpus5"; :>> estimatedPoints = 1;
    }

    action def DeliveryRunS264 {
        action storyReleaseAsset;
        verification storyReleaseAssetDoD : Test { :>> id = "0d800014-0814-6014-9b3e-000000300014"; :>> method = VerificationMethod::inspect; :>> procedureText = "Delivers dcReleaseAssetVerification (issue092) under D0137, accepted by wweatherholtz before application. `relTagPublish` required 'verify the workflow succeeded and the assets are attached', a condition satisfied by a green workflow plus a non-empty asset list — so v0.2.0, v0.2.1 and v0.2.2 were each verified by confirming files existed at a URL and no published asset was ever downloaded or executed. CHANGE APPLIED: the step now requires obtaining a published asset and confirming `keel version` reports the tagged version and the tag's commit; a mismatch means NOT published, so the fix is to re-tag rather than record it; and the check is folded into the step's producedArtifact so it is part of what the step DELIVERS rather than optional diligence. Scoped to ONE asset plus the green matrix build, deliberately: no host here can execute the macOS-arm64 binary, and requiring the unsatisfiable is how a gate trains its actor to bypass it (issue081). VERIFY: the process step and the release skill both name the OBSERVATION rather than the hoped-for condition; the skill carries the concrete `gh release download` + `keel version` commands and two new anti-patterns (verifying by asset existence; claiming behaviour measured on a local build); D0137 records the change with its acceptance event bound to the human's '#2 accepted' against a proposal that named the definition, the condition and the defect; marked #ProspectiveChange so the three prior Release facts are not retro-failed for evidence the process did not then require (issue068). keel validate + all 24 guards + check-engine green at 95ec70e. The practice was already DEMONSTRATED on v0.2.3 (asset reported keel 0.2.3 / build commit b006f10, matching the tag) before being codified."; }
        part storyReleaseAssetDoDR1 : TestResult { :>> id = "0d800015-0814-6015-9b3e-000000300015"; :>> outcome = VerdictKind::pass; :>> judgedAgainst = "95ec70e"; :>> judgedAt = "2026-08-14"; :>> judgedBy = "claudeOpus5"; }
    }

    verification raiRefineGate : Test { :>> id = "0d800016-0814-6016-9b3e-000000300016"; :>> title = "Sprint 264 refine gate (DoR)"; :>> createdAt = "2026-08-14"; :>> createdBy = "claudeOpus5"; :>> method = VerificationMethod::inspect; :>> procedureText = "DoR: the item sat at frontier top for two turns BLOCKED ON A CONTENT GATE rather than on effort — editing a process definition is a CHANGE (§3a) and cannot be self-accepted. The DoR condition was the human's sign-off, which arrived as '#2 accepted'. estimatedPoints=1, small because the design was already settled in issue092 and the evidence already gathered on v0.2.3. DoR met."; }
    part raiRefineGateR1 : TestResult { :>> id = "0d800017-0814-6017-9b3e-000000300017"; :>> outcome = VerdictKind::pass; :>> judgedAgainst = "95ec70e"; :>> judgedAt = "2026-08-14"; :>> judgedBy = "claudeOpus5"; }

    verification raiStandupGate : Test { :>> id = "0d800018-0814-6018-9b3e-000000300018"; :>> title = "Sprint 264 standup gate"; :>> createdAt = "2026-08-14"; :>> createdBy = "claudeOpus5"; :>> method = VerificationMethod::inspect; :>> procedureText = "Approach: apply the accepted change to the process definition and its deploying skill in one commit (doc-sync rides every change), author D0137 with the acceptance event quoting the proposal the human accepted, and mark it #ProspectiveChange so prior releases are not retro-failed. No blockers."; }
    part raiStandupGateR1 : TestResult { :>> id = "0d800019-0814-6019-9b3e-000000300019"; :>> outcome = VerdictKind::pass; :>> judgedAgainst = "95ec70e"; :>> judgedAt = "2026-08-14"; :>> judgedBy = "claudeOpus5"; }

    verification raiImplementGate : Test { :>> id = "0d80001a-0814-601a-9b3e-00000030001a"; :>> title = "Sprint 264 implement gate"; :>> createdAt = "2026-08-14"; :>> createdBy = "claudeOpus5"; :>> method = VerificationMethod::inspect; :>> procedureText = "Applied at 95ec70e. The wording change that matters is small: 'verify the assets are attached' states a hoped-for CONDITION and is satisfiable without observing anything about the assets, whereas 'download one and confirm it reports the tagged version and commit' names an OBSERVATION. Folding it into producedArtifact is what stops it degrading back into optional diligence. keel check-engine is the enforced instance gate for .engine changes and passed; the JVM workflow validator was attempted out of caution, stalled, and was killed and swept — it gates .engine/workflows/, which this change does not touch."; }
    part raiImplementGateR1 : TestResult { :>> id = "0d80001b-0814-601b-9b3e-00000030001b"; :>> outcome = VerdictKind::pass; :>> judgedAgainst = "95ec70e"; :>> judgedAt = "2026-08-14"; :>> judgedBy = "claudeOpus5"; }

    verification raiReviewGate : Test { :>> id = "0d80001c-0814-601c-9b3e-00000030001c"; :>> title = "Sprint 264 review gate"; :>> createdAt = "2026-08-14"; :>> createdBy = "claudeOpus5"; :>> method = VerificationMethod::inspect; :>> procedureText = "Reviewed. The change is right and narrow, and the discipline held where it usually slips: the fix was PROPOSED and left unapplied across two turns even though I was confident in it and could have folded it into a release commit unnoticed. What remains unaddressed on purpose is the producer side — a CI step self-checking the asset before upload — which D0137 records as a reasonable later addition but explicitly not a substitute, because it verifies the artifact where it is made rather than where it is received, and the receiving side is the one that was never checked."; }
    part raiReviewGateR1 : TestResult { :>> id = "0d80001d-0814-601d-9b3e-00000030001d"; :>> outcome = VerdictKind::pass; :>> judgedAgainst = "95ec70e"; :>> judgedAt = "2026-08-14"; :>> judgedBy = "claudeOpus5"; }

    verification raiCloseOutGate : Test { :>> id = "0d80001e-0814-601e-9b3e-00000030001e"; :>> title = "Sprint 264 closeOut gate (autonomous, D0049)"; :>> createdAt = "2026-08-14"; :>> createdBy = "claudeOpus5"; :>> method = VerificationMethod::inspect; :>> procedureText = "Autonomous closeOut (D0049). dcReleaseAssetVerification carries a passing DoD TestResult at 95ec70e; issue092 RESOLVES. D0137 accepted and recorded with its acceptance event. Process definition and release skill updated in the same commit. keel validate + all 24 guards + check-engine green; JVMs swept to zero."; }
    part raiCloseOutGateR1 : TestResult { :>> id = "0d80001f-0814-601f-9b3e-00000030001f"; :>> outcome = VerdictKind::pass; :>> judgedAgainst = "95ec70e"; :>> judgedAt = "2026-08-14"; :>> judgedBy = "claudeOpus5"; }

    verification raiRetroGate : Test { :>> id = "0d800020-0814-6020-9b3e-000000300020"; :>> title = "Sprint 264 retro gate (autonomous, D0049)"; :>> createdAt = "2026-08-14"; :>> createdBy = "claudeOpus5"; :>> method = VerificationMethod::analyze; :>> procedureText = "Autonomous retro (D0049) under D0131's retroTrack. WELL: (1) the CHANGE was proposed and genuinely withheld for two turns rather than self-accepted, and the acceptance event quotes the exact proposal text so the sign-off is auditable against what was actually shown; (2) the process wording was changed from a CONDITION to an OBSERVATION, which is the transferable form of the defect — a verification step that describes a hoped-for state is satisfiable without observing anything; (3) scope was capped at one asset for a stated reason (no host can run the macOS binary), rather than writing an aspirational requirement that would be routinely bypassed. AVOIDABLE-ISSUE 1: I invoked the JVM workflow validator on a change that touches no workflow file, and it stalled for the full 10-minute timeout before being killed and swept. `keel check-engine` is the enforced instance gate for .engine changes (§5) and had already passed. NO NEW ITEM, reason stated: D0048 and D0132 already establish that validation-path tools must be kernel-free and that the kernel is opt-in, and CLAUDE.md §5 already scopes these validators to schema/workflow changes — the defect was my over-application of a documented rule, not a gap in it. AVOIDABLE-ISSUE 2: I mixed PowerShell's `&` call operator into a bash command, producing a syntax error — the OS/shell-adaptation class, THIRD instance in this sitting after two path-form errors. This crosses the threshold I set in sprint 263's retro, and examining it properly REVERSES that retro's conclusion: I wrote there that the class was not automatable because it lives in ad-hoc shell invocations rather than committed artifacts. That reasoning was wrong — it assumed a control must inspect artifacts, but the in-loop gates established by D0134 inspect TOOL CALLS, and a shell command is a tool call. A PreToolUse check can detect the two concrete forms observed (an MSYS `/c/...` or `/tmp/...` path handed to a Windows program; PowerShell-only syntax such as a leading `&` call operator or `$env:` inside a bash command) before the command runs. So the honest disposition is a gate after all, ADVISORY rather than blocking, because a heuristic that blocks every bash command is the issue076/issue081 dynamic that trains its actor to disable it. TRACKED as issue094 with resolver dcShellAdaptationGate, declared and prioritised rather than built in this sprint — its scope is a new hook event with false-positive risk and it deserves its own sprint, not a tail-end addition to a CHANGE sprint. Estimate 1 pt, delivered."; }
    part raiRetroGateR1 : TestResult { :>> id = "0d800021-0814-6021-9b3e-000000300021"; :>> outcome = VerdictKind::pass; :>> judgedAgainst = "95ec70e"; :>> judgedAt = "2026-08-14"; :>> judgedBy = "claudeOpus5"; }
}
