// ProjectDeliveryS553 — Sprint 553: STPA on keel itself becomes a process with the computed control structure as its re-run trigger - and its first run finds three control gaps. EXECUTE. 5 pts.
package ProjectDeliveryS553 {
    private import EngineElement::*;
    private import EngineWork::*;
    private import EngineVerification::*;
    private import EngineRelationships::*;

    #CharteredBy dependency from stpaSelfStory to d0313;

    part stpaSelfStory : Story {
        :>> id = "9868953e-5271-4984-89b2-e8a234cbba7a";
        :>> title = "Sprint 553: STPA on keel itself becomes a process with the computed control structure as its re-run trigger - and its first run finds three control gaps (5 pts)";
        :>> createdAt = "2026-09-05"; :>> createdBy = "claudeOpus5"; :>> kind = WorkKind::code; :>> priority = WorkPriority::p0; :>> owner = "claudeOpus5"; :>> estimatedPoints = 5;
    }

    action def DeliveryRunS553 {
        action storyStpaSelf;
        verification storyStpaSelfDoD : Test { :>> id = "8aad54f8-e655-4fc2-92d4-f4a07de16b64"; :>> method = VerificationMethod::test; :>> procedureText = "DELIVERED BACKLOG ITEMS: dcStpaProcessForKeel (D0313). DONE: the process stpaSelf (.engine/processes/stpa-self.sysml, five steps with successions), the stpa-self skill and registry, the first run in .tracking/architecture/engine-ucas.sysml - cmdRecord, cmdLand and cmdAppendResult walked through all four UCA types, nine UnsafeControlActions each edged to a hazard, nine ControllerConstraints each edged to a control (gAcceptanceBindsToText, ctlPrePushBehind, gConfirmationAuthenticity, gAttestationAuthority) or to an Issue naming the gap (issue373 new, issue374 new, issue375 new, issue342, issue360), the run record stpaRun1 with its ANALYSED list and a pass at HEAD - and guard 62 stpa-currency (warning-tier) that names every computed action no run has analysed: 39 of 42 today."; }
        // RAN: same suite receipt: 492/0 exit 0; keel gate . at commit
        part storyStpaSelfDoDR1 : TestResult { :>> id = "30eac44c-97c5-4e4f-81b1-7b6e3bb76751"; :>> outcome = VerdictKind::pass; :>> judgedAgainst = "494d293340d569d911ff8a3ff7b07abe9da29526"; :>> judgedAt = "2026-09-05"; :>> judgedBy = "claudeOpus5"; }
    }

    verification stpaSelfRefineGate : Test { :>> id = "61fc962b-c1d3-4300-a048-1c112bea8af7"; :>> title = "Sprint 553 refine gate (DoR)"; :>> createdAt = "2026-09-05"; :>> createdBy = "claudeOpus5"; :>> method = VerificationMethod::inspect; :>> procedureText = "READY: the frame existed (EL/EHZ1-9, D0284's computed structure, D0285's diagram) and the human had named the process in the same breath as the verification revamp (st065). The one design question was the trigger: the DoD said the view diffs itself against its last run, and the honest computable form of that is the ANALYSED name list - a name the structure grew that no run walked. The union over runs counts, not the latest run, because runs accumulate like test results."; }
    verification stpaSelfStandupGate : Test { :>> id = "ba4d906d-898b-4f22-be4c-2fca29b8cc1f"; :>> title = "Sprint 553 standup gate"; :>> createdAt = "2026-09-05"; :>> createdBy = "claudeOpus5"; :>> method = VerificationMethod::inspect; :>> procedureText = "THREE CHOICES. (1) Warning-tier, not blocking: an unanalysed action is queued work, not dishonest state (D0098). (2) Local structure only: the remote's branch-protection row needs gh, and a commit gate must not need the network - gather was split into gather_local and the remote row, and the guard reads the local list, so remoteRefusesRewrite is never asked for. (3) The three actions the DoD named - auto-accept, record-result, commit-land - are cmdRecord, cmdAppendResult and cmdLand in the computed vocabulary; the run walks those and records considered-safe types in the run text so the reader can tell considered from not-considered."; }
    verification stpaSelfImplementGate : Test { :>> id = "09a32157-b188-4df5-b752-fbe01920fb90"; :>> title = "Sprint 553 implement gate"; :>> createdAt = "2026-09-05"; :>> createdBy = "claudeOpus5"; :>> method = VerificationMethod::test; :>> procedureText = "RAN: keel validate . clean (631 files); keel check-engine . clean; keel guard . - stpa-currency PASS with one warning naming the 39 unanalysed actions, priority-inversion clean after dcForkShapeIsDetected was ranked above the Medium work (D0311), claude-surface-drift green after sync-claude picked up the new skill; the Rust suite in the background to completion (receipt on the DoD result). The run's three new Issues: issue373 a fork without OPTION markers auto-accepts (High, resolver dcForkShapeIsDetected), issue374 a receipt proves a sentence was typed not that a run happened - it happened here on 2026-09-04 (High, resolver dcExternalFactGate), issue375 a DoD pass is judged against the commit before the work lands (Medium, resolver dcResultBindsToItsLandingCommit, new)."; }
    verification stpaSelfReviewGate : Test { :>> id = "806d01ff-1954-496a-bff2-13bb4db64e3c"; :>> title = "Sprint 553 review gate — three passes per D0172"; :>> createdAt = "2026-09-05"; :>> createdBy = "claudeOpus5"; :>> method = VerificationMethod::inspect; :>> procedureText = "THREE PASSES. (1) IS THE FIRST RUN HONEST ABOUT ITS COVERAGE: yes - the run record names the three actions walked, the considered-safe types, and says 39 remain; the guard repeats that number on every commit until runs cover them. (2) DOES A CONSTRAINT BOUND TO AN ISSUE COUNT AS A CONTROL: no, and the record says so - it is the D0254 third class made visible, a gap with a resolver, not a control; the controls view is unchanged. (3) THE RESIDUAL: a changed body behind an unchanged action name is not a trigger; stated in the guard doc, the Decision and the process text rather than claimed away."; }
    verification stpaSelfCloseOutGate : Test { :>> id = "1c2fbbcc-d930-4b64-8adb-b9d6ee17de6d"; :>> title = "Sprint 553 closeOut gate (autonomous, D0049)"; :>> createdAt = "2026-09-05"; :>> createdBy = "claudeOpus5"; :>> method = VerificationMethod::inspect; :>> procedureText = "CLOSED. D0313 accepted under standing consent; GUARD_NAMES 62; three Issues triaged with resolvers; the frontier gained dcResultBindsToItsLandingCommit."; }
    verification stpaSelfRetroGate : Test { :>> id = "74ffab99-a364-4963-978f-ab3566036971"; :>> title = "Sprint 553 retro gate (autonomous, D0049)"; :>> createdAt = "2026-09-05"; :>> createdBy = "claudeOpus5"; :>> method = VerificationMethod::analyze; :>> procedureText = "no new item - already tracked: issue374 is the receipt-as-testimony gap the process was asked to find and it is bound to dcExternalFactGate, with the authority model itself left to the fork D0312; issue375's resolver dcResultBindsToItsLandingCommit is on the frontier. The lesson the run itself teaches: the first three actions analysed produced three untracked gaps in an hour, which is the argument for the stpa-currency warning staying visible rather than being read past."; }
}
