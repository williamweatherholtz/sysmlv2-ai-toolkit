// ProjectDeliveryS451 — Sprint 451: keel init stops shipping this project's adoption declaration and exchange identities to every new project (issue243). EXECUTE. 1 pts.
package ProjectDeliveryS451 {
    private import EngineElement::*;
    private import EngineWork::*;
    private import EngineVerification::*;
    private import EngineRelationships::*;

    #CharteredBy dependency from initContractResetStory to d0209;

    part initContractResetStory : Story {
        :>> id = "5dd1cf1f-5d52-4c67-80b7-7c2eaffa0b43";
        :>> title = "Sprint 451: a new project no longer inherits someone else's choices (1 pts)";
        :>> createdAt = "2026-08-24"; :>> createdBy = "claudeFable5"; :>> kind = WorkKind::code; :>> priority = WorkPriority::p0; :>> owner = "claudeFable5"; :>> estimatedPoints = 1;
    }

    action def DeliveryRunS451 {
        action storyInitContractReset;
        verification storyInitContractResetDoD : Test { :>> id = "e3f43054-4c80-4638-bbed-e410932efc90"; :>> method = VerificationMethod::test; :>> procedureText = "DELIVERED: dcInitContractReset (resolves issue243, MEDIUM). THE DEFECT, found by the panel's ROI lens and confirmed by diff: keel init scaffolds the embedded .engine verbatim, so a freshly inited tree's .engine/contracts/activation.toml was BYTE-IDENTICAL to the self-build's - 11 named active processes plus all 32 viewpoints - and `keel activation` in that tree reported 'declared manifest: yes' for a declaration the project never made. That directly falsifies CLAUDE.md's own adoption guarantee, that an absent file or section means everything is active so a project that never adopted a control has not violated it: the file was not absent, it was another project's. The new tree also inherited unit-ids.toml, i.e. the self-build's EXCHANGE IDENTITIES for units it never exported, so an `import --update` could match against a lineage that is not its own. This was the human's question 3 answered worse than 'no onboarding': not merely un-guided, but pre-decided by someone else. THE FIX, reusing the shape init already had for deliverable-manifest.txt rather than inventing a mechanism: is_instance_contract() names the three contracts that are instance data rather than engine definition (activation.toml, unit-ids.toml, installed-units.toml), and starter_for() resets them - activation.toml becomes a fully COMMENTED template, so the honest default is what a fresh project HAS while the file still shows how to declare a subset, and the id registries start genuinely empty because an identity is minted on first export and never inherited. VERIFIED with a freshness-checked binary: a fresh init now reports 'declared manifest: no - everything present is active', carries zero inherited unit ids, and its activation.toml is no longer identical to this repo's; crucially it STILL passes its own validate + guard + check-engine, which is the issue090 lesson (a fix must not fail every downstream project on day one). A regression test pins all four properties: instance contracts are reset, engine definition is shipped verbatim, the activation starter contains no live declaration line, and no unit id is inherited."; }
        part storyInitContractResetDoDR1 : TestResult { :>> id = "0f4bde6a-933f-4b0e-8b4d-614133ac286e"; :>> outcome = VerdictKind::pass; :>> judgedAgainst = "7b7f7791c962e895238c3ab67023e1aa324be452"; :>> judgedAt = "2026-08-24"; :>> judgedBy = "claudeFable5"; }
    }

    verification initContractResetRefineGate : Test { :>> id = "2451c182-d358-487a-b581-0804ddbcf489"; :>> title = "Sprint 451 refine gate (DoR)"; :>> createdAt = "2026-08-24"; :>> createdBy = "claudeFable5"; :>> method = VerificationMethod::inspect; :>> procedureText = "DoR. Resolves issue243 (MEDIUM by severity, but the panel's ROI lens ranked it FIRST for day-one value because it is a defect in the product every new project meets, not in the self-build). Scope: reset the three instance contracts at init and pin it. 1 point."; }
    part initContractResetRefineGateR1 : TestResult { :>> id = "790455d0-7614-456c-b00c-e0b8d8025740"; :>> outcome = VerdictKind::pass; :>> judgedAgainst = "7b7f7791c962e895238c3ab67023e1aa324be452"; :>> judgedAt = "2026-08-24"; :>> judgedBy = "claudeFable5"; }
    verification initContractResetStandupGate : Test { :>> id = "92375838-c48d-4ccf-8b15-d04ee1c74dba"; :>> title = "Sprint 451 standup gate"; :>> createdAt = "2026-08-24"; :>> createdBy = "claudeFable5"; :>> method = VerificationMethod::inspect; :>> procedureText = "Approach: extend the special case init already uses for deliverable-manifest.txt rather than adding a mechanism - one predicate naming instance data, one starter provider. Make the activation starter FULLY COMMENTED so the default is genuinely absent-section semantics; a template that is live is a declaration. main.rs is off the frozen enforcement surface and this restores documented behaviour rather than changing policy, so no marked Decision is required. No blockers."; }
    part initContractResetStandupGateR1 : TestResult { :>> id = "cab80fa3-735a-4220-84ee-188e221c7377"; :>> outcome = VerdictKind::pass; :>> judgedAgainst = "7b7f7791c962e895238c3ab67023e1aa324be452"; :>> judgedAt = "2026-08-24"; :>> judgedBy = "claudeFable5"; }
    verification initContractResetImplementGate : Test { :>> id = "fe1dc2f4-ea8d-483e-9f11-f3e32f8d23cd"; :>> title = "Sprint 451 implement gate"; :>> createdAt = "2026-08-24"; :>> createdBy = "claudeFable5"; :>> method = VerificationMethod::test; :>> procedureText = "Verified by running the freshness-checked binary against a throwaway init: activation reports 'declared manifest: no - everything present is active'; unit-ids.toml has zero entries; diff against this repo's activation.toml now differs. The fresh tree's own gates pass (validate 1 file clean, guard ALL PASS, check-engine clean). cargo test --bin keel init_resets -> 1 passed; cargo clippy --workspace --all-targets -D warnings clean after two escaping fixes."; }
    part initContractResetImplementGateR1 : TestResult { :>> id = "276eb74a-edee-4d40-a84f-01329dabece5"; :>> outcome = VerdictKind::pass; :>> judgedAgainst = "7b7f7791c962e895238c3ab67023e1aa324be452"; :>> judgedAt = "2026-08-24"; :>> judgedBy = "claudeFable5"; }
    verification initContractResetReviewGate : Test { :>> id = "c415fc56-1237-4cb3-a577-32c2e3a2c254"; :>> title = "Sprint 451 review gate — three passes per D0172"; :>> createdAt = "2026-08-24"; :>> createdBy = "claudeFable5"; :>> method = VerificationMethod::inspect; :>> procedureText = "PASS 1, CLAIMS: the fresh-tree activation line, the zero id count, the diff result and the fresh-tree gate results are quoted read-backs. PASS 2, BOUNDARY: (i) only the three named contracts are reset - process-enforcement.toml is engine DEFINITION and is deliberately still shipped verbatim, which the test pins in both directions; (ii) existing projects are untouched, so a downstream tree that already inherited this repo's activation.toml keeps it until it chooses otherwise - the fix is forward-only, which is correct because rewriting a project's declared adoption without being asked would be the same class of defect in reverse; (iii) the fresh tree still ships all 23 processes and all 48 guards ACTIVE, which is the honest default and NOT the same thing as guided selection - question 3's guided-choice half remains unbuilt and is not claimed here. PASS 3, OWN DIFF: I fought Rust backslash escaping through two failed heredoc passes before using literal edits, which is the recurring shell-escaping class from this session's own retros; the durable habit is to use the editing tool for syntax-bearing content rather than nested heredocs, and I broke it again under time pressure. WHAT A REVIEWER SHOULD ATTACK: whether resetting activation.toml to a commented template is better than OMITTING the file entirely - omission is the purest expression of the absent-means-active default, and the only argument for keeping a commented file is discoverability of the syntax."; }
    part initContractResetReviewGateR1 : TestResult { :>> id = "8b7d9bb8-062f-42a1-9701-c41b057508a5"; :>> outcome = VerdictKind::pass; :>> judgedAgainst = "7b7f7791c962e895238c3ab67023e1aa324be452"; :>> judgedAt = "2026-08-24"; :>> judgedBy = "claudeFable5"; }
    verification initContractResetCloseOutGate : Test { :>> id = "6341b39a-b381-4ff7-849a-b1346e9757be"; :>> title = "Sprint 451 closeOut gate (autonomous, D0049)"; :>> createdAt = "2026-08-24"; :>> createdBy = "claudeFable5"; :>> method = VerificationMethod::inspect; :>> procedureText = "Autonomous closeOut (D0049). issue243 resolved and pinned; the fresh-tree gates verified green so no downstream project is broken by the change; validate + all 48 guards + check-engine + rules green. Two panel findings remain: issue245 and issue246."; }
    part initContractResetCloseOutGateR1 : TestResult { :>> id = "af840634-dcc1-48a3-9dfc-af4c23922ae4"; :>> outcome = VerdictKind::pass; :>> judgedAgainst = "7b7f7791c962e895238c3ab67023e1aa324be452"; :>> judgedAt = "2026-08-24"; :>> judgedBy = "claudeFable5"; }
    verification initContractResetRetroGate : Test { :>> id = "fae0428a-3107-4ddb-9837-559fd0ee0322"; :>> title = "Sprint 451 retro gate (autonomous, D0049)"; :>> createdAt = "2026-08-24"; :>> createdBy = "claudeFable5"; :>> method = VerificationMethod::analyze; :>> procedureText = "Autonomous retro (D0049). AVOIDABLE-ISSUE SCAN under rcRecurrence: the nested-heredoc escaping class recurred - two passes were lost to Rust character literals mangled by shell/Python quoting before I switched to literal edits, which is exactly the rule this session had already recorded ('use the editing tool for syntax-bearing content'). The recurrence cause is that a heredoc is faster to reach for when adding a multi-line helper; the durable form is that ANY content containing backslashes or quotes goes through the editor, without exception. WELL: the fix reused an existing special-case shape rather than adding machinery, and the check that mattered most - does a fresh project still pass its own gates - was run before commit rather than discovered downstream, which is the issue089/issue090 lesson finally applied in advance. Estimate 1 pt, delivered 1."; }
    part initContractResetRetroGateR1 : TestResult { :>> id = "fe1a7d1f-9184-45a1-a122-92b1952a8940"; :>> outcome = VerdictKind::pass; :>> judgedAgainst = "7b7f7791c962e895238c3ab67023e1aa324be452"; :>> judgedAt = "2026-08-24"; :>> judgedBy = "claudeFable5"; }
}
