// ProjectDeliveryS375 — Sprint 375: the third latch failure, diagnosed from the served runtime rather
// than the contract's prose. data-id is the sync key. EXECUTE. 3 pts.
package ProjectDeliveryS375 {
    private import EngineElement::*;
    private import EngineWork::*;
    private import EngineVerification::*;
    private import EngineRelationships::*;

    #CharteredBy dependency from syncAddressableStory to d0171;

    part syncAddressableStory : Story {
        :>> id = "0d800720-0814-6720-9b3e-000000300720";
        :>> title = "Sprint 375: deck v4 — every synced element carries the runtime's data-id sync key (3 pts)";
        :>> createdAt = "2026-08-21"; :>> createdBy = "claudeOpus5"; :>> kind = WorkKind::code; :>> priority = WorkPriority::p0; :>> owner = "claudeOpus5"; :>> estimatedPoints = 3;
    }

    action def DeliveryRunS375 {
        action storySyncAddressable;
        verification storySyncAddressableDoD : Test { :>> id = "0d800721-0814-6721-9b3e-000000300721"; :>> method = VerificationMethod::test; :>> procedureText = "DELIVERED BACKLOG ITEMS: dcDeckSyncAddressable declared; addresses issue190 under D0171. THE METHOD CHANGED AND THAT IS THE DELIVERABLE AS MUCH AS THE FIX: rounds one and two were diagnosed from the CONTRACT'S PROSE and verified against the LOCAL FILE - both fixed real defects, neither was sufficient, and both shipped a working-buttons claim. Round three FETCHED THE PUBLISHED ARTIFACT, which returns the frame runtime preamble itself, and read the mechanism: synced elements are addressed by [data-id=...] with an allowlist of data-*/aria-*/class/hidden/value/checked. The deck's cards carried data-uid - the canvas template said data-id and the generator renamed it - so NO tap was addressable, recordable, or persistent. THE SAME FETCH FOUND TWO MORE DEFECTS: the deck v3 stamp existed only in a JS variable and never rendered (I verified presence-in-FILE and told them to look for it on-SCREEN), and the script-ok marker escape was mangled to b7. DECK v4: every card and note input carries data-id; script writes ZERO text into the synced region under any path (pill, count and copy label all render via CSS from attributes); the version is VISIBLE in the sub-line. Emitted-HTML audit: 49 of 49 cards with data-id, 49 note inputs, zero textContent writes outside the artifact-local panel, marker last. The DEMO stays theirs. validate 407 clean; check-engine clean; 38 guards ALL PASS."; }
        part storySyncAddressableDoDR1 : TestResult { :>> id = "0d800722-0814-6722-9b3e-000000300722"; :>> outcome = VerdictKind::pass; :>> judgedAgainst = "7b2fd2f"; :>> judgedAt = "2026-08-21"; :>> judgedBy = "claudeOpus5"; }
    }

    verification saRefineGate : Test { :>> id = "0d800723-0814-6723-9b3e-000000300723"; :>> title = "Sprint 375 refine gate (DoR)"; :>> createdAt = "2026-08-21"; :>> createdBy = "claudeOpus5"; :>> method = VerificationMethod::inspect; :>> procedureText = "DoR. Their words carried the diagnostic: 'they don't latch. they indicate state' - the tap registers and the state does not HOLD, which rules the click path in and persistence out. 'Fix methodically' was read as an instruction about METHOD: stop deriving from the contract's text, obtain evidence. The cheapest evidence was fetching what is actually served, and it settled in one read what two contract-derived fixes had not. estimatedPoints=3."; }
    part saRefineGateR1 : TestResult { :>> id = "0d800724-0814-6724-9b3e-000000300724"; :>> outcome = VerdictKind::pass; :>> judgedAgainst = "7b2fd2f"; :>> judgedAt = "2026-08-21"; :>> judgedBy = "claudeOpus5"; }

    verification saStandupGate : Test { :>> id = "0d800725-0814-6725-9b3e-000000300725"; :>> title = "Sprint 375 standup gate"; :>> createdAt = "2026-08-21"; :>> createdBy = "claudeOpus5"; :>> method = VerificationMethod::inspect; :>> procedureText = "Approach: read the served page FIRST, then fix everything it shows at once - the addressing key, the never-rendered version stamp, the mangled escape - rather than the one defect the report named. The stamp finding is the one that stings: I had told them twice to look for a marker that did not render, so their 'still doesn't work' was partly unfalsifiable BY CONSTRUCTION, my construction. No blockers."; }
    part saStandupGateR1 : TestResult { :>> id = "0d800726-0814-6726-9b3e-000000300726"; :>> outcome = VerdictKind::pass; :>> judgedAgainst = "7b2fd2f"; :>> judgedAt = "2026-08-21"; :>> judgedBy = "claudeOpus5"; }

    verification saImplementGate : Test { :>> id = "0d800727-0814-6727-9b3e-000000300727"; :>> title = "Sprint 375 implement gate"; :>> createdAt = "2026-08-21"; :>> createdBy = "claudeOpus5"; :>> method = VerificationMethod::test; :>> procedureText = "THE RUNTIME'S OWN VALIDATOR IS THE SPEC. The served preamble contains the patch function verbatim: querySelector on [data-id=...], attribute names validated against data-*/aria-*/class/hidden/value/checked, text patches only on elements that pass a leaf check. Everything the deck does now fits inside exactly that envelope: one data-* attribute set per tap, on an element with data-id; input values on inputs with data-id; all rendering via CSS from those attributes; per-viewer chrome on data-local-* and the artifact-local panel. THE COPY-BUTTON LABEL was the last text write and runs synchronously in a gesture - defensible under rule 1, converted anyway, because one rule with no exceptions survives me and a rule with a defensible carve-out gets carved. TWO SHELL-MANGLING RELAPSES while writing the patch (a backslash-n eaten editing the patch file through python -c, fixed by using the Edit tool): the class dcAuthorViaWriteTool tracks, occurrence seven, and the item's rule tightens to cover EDITING patch files, not only authoring content."; }
    part saImplementGateR1 : TestResult { :>> id = "0d800728-0814-6728-9b3e-000000300728"; :>> outcome = VerdictKind::pass; :>> judgedAgainst = "7b2fd2f"; :>> judgedAt = "2026-08-21"; :>> judgedBy = "claudeOpus5"; }

    verification saReviewGate : Test { :>> id = "0d800729-0814-6729-9b3e-000000300729"; :>> title = "Sprint 375 review gate — three passes per D0172"; :>> createdAt = "2026-08-21"; :>> createdBy = "claudeOpus5"; :>> method = VerificationMethod::inspect; :>> procedureText = "PASS 1, CLAIMS vs emitted output: 49/49 cards carry data-id, 49 note inputs carry data-id, zero textContent assignments outside the artifact-local panel, version string in rendered text, marker last - counted, not asserted. PASS 2, BOUNDARY: the audit's own regex excludes the dbg panel's own line builder explicitly, so it cannot pass by matching nothing; the served-page check is the new boundary and it was DONE for the defect but not yet re-done for v4 (the fetch cache is 15 minutes; the v4 publish is newer than the cache window allows me to confirm from here) - stated as pass 2's limit. PASS 3, THE SPRINT'S OWN DIFF: my first patch application FAILED on an assertion because the sub-line pattern lacked its trailing newline - the assert did its job and nothing was half-applied, which is the asserted-replace discipline working; and my python -c edit of the patch file mangled a backslash, caught immediately because the very next run threw a SyntaxError at the mangled line. WHAT A REVIEWER SHOULD ATTACK: the data-id hypothesis is INFERRED from the runtime's inbound patch validator - the outbound capture code lives in a lazily-loaded module the fetch does not return, so the inference could be wrong in the same way the contract-derived fixes were. It is the strongest evidence yet (the template's own convention agrees), and if v4 still fails, the next probe is a minimal bisection page publishing four mechanisms side by side."; }
    part saReviewGateR1 : TestResult { :>> id = "0d80072a-0814-672a-9b3e-00000030072a"; :>> outcome = VerdictKind::pass; :>> judgedAgainst = "7b2fd2f"; :>> judgedAt = "2026-08-21"; :>> judgedBy = "claudeOpus5"; }

    verification saCloseOutGate : Test { :>> id = "0d80072b-0814-672b-9b3e-00000030072b"; :>> title = "Sprint 375 closeOut gate (autonomous, D0049)"; :>> createdAt = "2026-08-21"; :>> createdBy = "claudeOpus5"; :>> method = VerificationMethod::inspect; :>> procedureText = "Autonomous closeOut (D0049). issue190 recorded; deck v4 republished to the same URL; the skill gains rules 7 (data-id is the sync key; no text writes, no exceptions) and 8 (verify the SERVED page for anything the human is told to see; read the runtime preamble before theorizing). The demo confirmation remains theirs - I have claimed these buttons work twice and will not a third time. validate 407 clean; check-engine clean; 38 guards ALL PASS."; }
    part saCloseOutGateR1 : TestResult { :>> id = "0d80072c-0814-672c-9b3e-00000030072c"; :>> outcome = VerdictKind::pass; :>> judgedAgainst = "7b2fd2f"; :>> judgedAt = "2026-08-21"; :>> judgedBy = "claudeOpus5"; }

    verification saRetroGate : Test { :>> id = "0d80072d-0814-672d-9b3e-00000030072d"; :>> title = "Sprint 375 retro gate (autonomous, D0049)"; :>> createdAt = "2026-08-21"; :>> createdBy = "claudeOpus5"; :>> method = VerificationMethod::analyze; :>> procedureText = "Autonomous retro (D0049). AVOIDABLE-ISSUE SCAN under rcRecurrence: (1) verifying against the FILE what the human experiences on the SCREEN is occurrence TWO of the same shape (v3's stamp check, and round 1's eight-property audit that missed the async class entirely) - by the second-occurrence rule it becomes part of dcDeckSyncAddressable's DoD, which now requires the served-page check for any user-visible claim; (2) shell-mangling occurrence SEVEN, folded into dcAuthorViaWriteTool whose rule now covers editing patch files through the shell, not just authoring content. WELL: (1) the diagnosis method changed after two failures instead of after three - fetching the served page cost one call and outperformed both contract readings; (2) the review gate states plainly that the data-id inference could still be wrong and names the next probe, so a fourth failure starts from a plan rather than a shrug; (3) all three served-page defects were fixed in one pass rather than the one the report named; (4) the DoD stays open on their demo - two false working-buttons claims is the cap. Estimate 3 pts, delivered."; }
    part saRetroGateR1 : TestResult { :>> id = "0d80072e-0814-672e-9b3e-00000030072e"; :>> outcome = VerdictKind::pass; :>> judgedAgainst = "7b2fd2f"; :>> judgedAt = "2026-08-21"; :>> judgedBy = "claudeOpus5"; }
}
