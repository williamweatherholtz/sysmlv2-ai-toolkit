// ProjectDeliveryS383 — Sprint 383: keel decision-follow-through - the promise-to-work chain becomes a computed view. EXECUTE. 3 pts.
package ProjectDeliveryS383 {
    private import EngineElement::*;
    private import EngineWork::*;
    private import EngineVerification::*;
    private import EngineRelationships::*;

    #CharteredBy dependency from followThroughViewStory to d0173;

    part followThroughViewStory : Story {
        :>> id = "37cefa0a-6d80-4637-8682-9a12def136e0";
        :>> title = "Sprint 383: decision-follow-through - the gap between accepted and built is computed, never asserted (3 pts)";
        :>> createdAt = "2026-08-21"; :>> createdBy = "claudeFable5"; :>> kind = WorkKind::code; :>> priority = WorkPriority::p0; :>> owner = "claudeFable5"; :>> estimatedPoints = 3;
    }

    action def DeliveryRunS383 {
        action storyFollowThroughView;
        verification storyFollowThroughViewDoD : Test { :>> id = "f6de8cbe-8646-412d-8b50-44e34bf2781d"; :>> method = VerificationMethod::test; :>> procedureText = "DELIVERED BACKLOG ITEMS: dcDecisionFollowThroughView. Their st015 made computable: `keel decision-follow-through [--table]` lists, for EVERY accepted Decision, the tracked items reaching it by typed edge (charteredby/derivedfrom/resolves/satisfy, deduped), each item's evidence state (latest {item}DoDR outcome, with the sprint-story convention as fallback: a Story's doneness is its file's story-DoD), and GAPS - accepted Decisions with zero downstream items. JSON is the authority; --table renders the same data; served at /api/computed/decision-follow-through through the existing cached binding table; advertised in the help catalogue. THE THREE ANCHORS, verified from the VIEW'S OUTPUT: d0173 shows its three chartered stories (firstPull, mintCommand, sprintScaffold) all pass; d0171 shows all seven deck-series stories pass; and the gap count - 64 of 168 accepted - RECONCILES EXACTLY with the number the hardening lens's own doc recorded by hand (64 with no chartered work), while the view's note states the two surfaces are complementary (the lens checks DECLARED artifact promises, this view checks edges). NOT A GATE, stated in the output: some gaps are legitimate; the enforcement question is dcDecisionScaffoldingGuard's proposed Decision, gated on their st014. 215 tests; clippy 0 (it caught the view exceeding the line budget - evidence logic extracted to helpers - and a doc split that left dispositions undocumented); 40 guards ALL PASS."; }
        part storyFollowThroughViewDoDR1 : TestResult { :>> id = "908325f6-d475-4b6e-83b4-65a8c48dabb4"; :>> outcome = VerdictKind::pass; :>> judgedAgainst = "245d2d3"; :>> judgedAt = "2026-08-21"; :>> judgedBy = "claudeOpus5"; }
    }

    verification followThroughViewRefineGate : Test { :>> id = "671dddbb-f0b3-48ce-97a1-59d5d9a9686a"; :>> title = "Sprint 383 refine gate (DoR)"; :>> createdAt = "2026-08-21"; :>> createdBy = "claudeFable5"; :>> method = VerificationMethod::inspect; :>> procedureText = "DoR. Third item on the ready frontier (D0052), fully specified by dcDecisionFollowThroughViewDoD including its three verification anchors. estimatedPoints=3."; }
    part followThroughViewRefineGateR1 : TestResult { :>> id = "7f57af36-2799-4eb5-8ff7-25eebe734912"; :>> outcome = VerdictKind::pass; :>> judgedAgainst = "245d2d3"; :>> judgedAt = "2026-08-21"; :>> judgedBy = "claudeOpus5"; }
    verification followThroughViewStandupGate : Test { :>> id = "1c6b0146-b910-4dbc-a781-6b5df1611451"; :>> title = "Sprint 383 standup gate"; :>> createdAt = "2026-08-21"; :>> createdBy = "claudeFable5"; :>> method = VerificationMethod::inspect; :>> procedureText = "Approach: compute from the MODEL'S EDGES, not from a new registry - the four inbound kinds are the ones the schema already declares and the corpus already uses; evidence reuses the DoDR result convention rather than inventing a status field (invariant 6: anything naming a verdict is computed). The serve binding rides the existing computed-view cache table, so D0167 staleness semantics apply unchanged. No blockers."; }
    part followThroughViewStandupGateR1 : TestResult { :>> id = "202aafe8-904c-492a-a772-3ca5e5a2cc77"; :>> outcome = VerdictKind::pass; :>> judgedAgainst = "245d2d3"; :>> judgedAt = "2026-08-21"; :>> judgedBy = "claudeOpus5"; }
    verification followThroughViewImplementGate : Test { :>> id = "c0162786-461c-4a99-8004-3bdf84180a5c"; :>> title = "Sprint 383 implement gate"; :>> createdAt = "2026-08-21"; :>> createdBy = "claudeFable5"; :>> method = VerificationMethod::test; :>> procedureText = "Every claim from a run: the three anchors read back from the emitted JSON (d0173 x3 pass, d0171 x7 pass, 64/168 gaps reconciling with the lens doc's hand count); the --table path exercised live - and its first run FAILED HONESTLY (unknown flag) because root_arg treats unlisted flags as refusable, which is issue179's convention doing its job against my own new command; fixed by declaring the flag. Clippy caught two real defects: the function over the line budget (evidence extracted to dft_latest_result/dft_evidence) and my insertion splitting dispositions from its doc comment."; }
    part followThroughViewImplementGateR1 : TestResult { :>> id = "eb09ce62-9f4c-4e47-b083-42510ef6f393"; :>> outcome = VerdictKind::pass; :>> judgedAgainst = "245d2d3"; :>> judgedAt = "2026-08-21"; :>> judgedBy = "claudeOpus5"; }
    verification followThroughViewReviewGate : Test { :>> id = "95f9b98c-7a47-45ed-b53f-b3a9ed53ae84"; :>> title = "Sprint 383 review gate — three passes per D0172"; :>> createdAt = "2026-08-21"; :>> createdBy = "claudeFable5"; :>> method = VerificationMethod::inspect; :>> procedureText = "PASS 1, CLAIMS vs computed: all numbers in this record read from the view's emitted JSON, none from the source. PASS 2, BOUNDARY: a Decision with edges but NO evidence renders as no-evidence rather than being dropped; duplicate (item, kind) edges dedup; accepted-status matching is suffix-based, consistent with the codebase's enum-path convention. PASS 3, OWN DIFF: the DoD's anchor prediction said sprints 379/380 under d0173 - the view showed 379 is chartered by d0171, and the record states the correction rather than adjusting the claim to fit (the story list above is what the view actually shows). WHAT A REVIEWER SHOULD ATTACK: the story-evidence fallback assumes one story per sprint file; a two-story file would take the first story-DoD stem found - present corpus has none, and the ceremony convention is one story per sprint."; }
    part followThroughViewReviewGateR1 : TestResult { :>> id = "6c22934d-0d95-42b7-887c-222d918d07af"; :>> outcome = VerdictKind::pass; :>> judgedAgainst = "245d2d3"; :>> judgedAt = "2026-08-21"; :>> judgedBy = "claudeOpus5"; }
    verification followThroughViewCloseOutGate : Test { :>> id = "ee751488-5c57-4661-940b-6bb2693a65d0"; :>> title = "Sprint 383 closeOut gate (autonomous, D0049)"; :>> createdAt = "2026-08-21"; :>> createdBy = "claudeFable5"; :>> method = VerificationMethod::inspect; :>> procedureText = "Autonomous closeOut (D0049). dcDecisionFollowThroughView's DoD result flipped to pass at the judging HEAD; view + CLI + serve binding + catalogue line landed together; the record you are reading was scaffolded by keel new sprint and judged through append-gate-result. validate clean; 40 guards ALL PASS; 215 tests; clippy 0."; }
    part followThroughViewCloseOutGateR1 : TestResult { :>> id = "b9c03541-b89b-4fdd-a7b2-8b4a43094c70"; :>> outcome = VerdictKind::pass; :>> judgedAgainst = "245d2d3"; :>> judgedAt = "2026-08-21"; :>> judgedBy = "claudeOpus5"; }
    verification followThroughViewRetroGate : Test { :>> id = "67c0e940-afab-4dd8-b004-473091fdd7c8"; :>> title = "Sprint 383 retro gate (autonomous, D0049)"; :>> createdAt = "2026-08-21"; :>> createdBy = "claudeFable5"; :>> method = VerificationMethod::analyze; :>> procedureText = "Autonomous retro (D0049). AVOIDABLE-ISSUE SCAN under rcRecurrence: my own new command refused its own documented flag on first run - the root_arg contract (unlisted flags refuse) was applied by the machine against its author, first occurrence of self-inflicted-refusal, no item: the control worked and the cost was one local run. WELL: (1) clippy caught a documentation-severing edit that would have silently stripped dispositions' contract docs - the lint tier is part of the doc-sync control surface; (2) the anchor discipline (predict, then read back) caught my own wrong prediction about which decision charters sprint 379, and the record keeps the correction visible; (3) the view closes the loop their note opened: the answer to is-there-no-scaffolding is now one command, and its first output already names the 64 decisions to triage when the guard Decision is signed. Estimate 3 pts, delivered."; }
    part followThroughViewRetroGateR1 : TestResult { :>> id = "32a573af-8d9a-48f3-bdf6-04d01f11e5dc"; :>> outcome = VerdictKind::pass; :>> judgedAgainst = "245d2d3"; :>> judgedAt = "2026-08-21"; :>> judgedBy = "claudeOpus5"; }
}
