// ProjectDeliveryS623 — Sprint 623: Sprint 623 makes the decision brief's facts script read a Decision's standing the way the engine does after D0398 (dcBriefFactsReadStandingFromTheEdge, issue420): status minus the Supersede edge, and a pending count the engine disagrees with is refused rather than published. EXECUTE. 1 pts.
package ProjectDeliveryS623 {
    private import EngineElement::*;
    private import EngineWork::*;
    private import EngineVerification::*;
    private import EngineRelationships::*;

    #CharteredBy dependency from briefFactsStandingStory to d0398;

    part briefFactsStandingStory : Story {
        :>> id = "815ddb08-baad-4881-b802-4830d53a5657";
        :>> title = "Sprint 623: Sprint 623 makes the decision brief's facts script read a Decision's standing the way the engine does after D0398 (dcBriefFactsReadStandingFromTheEdge, issue420): status minus the Supersede edge, and a pending count the engine disagrees with is refused rather than published (1 pts)";
        :>> createdAt = "2026-09-09"; :>> createdBy = "claudeOpus5"; :>> kind = WorkKind::code; :>> priority = WorkPriority::p0; :>> owner = "claudeOpus5"; :>> estimatedPoints = 1;
    }

    action def DeliveryRunS623 {
        action storyBriefFactsStanding;
        verification storyBriefFactsStandingDoD : Test { :>> id = "8ae96cab-37de-4414-8290-88270c3c5af2"; :>> method = VerificationMethod::test; :>> procedureText = "DELIVERED when scripts/exec_brief/facts.py computes the retired set from non-comment #Supersede lines and subtracts it from decisionsAccepted, decisionsProposed and the consent-scope census; the pre-D0398 census facts (decisionsStatusSuperseded, acceptedWithSupersedeEdge, supersededWithoutEdge, supersessionDisagreements) are replaced by decisionsRetired, supersedeEdges and supersedeClauseEdges; and decisionsProposed is emitted null with both numbers named whenever it differs from orient's pendingAcceptances. VERIFY on this tree: decisionsProposed 1 = pendingAcceptances 1, decisionsAccepted 389 (the governance card's count), decisionsRetired 7, supersedeClauseEdges 7, scopeDecisionsOpen 1, pendingAlreadyShipped 0."; }
        // RAN: python scripts/exec_brief/facts.py at 649b433: decisionsProposed 1 = pendingAcceptances 1, decisionsAccepted 389, decisionsRetired 7, supersedeClauseEdges 7, scopeDecisionsOpen 1, pendingAlreadyShipped 0; keel validate 708 clean
        part storyBriefFactsStandingDoDR1 : TestResult { :>> id = "129fdb7a-995c-4253-83fd-083a678a04e2"; :>> outcome = VerdictKind::pass; :>> judgedAgainst = "649b433"; :>> judgedAt = "2026-09-09"; :>> judgedBy = "claudeOpus5"; }
    }

    verification briefFactsStandingRefineGate : Test { :>> id = "5219e0c3-6fcc-4f42-ac8e-51977bc24740"; :>> title = "Sprint 623 refine gate (DoR)"; :>> createdAt = "2026-09-09"; :>> createdBy = "claudeOpus5"; :>> method = VerificationMethod::inspect; :>> procedureText = "READY because the defect was measured before any edit (facts.py at 649b433 read decisionsProposed 3 against pendingAcceptances 1, and listed d0353 as a proposed Decision whose code ships) and the fix is one reader gaining the rule the Rust readers gained in sprint 622. 1 pt: a script change, no schema, no engine code."; }
    part briefFactsStandingRefineGateR1 : TestResult { :>> id = "3adf935f-26ae-42f0-a065-010dd06ec5a7"; :>> outcome = VerdictKind::pass; :>> judgedAgainst = "649b433"; :>> judgedAt = "2026-09-09"; :>> judgedBy = "claudeOpus5"; }
    verification briefFactsStandingStandupGate : Test { :>> id = "7329045a-e921-497f-8a66-6ef634ca8d92"; :>> title = "Sprint 623 standup gate"; :>> createdAt = "2026-09-09"; :>> createdBy = "claudeOpus5"; :>> method = VerificationMethod::inspect; :>> procedureText = "Plan: (1) compute retired from #Supersede lines and subtract where standing is read; (2) replace the D0384 census block; (3) make the orient cross-check a refusal, not a note; (4) rerun facts.py and compare with the governance card and orient; (5) record issue420 with this task as resolver, stamp, gate."; }
    part briefFactsStandingStandupGateR1 : TestResult { :>> id = "e2b6b386-72bd-45ee-98b2-e1a751aa21aa"; :>> outcome = VerdictKind::pass; :>> judgedAgainst = "649b433"; :>> judgedAt = "2026-09-09"; :>> judgedBy = "claudeOpus5"; }
    verification briefFactsStandingImplementGate : Test { :>> id = "2f6e49ad-bd62-4ae2-b317-8e3d9aa3b605"; :>> title = "Sprint 623 implement gate"; :>> createdAt = "2026-09-09"; :>> createdBy = "claudeOpus5"; :>> method = VerificationMethod::test; :>> procedureText = "RAN 2026-09-09: facts_patch.py + facts_patch2.py + one textpatch replace on scripts/exec_brief/facts.py (all through scripts/textpatch.py, each anchor found once). facts.py rerun: decisionsProposed 1, pendingAcceptances 1, decisionsAccepted 389, decisionsRetired 7 (d0003 d0014 d0038 d0069 d0071 d0310 d0353), supersedeEdges 55, supersedeClauseEdges 7 (d0114 d0115 d0129 d0175 d0178 d0205 d0351 - a Decision's text quoting the grammar with X and Y is filtered by requiring a declared target), scopeDecisionsOpen 1 (d0376 rejected is decided, not open), pendingAlreadyShipped 0. keel validate 708 clean."; }
    // RAN: 2026-09-09 facts.py patched through textpatch (3 patches, each anchor once); rerun reads decisionsProposed 1 = pendingAcceptances 1, decisionsAccepted 389, decisionsRetired 7, supersedeClauseEdges 7, scopeDecisionsOpen 1; validate 708 clean
    part briefFactsStandingImplementGateR1 : TestResult { :>> id = "7c83c8cc-a7aa-4ce3-b287-4fb50329a23f"; :>> outcome = VerdictKind::pass; :>> judgedAgainst = "649b433"; :>> judgedAt = "2026-09-09"; :>> judgedBy = "claudeOpus5"; }
    verification briefFactsStandingReviewGate : Test { :>> id = "b9eaa076-71d9-44e4-9a03-708c93896500"; :>> title = "Sprint 623 review gate — three passes per D0172"; :>> createdAt = "2026-09-09"; :>> createdBy = "claudeOpus5"; :>> method = VerificationMethod::inspect; :>> procedureText = "Pass 1 (correctness): the retired set is the same predicate keel_cli::supersede_targets applies - non-comment #Supersede lines, target split on commas - so the script and the binary cannot disagree on WHICH Decisions are retired, only on whether the file was read; the accepted count now equals the governance card's 389. Pass 2 (honesty): nothing is backfilled; a retired Decision keeps its status and simply leaves the standing counts; the census facts that no longer describe anything were deleted, not tombstoned. Pass 3 (controls): the cross-check is a refusal - decisionsProposed becomes null naming both counts when the reader drifts from the engine again - which is what D0047 asks of a recurring class; the class is a Python reader of a field whose meaning changed, and the Rust guards cannot see it."; }
    part briefFactsStandingReviewGateR1 : TestResult { :>> id = "ad1ef2eb-f9d6-450d-9e71-854f56b91bb7"; :>> outcome = VerdictKind::pass; :>> judgedAgainst = "649b433"; :>> judgedAt = "2026-09-09"; :>> judgedBy = "claudeOpus5"; }
    verification briefFactsStandingCloseOutGate : Test { :>> id = "872f0e3a-1705-4bf1-a9af-4d1589a354b4"; :>> title = "Sprint 623 closeOut gate (autonomous, D0049)"; :>> createdAt = "2026-09-09"; :>> createdBy = "claudeOpus5"; :>> method = VerificationMethod::inspect; :>> procedureText = "Task done and stamped with the rerun as evidence; issue420 recorded with this task as resolver; no result line written by a script (D0301)."; }
    part briefFactsStandingCloseOutGateR1 : TestResult { :>> id = "75a5700d-4707-4e2c-bebb-c55a49854630"; :>> outcome = VerdictKind::pass; :>> judgedAgainst = "649b433"; :>> judgedAt = "2026-09-09"; :>> judgedBy = "claudeOpus5"; }
    verification briefFactsStandingRetroGate : Test { :>> id = "744301c3-f723-4ec5-8cd5-4ca79dd98528"; :>> title = "Sprint 623 retro gate (autonomous, D0049)"; :>> createdAt = "2026-09-09"; :>> createdBy = "claudeOpus5"; :>> method = VerificationMethod::analyze; :>> procedureText = "Retro held; avoidable-issue scan: the sprint 622 doc-sync grep was for the enum member that left (superseded) and the field readers in Rust; a reader that names the field by regex and never the member was invisible to it. Tracked as dcFieldReadersOutsideRustAreEnumerated (added to the backlog in this commit): a computed field-readers lens over scripts/, .engine/tools/ and .github/, and a warning guard when a schema definition changes without any listed reader in the same commit - the sweep for a meaning change becomes one command instead of a grep the author remembers. No other finding."; }
    part briefFactsStandingRetroGateR1 : TestResult { :>> id = "017788e7-90e3-4a9a-b827-5fb9e4d30007"; :>> outcome = VerdictKind::pass; :>> judgedAgainst = "649b433"; :>> judgedAt = "2026-09-09"; :>> judgedBy = "claudeOpus5"; }
}
