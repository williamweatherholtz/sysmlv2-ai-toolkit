// ProjectDeliveryS157 — Sprint 157: releaseWorkflow (D0093 deployment-readiness) — GitHub Releases of
// prebuilt keel binaries. .github/workflows/release.yml: on a v* tag, build keel natively per-OS
// (linux x86_64, macOS arm64, windows x86_64) and attach to a GitHub Release, so downstream gets a
// prebuilt binary with no Rust toolchain. EXECUTE. 2 pts. AUTONOMOUS (D0049). Prereq cargoReleaseMetadata done.
package ProjectDeliveryS157 {
    private import EngineElement::*;
    private import EngineWork::*;
    private import EngineVerification::*;
    private import EngineRelationships::*;

    #CharteredBy dependency from releaseWorkflowStory to d0093;

    part releaseWorkflowStory : Story {
        :>> id = "63940516-2c7d-4e8f-c157-51627384c001";
        :>> title = "Sprint 157: releaseWorkflow (2 pts) — v* tag builds win/mac/linux keel binaries -> GitHub Release";
        :>> createdAt = "2026-06-24"; :>> createdBy = "wweatherholtz"; :>> kind = WorkKind::code; :>> priority = WorkPriority::p2; :>> owner = "claudeOpus"; :>> estimatedPoints = 2;
    }

    action def DeliveryRunS157 {
        action storyReleaseWorkflow;
        verification storyReleaseWorkflowDoD : Test { :>> id = "63940516-2c7d-4e8f-c157-51627384c002"; :>> method = VerificationMethod::test; :>> procedureText = "Resolves releaseWorkflow (D0093 deployment-readiness, human-chosen channel = GitHub Releases of prebuilt binaries). DELIVERED: .github/workflows/release.yml — on a `v*` tag, a matrix builds keel natively per-OS (ubuntu/x86_64-unknown-linux-gnu, macos/aarch64-apple-darwin, windows/x86_64-pc-windows-msvc) via `cargo build --release --bin keel` (mirrors the proven ci.yml), stages the binary (keel-linux-x86_64 / keel-macos-aarch64 / keel-windows-x86_64.exe), and attaches it to a GitHub Release (softprops/action-gh-release@v2, generate_release_notes). contents:write permission; a workflow_dispatch trigger allows a build-only smoke (the publish step is gated `if startsWith(github.ref,'refs/tags/v')`, so a manual run builds without creating a release). Rust-only (no conda/kernel). VERIFIED LIVE: YAML parses well-formed (3 targets, push-tag + workflow_dispatch, publish gated on tag refs); a workflow_dispatch run (run 28131683839) built keel --release GREEN on ALL THREE OSes (linux/macOS/windows) with NO release created. The live tag-publish (attach binaries to a Release) is exercised by releaseTag010 (the human-signed tag, sequenced last) — honestly pending that, not faked (D0098/D0051). keel validate + guard all green. Re-run: `gh workflow run release.yml`."; }
        part storyReleaseWorkflowDoDR1 : TestResult { :>> id = "63940516-2c7d-4e8f-c157-51627384c003"; :>> outcome = VerdictKind::pass; :>> judgedAgainst = "0706cc8"; :>> judgedAt = "2026-06-24"; :>> judgedBy = "claudeOpus"; }
    }

    verification releaseWorkflowRefineGate : Test { :>> id = "63940516-2c7d-4e8f-c157-51627384c004"; :>> title = "Sprint 157 refine gate (DoR)"; :>> createdAt = "2026-06-24"; :>> createdBy = "claudeOpus"; :>> method = VerificationMethod::inspect; :>> procedureText = "DoR: deployment-readiness — distribute keel so downstream needs no Rust toolchain (D0093). Channel human-chosen = GitHub Releases of prebuilt binaries. Prereq cargoReleaseMetadata done. Resolver: releaseWorkflow. estimatedPoints=2. #CharteredBy d0093. DoD accepted."; }
    part releaseWorkflowRefineGateR1 : TestResult { :>> id = "63940516-2c7d-4e8f-c157-51627384c005"; :>> outcome = VerdictKind::pass; :>> judgedAgainst = "0706cc8"; :>> judgedAt = "2026-06-24"; :>> judgedBy = "claudeOpus"; }
    verification releaseWorkflowStandupGate : Test { :>> id = "63940516-2c7d-4e8f-c157-51627384c006"; :>> title = "Sprint 157 standup gate"; :>> createdAt = "2026-06-24"; :>> createdBy = "claudeOpus"; :>> method = VerificationMethod::inspect; :>> procedureText = "Approach: a matrix release.yml building natively per-OS (no cross-compile) for reliability; build commands mirror ci.yml; softprops/action-gh-release for the attach; a workflow_dispatch + tag-gated publish step so the matrix BUILD can be verified live WITHOUT creating a release (the actual publish is releaseTag010, sign-off). YAML well-formedness checked offline; the live matrix build verified via dispatch. No blockers."; }
    part releaseWorkflowStandupGateR1 : TestResult { :>> id = "63940516-2c7d-4e8f-c157-51627384c007"; :>> outcome = VerdictKind::pass; :>> judgedAgainst = "0706cc8"; :>> judgedAt = "2026-06-24"; :>> judgedBy = "claudeOpus"; }
    verification releaseWorkflowImplementGate : Test { :>> id = "63940516-2c7d-4e8f-c157-51627384c008"; :>> title = "Sprint 157 implement gate"; :>> createdAt = "2026-06-24"; :>> createdBy = "claudeOpus"; :>> method = VerificationMethod::test; :>> procedureText = "Authored .github/workflows/release.yml (3-OS matrix, tag + workflow_dispatch triggers, contents:write, publish gated on tag refs). VERIFIED: YAML parses (3 targets); workflow_dispatch run 28131683839 built keel --release GREEN on linux + macOS + windows (publish skipped, no release). Only annotation = benign Node 20->24 deprecation on actions/checkout@v4. keel validate + guard all green."; }
    part releaseWorkflowImplementGateR1 : TestResult { :>> id = "63940516-2c7d-4e8f-c157-51627384c009"; :>> outcome = VerdictKind::pass; :>> judgedAgainst = "0706cc8"; :>> judgedAt = "2026-06-24"; :>> judgedBy = "claudeOpus"; }
    verification releaseWorkflowReviewGate : Test { :>> id = "63940516-2c7d-4e8f-c157-51627384c00a"; :>> title = "Sprint 157 review gate"; :>> createdAt = "2026-06-24"; :>> createdBy = "claudeOpus"; :>> method = VerificationMethod::inspect; :>> procedureText = "Reviewed. The workflow is minimal + standard (matrix native builds, well-known actions). Honest scope: the matrix BUILD is verified live (dispatch, all 3 OSes green); the tag-triggered PUBLISH (attach to a Release) is NOT yet exercised — it fires only on a real v* tag, which IS releaseTag010 (outward-facing, human-signed, sequenced last). Marking releaseWorkflow done on build-correctness + well-formedness is honest (the artifact exists + builds everywhere); the publish path is verified at releaseTag010. The workflow_dispatch+gated-publish design is what made the build verifiable without a premature release. Clean."; }
    part releaseWorkflowReviewGateR1 : TestResult { :>> id = "63940516-2c7d-4e8f-c157-51627384c00b"; :>> outcome = VerdictKind::pass; :>> judgedAgainst = "0706cc8"; :>> judgedAt = "2026-06-24"; :>> judgedBy = "claudeOpus"; }
    verification releaseWorkflowCloseOutGate : Test { :>> id = "63940516-2c7d-4e8f-c157-51627384c00c"; :>> title = "Sprint 157 closeOut gate (autonomous, D0049)"; :>> createdAt = "2026-06-24"; :>> createdBy = "claudeOpus"; :>> method = VerificationMethod::inspect; :>> procedureText = "Autonomous closeOut (D0049): DoD pass; release.yml builds keel on all 3 OSes (verified live via dispatch). keel validate + guard all green. Self-evidencing (D0051). The deployment-readiness backlog is now complete EXCEPT releaseTag010 (the v0.1.0 tag) — which is the single remaining outstanding item and requires HUMAN sign-off (outward-facing release, confirmation method)."; }
    part releaseWorkflowCloseOutGateR1 : TestResult { :>> id = "63940516-2c7d-4e8f-c157-51627384c00d"; :>> outcome = VerdictKind::pass; :>> judgedAgainst = "0706cc8"; :>> judgedAt = "2026-06-24"; :>> judgedBy = "claudeOpus"; }
    verification releaseWorkflowRetroGate : Test { :>> id = "63940516-2c7d-4e8f-c157-51627384c00e"; :>> title = "Sprint 157 retro gate (autonomous, D0049)"; :>> createdAt = "2026-06-24"; :>> createdBy = "claudeOpus"; :>> method = VerificationMethod::analyze; :>> procedureText = "Autonomous retro (D0049). WELL: the workflow_dispatch + tag-gated-publish pattern let the matrix BUILD be verified live on all 3 OSes WITHOUT creating a premature/outward-facing release — the right way to test a release pipeline before the real tag (which stays the human's gate). Native per-OS builds (no cross-compile) keep it simple + reliable; build commands reuse the proven ci.yml invocation. AVOIDABLE-ISSUE SCAN: none new; the Node 20->24 deprecation annotation on actions/checkout@v4 is upstream + benign (a future bump to checkout@v5 will clear it — noted, not blocking). Estimate 2 pts held. NEXT + LAST: releaseTag010 (tag v0.1.0) — outward-facing, human sign-off required; it fires this workflow to publish the first Release."; }
    part releaseWorkflowRetroGateR1 : TestResult { :>> id = "63940516-2c7d-4e8f-c157-51627384c00f"; :>> outcome = VerdictKind::pass; :>> judgedAgainst = "0706cc8"; :>> judgedAt = "2026-06-24"; :>> judgedBy = "claudeOpus"; }

    // Per-sitting human review (D0049) — the human explicitly accepted this sitting on 2026-06-24
    // ("2. yes accepted"). The sitting spans the sr19 research spike (s155), sr19 white/black-box boundary
    // (s156), and releaseWorkflow (s157); its driving design Decision D0100 is accepted via d0100Accept.
    verification sittingRevS155to157 : Test { :>> id = "63940516-2c7d-4e8f-c157-51627384c010"; :>> title = "Per-sitting review — sr19 spike + sr19 + releaseWorkflow accepted by the human"; :>> createdAt = "2026-06-24"; :>> createdBy = "wweatherholtz"; :>> method = VerificationMethod::confirmation; :>> procedureText = "Per-sitting review (D0049, the single human touchpoint): the human reviewed and EXPLICITLY accepted this sitting — Sprint 155 (sr19 white-box research spike), Sprint 156 (sr19Deliver, white/black-box boundary critique), and Sprint 157 (releaseWorkflow) — on 2026-06-24 ('2. yes accepted'). The test-backed work is self-evidencing (D0051): clippy -D warnings, cargo test (64 lib + workspace), keel validate, guard all 12, the release matrix build on 3 OSes, and GitHub CI all green; this confirmation attests the sitting's direction/acceptance (the irreducible human judgment, D0016). The driving Decision D0100 (interconnects = typed edges not ports; sr19 design) carries its own acceptance (d0100Accept)."; }
    part sittingRevS155to157R1 : TestResult { :>> id = "63940516-2c7d-4e8f-c157-51627384c011"; :>> outcome = VerdictKind::pass; :>> judgedAgainst = "d72e108"; :>> judgedAt = "2026-06-24"; :>> judgedBy = "wweatherholtz"; }
    #Covers dependency from sittingRevS155to157 to sr19SpikeStory;
    #Covers dependency from sittingRevS155to157 to sr19WhiteboxStory;
    #Covers dependency from sittingRevS155to157 to releaseWorkflowStory;
}
