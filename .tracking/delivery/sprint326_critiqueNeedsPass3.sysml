// ProjectDeliveryS326 — Sprint 326: critique backfill pass 3 — five viewer Needs. Two of my own planned
// findings turned out to be FALSE and were dropped after checking. EXECUTE. 3 pts.
package ProjectDeliveryS326 {
    private import EngineElement::*;
    private import EngineWork::*;
    private import EngineVerification::*;
    private import EngineRelationships::*;

    #CharteredBy dependency from critPass3Story to d0080;

    part critPass3Story : Story {
        :>> id = "0d800410-0814-6410-9b3e-000000300410";
        :>> title = "Sprint 326: critique pass 3 — 5 viewer Needs x Core-3, 10 fail / 5 pass (3 pts)";
        :>> createdAt = "2026-08-17"; :>> createdBy = "claudeOpus5"; :>> kind = WorkKind::modeling; :>> priority = WorkPriority::p0; :>> owner = "claudeOpus5"; :>> estimatedPoints = 3;
    }

    action def DeliveryRunS326 {
        action storyCritPass3;
        verification storyCritPass3DoD : Test { :>> id = "0d800411-0814-6411-9b3e-000000300411"; :>> method = VerificationMethod::analyze; :>> procedureText = "Pass 3: nViewerCrossCuttingSlices, nViewerEncodingViewpoints, nViewerExplorableGraph, nViewerExportShare, nViewerGenerativeUi — all wweatherholtz-authored. 10 fail, 5 pass. TWO OF MY OWN PLANNED FINDINGS WERE FALSE AND WERE DROPPED AFTER CHECKING, which is the most useful thing this pass produced: I expected nViewerCrossCuttingSlices to cite retired query.py functions (element_neighbourhood / need_slice) and they are LIVE in keel-cli/src/view.rs; I expected nViewerEncodingViewpoints' auto-generation premise to fail because dates would be plain Strings, and schema/core declares createdAt as Timestamp, a distinct type. Both became PASSES recorded on verified fact. THE REAL FINDINGS: nViewerGenerativeUi's 'NO viewer code change' is true for reading and false for writing — item_detail generalizes to any type, while `keel record` accepts exactly two hardcoded verbs, so a new item type arrives viewable and unmanipulable, and the missing half lives in the ENGINE where the viewer cannot fix it. nViewerExportShare offers a share LINK to 'someone who cannot open the live tool', which D0158's local-only console cannot serve. nViewerExplorableGraph targets 'past a few thousand nodes' while this repository's own model measured 8005 deliverable items in sprint 317 — the target is behind the data. READ BACK: Need coverage 13 -> 18 of 39. validate 354 clean; 34 guards ALL PASS."; }
        part storyCritPass3DoDR1 : TestResult { :>> id = "0d800412-0814-6412-9b3e-000000300412"; :>> outcome = VerdictKind::pass; :>> judgedAgainst = "1b3d471"; :>> judgedAt = "2026-08-17"; :>> judgedBy = "claudeOpus5"; }
    }

    verification c3RefineGate : Test { :>> id = "0d800413-0814-6413-9b3e-000000300413"; :>> title = "Sprint 326 refine gate (DoR)"; :>> createdAt = "2026-08-17"; :>> createdBy = "claudeOpus5"; :>> method = VerificationMethod::inspect; :>> procedureText = "DoR. Five viewer Needs, the last dense cluster of human-authored ones; after this pass 5 critiquable Needs remain. Targets read with their FULL statements rather than titles, which mattered here more than in earlier passes — nViewerEncodingViewpoints' statement is several hundred words of channel bindings, and its testability defect is in one subordinate clause ('semantically enough') that a title could never reveal. estimatedPoints=3."; }
    part c3RefineGateR1 : TestResult { :>> id = "0d800414-0814-6414-9b3e-000000300414"; :>> outcome = VerdictKind::pass; :>> judgedAgainst = "1b3d471"; :>> judgedAt = "2026-08-17"; :>> judgedBy = "claudeOpus5"; }

    verification c3StandupGate : Test { :>> id = "0d800415-0814-6415-9b3e-000000300415"; :>> title = "Sprint 326 standup gate"; :>> createdAt = "2026-08-17"; :>> createdBy = "claudeOpus5"; :>> method = VerificationMethod::inspect; :>> procedureText = "Approach: check every factual claim a critique intends to make BEFORE writing it — three were planned against the codebase this pass and two did not survive the check. Reuse the pass-2 batch writer, which refuses a text containing a double quote and refuses to append to a file that does not end in a closing brace. No blockers."; }
    part c3StandupGateR1 : TestResult { :>> id = "0d800416-0814-6416-9b3e-000000300416"; :>> outcome = VerdictKind::pass; :>> judgedAgainst = "1b3d471"; :>> judgedAt = "2026-08-17"; :>> judgedBy = "claudeOpus5"; }

    verification c3ImplementGate : Test { :>> id = "0d800417-0814-6417-9b3e-000000300417"; :>> title = "Sprint 326 implement gate"; :>> createdAt = "2026-08-17"; :>> createdBy = "claudeOpus5"; :>> method = VerificationMethod::analyze; :>> procedureText = "THE VERIFY-BEFORE-ASSERTING DISCIPLINE (D0151) PAID FOR ITSELF TWICE IN ONE PASS, and both near-misses would have been confident, plausible and wrong — the exact failure D0151 exists to prevent, and the exact failure that makes a critique corpus worthless. (1) I was about to record that nViewerCrossCuttingSlices cites retired implementations, reasoning from the memory that query.py was retired at D0074; element_neighbourhood and need_slice were PORTED and are live in view.rs, so the Need's clause is accurate. (2) I was about to record that nViewerEncodingViewpoints cannot auto-generate because the schema types dates as String; createdAt is declared Timestamp. Both are now PASSES whose procedureText states what I checked and what I had wrongly expected, so a reader can see the reasoning rather than only the verdict. A critique that asserts a false fact about the codebase is worse than no critique: it would have sent someone to fix a Need that is correct."; }
    part c3ImplementGateR1 : TestResult { :>> id = "0d800418-0814-6418-9b3e-000000300418"; :>> outcome = VerdictKind::pass; :>> judgedAgainst = "1b3d471"; :>> judgedAt = "2026-08-17"; :>> judgedBy = "claudeOpus5"; }

    verification c3ReviewGate : Test { :>> id = "0d800419-0814-6419-9b3e-000000300419"; :>> title = "Sprint 326 review gate"; :>> createdAt = "2026-08-17"; :>> createdBy = "claudeOpus5"; :>> method = VerificationMethod::inspect; :>> procedureText = "Reviewed. THE FAIL RATE IS FALLING ACROSS PASSES — 14 of 15, then 11, now 10 — and the reason is worth recording because the opposite trend would be the suspicious one: pass 1 took the oldest and broadest Needs, where clauses had aged out of truth and bounds were missing wholesale; pass 3's viewer Needs were authored later, against a working prototype, and are correspondingly more precise. The passes are also better evidenced: five of this pass's fifteen lenses pass, and two of those five pass BECAUSE a check contradicted my expectation rather than because I found nothing to say. ONE CROSS-PASS OBSERVATION recorded in the critiques themselves: the test that would verify nViewerGenerativeUi (add a schema attribute, require it to appear with no viewer edit) is the same test that would have caught the VIEW_SUBCOMMANDS drift found against nServeReuseModel in pass 2 — one fixture would serve two must-priority Needs, and neither has it."; }
    part c3ReviewGateR1 : TestResult { :>> id = "0d80041a-0814-641a-9b3e-00000030041a"; :>> outcome = VerdictKind::pass; :>> judgedAgainst = "1b3d471"; :>> judgedAt = "2026-08-17"; :>> judgedBy = "claudeOpus5"; }

    verification c3CloseOutGate : Test { :>> id = "0d80041b-0814-641b-9b3e-00000030041b"; :>> title = "Sprint 326 closeOut gate (autonomous, D0049)"; :>> createdAt = "2026-08-17"; :>> createdBy = "claudeOpus5"; :>> method = VerificationMethod::inspect; :>> procedureText = "Autonomous closeOut (D0049). Need coverage 13 -> 18 of 39. Remaining critiquable: 5 Needs, 25 SystemRequirements, 22 Decisions; 87 elements stay blocked on a critic who is not claudeOpus5. Zero open issues; ready frontier empty; D0159 queued. validate 354 clean; check-engine clean; 34 guards ALL PASS; no code changed. NOTED FOR THE OWNER: nViewerEncodingViewpoints (N-18) is still PENDING its Business gate — its testability defect ('semantically enough to auto-generate', with no criterion) is cheap to fix before acceptance and expensive after."; }
    part c3CloseOutGateR1 : TestResult { :>> id = "0d80041c-0814-641c-9b3e-00000030041c"; :>> outcome = VerdictKind::pass; :>> judgedAgainst = "1b3d471"; :>> judgedAt = "2026-08-17"; :>> judgedBy = "claudeOpus5"; }

    verification c3RetroGate : Test { :>> id = "0d80041d-0814-641d-9b3e-00000030041d"; :>> title = "Sprint 326 retro gate (autonomous, D0049)"; :>> createdAt = "2026-08-17"; :>> createdBy = "claudeOpus5"; :>> method = VerificationMethod::analyze; :>> procedureText = "Autonomous retro (D0049) under D0131's retroTrack. WELL: (1) three factual claims were checked against the codebase before being written and two were WRONG — dropped, and recorded as passes that state what I had expected and what the check found, so the reasoning is auditable rather than the verdict alone; (2) the falling fail rate was explained rather than presented, because a critic whose fail rate drifts without explanation is either learning or softening and the record should say which; (3) a cross-pass observation (one fixture would verify two Needs) was recorded inside the critiques where an implementer will find it, not in a sprint note nobody re-reads. AVOIDABLE-ISSUE: none this sprint. WHAT WOULD HAVE GONE WRONG WITHOUT THE CHECK, stated because it is the whole argument for D0151: two confident, plausible, specific findings — each citing a real mechanism and a real Decision number — would have sent a reader to correct two Needs that are accurate, and the critique corpus would have carried false facts about the codebase under my name with a pass-looking coverage number on top. Estimate 3 pts, delivered."; }
    part c3RetroGateR1 : TestResult { :>> id = "0d80041e-0814-641e-9b3e-00000030041e"; :>> outcome = VerdictKind::pass; :>> judgedAgainst = "1b3d471"; :>> judgedAt = "2026-08-17"; :>> judgedBy = "claudeOpus5"; }
}
