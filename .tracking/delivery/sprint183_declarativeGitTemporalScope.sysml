// ProjectDeliveryS183 — Sprint 183: declarativeGitTemporalScope (D0105 migration, MIGRATE step 4).
// Add the git-temporal `newlyAdded` rule scope (the load-bearing complexity D0105 flagged) + source-file
// tracking per model item, and migrate guard:charter to a declared EdgeRule at PARITY. Guards still run.
// EXECUTE. 2 pt. AUTONOMOUS (D0049).
package ProjectDeliveryS183 {
    private import EngineElement::*;
    private import EngineWork::*;
    private import EngineVerification::*;
    private import EngineRelationships::*;

    #CharteredBy dependency from declGitScopeStory to d0105;

    part declGitScopeStory : Story {
        :>> id = "63940516-2c7d-4e8f-c183-51627384c001";
        :>> title = "Sprint 183: declarativeGitTemporalScope (2 pt) - newlyAdded git scope + guard:charter rule at parity (D0105 MIGRATE)";
        :>> createdAt = "2026-07-03"; :>> createdBy = "wweatherholtz"; :>> kind = WorkKind::code; :>> priority = WorkPriority::p1; :>> owner = "claudeOpus"; :>> estimatedPoints = 2;
    }

    action def DeliveryRunS183 {
        action storyDeclGitScope;
        verification storyDeclGitScopeDoD : Test { :>> id = "63940516-2c7d-4e8f-c183-51627384c002"; :>> method = VerificationMethod::test; :>> procedureText = "D0105 MIGRATE step 4 (the git-temporal SCOPE — the inner-platform-risk zone D0105 flagged). (1) ItemInfo gains a repo-relative `file` (threaded through ingest/add_item; Model::build strips the root + forward-slashes — matches `git diff --name-only`). (2) staged_added_files(root): `git diff --cached --name-only --diff-filter=A`. (3) edge_rule_violations gains a scope_files filter; check() maps appliesWhen `newlyAdded` -> Some(staged set) (forward-only), `all` -> None, else evaluated=false (fail-closed). (4) New rule .engine/rules/rules.sysml charterRule (subject Story, requiredEdge charteredBy, newlyAdded), #JustifiedBy d0068 — mirrors guard:charter (D0068). (5) PARITY: unit test edge_rule_newly_added_scope_restricts_to_staged_files (an uncharted Story in a staged-added file is flagged; one in a non-added file is out of scope; all-scope flags both) + LIVE: this very sprint file is staged-added with a #CharteredBy edge, so `keel guard charter` + charterRule both pass it (0 violations). NOTHING retired. VERIFY: clippy -D warnings clean; cargo test (5 rule parity tests pass) green; keel validate + guard all (14) green; rule instance rust-validated (D0048)."; }
        part storyDeclGitScopeDoDR1 : TestResult { :>> id = "63940516-2c7d-4e8f-c183-51627384c003"; :>> outcome = VerdictKind::pass; :>> judgedAgainst = "1b1ceda"; :>> judgedAt = "2026-07-03"; :>> judgedBy = "claudeOpus"; }
    }

    verification declGitScopeRefineGate : Test { :>> id = "63940516-2c7d-4e8f-c183-51627384c004"; :>> title = "Sprint 183 refine gate (DoR)"; :>> createdAt = "2026-07-03"; :>> createdBy = "claudeOpus"; :>> method = VerificationMethod::inspect; :>> procedureText = "DoR: the git-temporal half of the scope sub-language (the D0105-flagged risk zone). charter is the parity target. estimatedPoints=2. #CharteredBy d0105. DoR met."; }
    part declGitScopeRefineGateR1 : TestResult { :>> id = "63940516-2c7d-4e8f-c183-51627384c005"; :>> outcome = VerdictKind::pass; :>> judgedAgainst = "1b1ceda"; :>> judgedAt = "2026-07-03"; :>> judgedBy = "claudeOpus"; }
    verification declGitScopeStandupGate : Test { :>> id = "63940516-2c7d-4e8f-c183-51627384c006"; :>> title = "Sprint 183 standup gate"; :>> createdAt = "2026-07-03"; :>> createdBy = "claudeOpus"; :>> method = VerificationMethod::inspect; :>> procedureText = "Approach: thread source-file into ItemInfo (invasive but mechanical; updated all test constructions); staged_added_files git helper; scope_files filter in edge_rule_violations; charterRule newlyAdded; parity (unit + the self-referential live staged-file test). No guard retired."; }
    part declGitScopeStandupGateR1 : TestResult { :>> id = "63940516-2c7d-4e8f-c183-51627384c007"; :>> outcome = VerdictKind::pass; :>> judgedAgainst = "1b1ceda"; :>> judgedAt = "2026-07-03"; :>> judgedBy = "claudeOpus"; }
    verification declGitScopeImplementGate : Test { :>> id = "63940516-2c7d-4e8f-c183-51627384c008"; :>> title = "Sprint 183 implement gate"; :>> createdAt = "2026-07-03"; :>> createdBy = "claudeOpus"; :>> method = VerificationMethod::test; :>> procedureText = "ItemInfo.file + staged_added_files + newlyAdded scope + charterRule landed. LIVE: keel rules charterRule (scope newlyAdded, evaluated=true) + guard charter both pass. clippy -D clean (fixed into_iter-single-item lint); cargo test edge_rule_newly_added_scope_restricts_to_staged_files + all 5 rule tests pass; keel validate + guard green."; }
    part declGitScopeImplementGateR1 : TestResult { :>> id = "63940516-2c7d-4e8f-c183-51627384c009"; :>> outcome = VerdictKind::pass; :>> judgedAgainst = "1b1ceda"; :>> judgedAt = "2026-07-03"; :>> judgedBy = "claudeOpus"; }
    verification declGitScopeReviewGate : Test { :>> id = "63940516-2c7d-4e8f-c183-51627384c00a"; :>> title = "Sprint 183 review gate"; :>> createdAt = "2026-07-03"; :>> createdBy = "claudeOpus"; :>> method = VerificationMethod::inspect; :>> procedureText = "Reviewed. The git-temporal scope — the piece D0105 named the inner-platform risk — landed bounded + fail-closed: git access is one localized helper, the scope stays a closed enum (all/whereStatus/newlyAdded), and it's forward-only exactly like the guard. The ItemInfo.file threading was invasive but mechanical + fully test-covered. charter reaches parity, self-tested by this sprint's own staged file. Clean."; }
    part declGitScopeReviewGateR1 : TestResult { :>> id = "63940516-2c7d-4e8f-c183-51627384c00b"; :>> outcome = VerdictKind::pass; :>> judgedAgainst = "1b1ceda"; :>> judgedAt = "2026-07-03"; :>> judgedBy = "claudeOpus"; }
    verification declGitScopeCloseOutGate : Test { :>> id = "63940516-2c7d-4e8f-c183-51627384c00c"; :>> title = "Sprint 183 closeOut gate (autonomous, D0049)"; :>> createdAt = "2026-07-03"; :>> createdBy = "claudeOpus"; :>> method = VerificationMethod::inspect; :>> procedureText = "Autonomous closeOut (D0049): DoD pass; both scope halves (whereStatus + newlyAdded) now work; 5 guards have parity rules (rootedness, issues, decision-rationale, acceptance-events, charter). clippy + cargo test + keel validate + guard green. Self-evidencing (D0051)."; }
    part declGitScopeCloseOutGateR1 : TestResult { :>> id = "63940516-2c7d-4e8f-c183-51627384c00d"; :>> outcome = VerdictKind::pass; :>> judgedAgainst = "1b1ceda"; :>> judgedAt = "2026-07-03"; :>> judgedBy = "claudeOpus"; }
    verification declGitScopeRetroGate : Test { :>> id = "63940516-2c7d-4e8f-c183-51627384c00e"; :>> title = "Sprint 183 retro gate (autonomous, D0049)"; :>> createdAt = "2026-07-03"; :>> createdBy = "claudeOpus"; :>> method = VerificationMethod::analyze; :>> procedureText = "Autonomous retro (D0049). WELL: the flagged hard part (git-temporal scope) landed cleanly + bounded — git is one localized helper, scope stays a closed set, forward-only matches the guard; the self-referential live test (this sprint's own staged file exercises charterRule) is a satisfying parity proof. AVOIDABLE-ISSUE SCAN: the invasive ItemInfo.file change risked breaking ~35 test constructions — caught + fixed by the compiler + a bulk edit; LESSON: adding a field to a widely-constructed struct is a mini-migration (compiler is the guard). Estimate 2 pt held. PROGRESS: 5 of ~14 guards at parity; scope sub-language COMPLETE (all/whereStatus/newlyAdded). REMAINING: sprint-coverage (newlyAdded, now unblocked), relational critic-independence, external-file manifest-coverage/viewpoint-renderer, OrderingRule ceremony; then CONTRACT + the keel-check name reconciliation."; }
    part declGitScopeRetroGateR1 : TestResult { :>> id = "63940516-2c7d-4e8f-c183-51627384c00f"; :>> outcome = VerdictKind::pass; :>> judgedAgainst = "1b1ceda"; :>> judgedAt = "2026-07-03"; :>> judgedBy = "claudeOpus"; }
}
