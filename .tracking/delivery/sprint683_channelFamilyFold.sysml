// ProjectDeliveryS683 — Sprint 683: The channel family joins keel github. Under D0453 (accepted on the human's own words 2026-09-12, brief copy-out) the five github verbs - github-pull, github-ingest, github-decider, github-gesture, github-decision-id - leave the top-level dispatch and become sub-verbs of `keel github` (pull, ingest, decider, gesture, decision-id), each keeping its word after the hyphen and its arguments; keel currency keeps its name because it is CI's name for the unattended pass (D0338). In the sprint 512 shape (D0273): a committed transform rewrites every call site in the same commit as the removal, no alias window, each arm MOVED verbatim into the router with its function and its trust classification untouched, and the pre-fold binary is held byte-equal to the post-fold binary on stdout, stderr and exit code over the fixtures the Rust tests use, including the fail-closed case of an undetermined trust - because these are the verbs through which words from outside the repository become facts inside it. Delivers the fifth and last of the folds dcRemainingCliFamilies names; the dispatch count hardening reads drops 39 to 35. CHANGE.. EXECUTE. 2 pts.
package ProjectDeliveryS683 {
    private import EngineElement::*;
    private import EngineWork::*;
    private import EngineVerification::*;
    private import EngineRelationships::*;

    #CharteredBy dependency from channelFamilyFoldStory to d0453;

    part channelFamilyFoldStory : Story {
        :>> id = "53ba1e49-e989-464a-82a2-0ea30b6df37e";
        :>> title = "Sprint 683: The channel family joins keel github. Under D0453 (accepted on the human's own words 2026-09-12, brief copy-out) the five github verbs - github-pull, github-ingest, github-decider, github-gesture, github-decision-id - leave the top-level dispatch and become sub-verbs of `keel github` (pull, ingest, decider, gesture, decision-id), each keeping its word after the hyphen and its arguments; keel currency keeps its name because it is CI's name for the unattended pass (D0338). In the sprint 512 shape (D0273): a committed transform rewrites every call site in the same commit as the removal, no alias window, each arm MOVED verbatim into the router with its function and its trust classification untouched, and the pre-fold binary is held byte-equal to the post-fold binary on stdout, stderr and exit code over the fixtures the Rust tests use, including the fail-closed case of an undetermined trust - because these are the verbs through which words from outside the repository become facts inside it. Delivers the fifth and last of the folds dcRemainingCliFamilies names; the dispatch count hardening reads drops 39 to 35. CHANGE. (2 pts)";
        :>> createdAt = "2026-09-12"; :>> createdBy = "claudeFable5"; :>> kind = WorkKind::code; :>> priority = WorkPriority::p0; :>> owner = "claudeFable5"; :>> estimatedPoints = 2;
    }

    action def DeliveryRunS683 {
        action storyChannelFamilyFold;
        verification storyChannelFamilyFoldDoD : Test { :>> id = "7fe1855e-5c48-4d39-a63d-8ae836160022"; :>> method = VerificationMethod::test; :>> procedureText = "DELIVERED: `keel github pull|ingest|decider|gesture|decision-id ...` answers with arguments unchanged and `keel github` bare prints a usage naming the five sub-verbs; `keel currency` is untouched. The five top-level arms are gone from main.rs and COMMAND_NAMES (38 to 34); the five CliCommand facts are removed from both homes and one github fact carries the five sub-verbs in its invocation (89 facts to 85, cli-surface-declared equal); the fact's effect is `both` and its stability `stable`, the three deprecated sub-verbs marked in the synopsis, because a fact declares one effect and one stability per command (issue501's class, dcSubVerbEffectIsDeclared). Every call site under .engine, CLAUDE.md, scripts and the Rust prose is rewritten by .engine/tools/migrations/2026-09-12-channel-family-fold.py (dry-run default, per-verb per-file conservation, re-plan 0); the Rust argv sites and the bare spellings the `keel <verb>` rule cannot see (CLAUDE.md section 4, the skill's removal path, currency's step banner, the refusal-message prefixes) by hand, each asserted to hit once; .claude regenerated by keel sync-claude. The pre-fold binary keel-prefold683.exe (build ecd447e) and the post-fold binary agree on stdout, stderr and exit code for every sub-verb over the federation fixture (ingest from file: first write, re-ingest refused, --by missing, --at missing, no --repo so trust fails CLOSED), decider bare and with a declared and an undeclared login, gesture over an accept comment and an empty one, decision-id plain, --join and bare, pull without --repo and pull against an unreachable repository - 16 cases SAME 7 DIFF 9 (cmp683.log), exit codes equal on all 16 and stdout equal on all 16; every DIFF is stderr only and is read from the log, not assumed - one class: the refusal or usage line that names the command (`github ingest: --by ...` for `github-ingest: --by ...`, `usage: keel github pull` for `usage: keel github-pull`), plus the router's own usage, the --help surface five entries shorter, and currency's step banner naming `github pull`. The ingest fail-closed case wrote sourceTrust = SourceTrust::untrusted in both scratch trees and the two trees differ only in the minted UUID. The router-to-fact test holds `keel github`'s arms to the fact's invocation; a retired channel verb is no longer a command. The control structure derives one action per sub-verb from the github fact, so cmdGithubPull and cmdGithubIngest keep their names and stpa-currency's open list gains the three read and tooling sub-verbs the fact cannot type - issue501's class, not a new finding. hardening reads dispatched 35/35. Decisions and .tracking are not rewritten; keel-cli/tests/fixtures is frozen. Resolves issue508: scripts/exec_brief/facts.py runs the keel binary from KEEL_BIN, then the keel-serve.exe copy, and the build image only when no copy exists, so a brief build can no longer hold target/release/keel.exe against cargo's relink."; }
        // RAN: keel suite --touched . from keel-serve.exe, detached: touched-receipt.toml outcome pass, 634 passed 0 failed, 244 s, at 1789212319 - launch epoch 1789212075 == seconds, stems cli_facts cli_surface currency github github_ingest hardening, lib true; compare683.py 16 cases SAME 7 DIFF 9 stderr-only command-name substitution, exit codes and stdout equal on all 16 (cmp683.log); keel show hardening . dispatched 35 namedInHelp 35 (hardening683.json); keel gate guard --no-receipt . cli-surface-declared PASS 85 scanned; capability_refusal_bites 9/9 incl. a_retired_channel_verb_is_no_longer_a_command; python .engine/tools/migrations/2026-09-12-channel-family-fold.py --apply 22 sites 8 files re-plan 0; keel sync-claude --check clean; python scripts/exec_brief/facts.py after the KEEL_BIN/keel-serve.exe resolution ran to exit 0 beside no cargo, issue508
        part storyChannelFamilyFoldDoDR1 : TestResult { :>> id = "28c32154-a3f0-458f-8f91-96c00a4a0980"; :>> outcome = VerdictKind::pass; :>> judgedAgainst = "ecd447e"; :>> judgedAt = "2026-09-12"; :>> judgedBy = "claudeFable5"; }
    }

    verification channelFamilyFoldRefineGate : Test { :>> id = "a4949051-7466-458c-8a31-a00c4a2013b4"; :>> title = "Sprint 683 refine gate (DoR)"; :>> createdAt = "2026-09-12"; :>> createdBy = "claudeFable5"; :>> method = VerificationMethod::inspect; :>> procedureText = "Chartered by D0453, accepted by the human on the brief copy-out 2026-09-12. Two points, as D0453 sized it: five dispatch arms move under one new router with their bodies untouched, one constant array shrinks, five facts leave two homes and one fact is added, one Python transform over some forty sites in .engine, scripts and the Rust prose, two argv sites and a handful of bare spellings by hand, and a fixture comparison where the fail-closed trust line is the answer. The smallest of the five folds: no hook, workflow, guard needle or scaffold names a github verb (census: git grep over the tracked tree outside .tracking, .engine/decisions, CHANGELOG.md, docs/reviews and the frozen fixtures - 18 files). NOT A PROCESS CHANGE beyond what D0453 states - the fold is the Decision's own text and the transform rewrites two actionText lines of .engine/processes/github-intake.sysml to the spelling the Decision names; whether the keystone lock reads that as a process-def change is probed on the staged tree, and if it does the marker Decision is plan-covered by d0453 (D0396) as d0455 was by d0452. NOT A FORK - the fork was d0399 and is decided."; }
    // RAN: keel show authority-queue . at ecd447e: d0453 absent from decisionAcceptance (accepted by the human, brief copy-out 2026-09-12, landed 6821b5c); keel show whats-next .: dcRemainingCliFamilies at the head of the ready list; record sprint 683 channelFamilyFold --charter d0453 --points 2 (CharteredBy edge authored by the write); census: git grep over the tracked tree outside .tracking, .engine/decisions, CHANGELOG.md, docs/reviews, keel-cli/tests/fixtures - 18 files name a github verb, none under .githooks, .github/workflows, guards.rs, scaffold or control_structure.rs; keel gate guard . on the staged tree read .engine/processes/github-intake.sysml and the github-intake skill and registry as locked (process-change red with no marked Decision), so the marker Decision d0456 was recorded plan-covered by d0453 (D0396)
    part channelFamilyFoldRefineGateR1 : TestResult { :>> id = "c1a87f1c-03ad-4ef9-a848-ed0c821652fd"; :>> outcome = VerdictKind::proposed; :>> judgedAgainst = "ecd447e"; :>> judgedAt = "2026-09-12"; :>> judgedBy = "claudeFable5"; }
    verification channelFamilyFoldStandupGate : Test { :>> id = "f83fd600-fe17-4ab8-9a8c-8bedb63d5cd7"; :>> title = "Sprint 683 standup gate"; :>> createdAt = "2026-09-12"; :>> createdBy = "claudeFable5"; :>> method = VerificationMethod::inspect; :>> procedureText = "Order, taken from the 678-682 retros: preserve the pre-fold binary FIRST as keel-prefold683.exe from the landed ecd447e build; census every site by git grep and read each one; sweep every control bound to a verb's spelling before the transform runs - none found: the guards, hooks, workflows, scaffold and control-structure reader name no github verb, and camel('github')+camel('pull') is the name camel('github-pull') gave, so the computed action names hold; remove the five arms from main() and route them from cmd_github, each old line asserted unique; shrink COMMAND_NAMES and remove the five facts from both homes while adding the github fact in one script so cli-surface-declared stays equal; extend the router-to-fact test to the third router; rewrite the argv and bare sites by hand; run the transform dry then apply; sync-claude; rebuild; compare old against new over the fixture cases; read hardening back; probe the keystone lock on the staged tree."; }
    // RAN: cp target/release/keel.exe target/release/keel-prefold683.exe before any edit (keel-prefold683.exe version reads ecd447e); census.py over main.rs: five arms each found once; spelling-bound controls swept before the transform: grep over guards.rs, .githooks, .github/workflows, scaffold assets and control_structure.rs finds no github verb; camel(github)+camel(pull) == camel(github-pull) checked in control_structure.rs sub-verb naming so cmdGithubPull and cmdGithubIngest keep their names; order then followed as stated: arms removed and routed, COMMAND_NAMES and both fact homes edited in one script, router test extended, argv and bare sites by hand, transform dry then apply, sync-claude, cargo build --release, compare683.py, keel show hardening, keel gate guard on the staged tree
    part channelFamilyFoldStandupGateR1 : TestResult { :>> id = "89b1bb84-9de9-499a-b142-5ba69352ec53"; :>> outcome = VerdictKind::proposed; :>> judgedAgainst = "ecd447e"; :>> judgedAt = "2026-09-12"; :>> judgedBy = "claudeFable5"; }
    verification channelFamilyFoldImplementGate : Test { :>> id = "df65b481-d1d5-42c3-b524-522d25b6764c"; :>> title = "Sprint 683 implement gate"; :>> createdAt = "2026-09-12"; :>> createdBy = "claudeFable5"; :>> method = VerificationMethod::test; :>> procedureText = "DELIVERED: main.rs five arms removed; github_subverb routes pull, ingest, decider, gesture and decision-id to the untouched functions with their remaining argv (ingest and pull keep their explicit --root resolution verbatim); cmd_github names a word that is not a sub-verb and prints the usage naming the five, a flag falling through to the usage alone - the positional read is flag-guarded because hardening::every_positional_read_is_flag_guarded refused the first draft; COMMAND_NAMES 34; cli_facts.rs and commands.sysml lose five facts and gain the github fact (effect both, stability stable, the three deprecated sub-verbs named in the synopsis), 85 facts, cli-surface-declared 85 scanned clean; hardening.rs comment 35; the router-to-fact test (renamed the_gate_audit_and_github_sub_verbs_match_their_facts) holds ('github', 5) and a_retired_channel_verb_is_no_longer_a_command holds the five retired names to the usage banner and `keel github pulls` to the not-a-sub-verb line; federation.rs and unknown_flag_is_refused.rs argv and prose; the transform .engine/tools/migrations/2026-09-12-channel-family-fold.py applied 22 sites across 8 files (github.rs 8, github_ingest.rs 5, the github-intake process 2 and skill 2, main.rs 2, the skill registry 1, two exec_brief builders 1 each) with per-verb per-file conservation and re-plan 0; bare spellings by hand list (fold683_rust.py, each hit count asserted): nine refusal prefixes in github_ingest.rs, one in github.rs, currency's banner, CLAUDE.md section 4, the skill's removal path; keel sync-claude regenerated .claude (--check clean, 46 skills); d0456 recorded as the plan-covered marker Decision (D0396, step quoted verbatim from d0453 after the first record refused a paraphrase) with a #DependsOn edge to d0453."; }
    // RAN: python .engine/tools/migrations/2026-09-12-channel-family-fold.py --dry-run then --apply: 22 sites / 8 files, conservation reconciled per verb per file, re-plan 0; fold683_rust.py hand list each anchor asserted to hit once (five arms, github_subverb + cmd_github inserted after fn resolve_guard_root, COMMAND_NAMES 34, CLI_FACTS 85, cliGithub part in commands.sysml, hardening.rs comment, tests, nine github_ingest.rs prefixes, github.rs prefix, currency.rs banner, CLAUDE.md, SKILL.md); cargo build --release -p keel-cli (first build refused CLI_FACTS 89 vs 85 entries, fixed); cargo test --lib hardening 10/10 after the flag-guard fix on cmd_github (every_positional_read_is_flag_guarded refused args.first() bare); cargo test --lib control_structure 11/11; cargo test --test capability_refusal_bites 9/9; --test federation f7 1/1; --test unknown_flag_is_refused 4/4; cargo clippy --all-targets -D warnings clean; keel sync-claude then sync-claude --check clean (46 skills); keel show hardening . dispatched 35 namedInHelp 35 coveragePct 100 (hardening683.json); keel gate guard --no-receipt . cli-surface-declared PASS 85 scanned, process-change PASS 3 scanned with d0456 in the tree (guard683b.log)
    part channelFamilyFoldImplementGateR1 : TestResult { :>> id = "41b3a242-a034-4fa9-94c1-d5a191d39ee5"; :>> outcome = VerdictKind::pass; :>> judgedAgainst = "ecd447e"; :>> judgedAt = "2026-09-12"; :>> judgedBy = "claudeFable5"; }
    verification channelFamilyFoldReviewGate : Test { :>> id = "3c34fc81-e3a2-4867-8e53-2d5513040cf7"; :>> title = "Sprint 683 review gate — three passes per D0172"; :>> createdAt = "2026-09-12"; :>> createdBy = "claudeFable5"; :>> method = VerificationMethod::inspect; :>> procedureText = "DELIVERED: fixture comparison (compare683.py, 16 cases, each writing case in its own scaffold per binary, both scaffolded by the pre-fold binary) SAME 7 DIFF 9, every DIFF stderr-only and the command-name substitution, exit codes and stdout equal on all 16, the fail-closed trust line identical in both trees; hardening dispatched 35 namedInHelp 35 read back from keel show hardening; clippy --all-targets -D warnings clean; capability_refusal_bites 9/9, federation 1/1, unknown_flag_is_refused 4/4, hardening lib 10/10, control_structure lib 11/11; keel gate guard stpa-currency 44 of 65 open, the five cmdGithub* among them (warn only, issue501's class - the DoD of dcSubVerbEffectIsDeclared now names the github case); process-change PASS 3 scanned once d0456 was in the tree, having read the process, skill and registry as locked before it. Finding carried to the retro: issue507 (the verb count after the fifth fold)."; }
    // RAN: compare683.py (16 cases, keel-prefold683.exe ecd447e vs keel-serve.exe ecd447e+dirty, each writing case in a fresh scaffold per binary scaffolded by the pre-fold binary) -> cmp683.log SAME 7 DIFF 9; every DIFF read: stderr only, the command-name substitution (github-X: -> github X, usage: keel github-X -> usage: keel github X), exit codes equal on all 16, stdout equal on all 16; ingest fail-closed case wrote sourceTrust untrusted in both trees, trees differ only in the minted UUID; keel show hardening . 35/35; cargo clippy --all-targets -D warnings clean; capability_refusal_bites 9/9 incl. the_gate_audit_and_github_sub_verbs_match_their_facts and a_retired_channel_verb_is_no_longer_a_command; keel gate guard --no-receipt . stpa-currency PASS 65 scanned 1 warning (44 of 65 open incl. cmdGithubDecider, cmdGithubDecisionId, cmdGithubGesture, cmdGithubIngest, cmdGithubPull); keel show control-structure . 66 actions (63 before), feedbacks readGithubDecider and readGithubGesture gone - issue501 class, DoD of dcSubVerbEffectIsDeclared extended; finding issue507 recorded with resolver dcRemainingCliFamilies
    part channelFamilyFoldReviewGateR1 : TestResult { :>> id = "da2295e6-9284-4086-8f25-a48101dea359"; :>> outcome = VerdictKind::proposed; :>> judgedAgainst = "ecd447e"; :>> judgedAt = "2026-09-12"; :>> judgedBy = "claudeFable5"; }
    verification channelFamilyFoldCloseOutGate : Test { :>> id = "e77d2fdd-cc11-4625-869c-3904b5fbb0a5"; :>> title = "Sprint 683 closeOut gate (autonomous, D0049)"; :>> createdAt = "2026-09-12"; :>> createdBy = "claudeFable5"; :>> method = VerificationMethod::inspect; :>> procedureText = "DELIVERED: closes on the fixture comparison, the hardening read-back, gate validate, gate check-engine, gate guard --no-receipt (every guard 0 violations once the retro text landed), sync-claude --check, clippy, the surface and refusal tests and the touched suite run by the VERIFIER (D0425/D0438), receipt in the closeOut result. The co-committed marker Decision is d0456 (plan-covered by d0453, D0396). dcRemainingCliFamilies does NOT close: its per-fold VERIFY holds (D0453 states falls by four, hardening reads 39 to 35) but the clause it exists to make honest - D0273's under 25, d0399 option A's roughly 20 - reads 35, which is what option A's own counts gave; the choice between folding eleven more names and amending the clause is the fork d0457, held for the human with the counts, and issue507 records the miss against dcRemainingCliFamilies."; }
    // RAN: VERIFIER receipt (verifier_receipt683.md, skill test-verify, haiku, D0425/D0438): keel gate validate . -> 782 items clean exit 0; keel gate check-engine . -> clean exit 0; keel gate guard --no-receipt . -> ALL PASS, 316 warnings 0 violations, process-change PASS with d0456 in the tree; keel sync-claude --check -> clean, 46 skills; cargo clippy --release --all-targets -D warnings -> clean; D0388 pair: capability_refusal_bites 9/9 (positive), `keel github-pull` -> usage banner exit 2 and `keel github pulls` -> not-a-sub-verb exit 2 (negative); the receipt reported ONE discrepancy - keel suite --touched failed to compile, target/release/keel.exe locked (facts.py had run the build image, issue508, fixed in facts.py) - so the touched run was re-launched detached by the primary after the fix: .keel/metrics/touched-receipt.toml head ecd447e at 1789212319 seconds 244 (launch epoch 1789212075, at - seconds == launch), stems [cli_facts, cli_surface, currency, github, github_ingest, hardening], lib true, 17 integration tests, outcome pass, passed 634 failed 0, log .keel/metrics/touched-1789212075.log; dcRemainingCliFamilies left open: hardening 35 against under 25 (issue507, fork d0457)
    part channelFamilyFoldCloseOutGateR1 : TestResult { :>> id = "bc3fc000-8303-4908-8310-69ea98d7bc41"; :>> outcome = VerdictKind::proposed; :>> judgedAgainst = "ecd447e"; :>> judgedAt = "2026-09-12"; :>> judgedBy = "claudeFable5"; }
    verification channelFamilyFoldRetroGate : Test { :>> id = "342578a4-f250-4a40-aa64-9eca12782b75"; :>> title = "Sprint 683 retro gate (autonomous, D0049)"; :>> createdAt = "2026-09-12"; :>> createdBy = "claudeFable5"; :>> method = VerificationMethod::analyze; :>> procedureText = "AVOIDABLE-ISSUE SCAN, two findings, two tracked items (D0131): (2) the touched suite failed to relink target/release/keel.exe (Access is denied) because scripts/exec_brief/facts.py ran the build image for its show reads while the VERIFIER had cargo running - issue150 lived in CLAUDE.md as a rule and in no code - issue508, resolver this story: facts.py now resolves KEEL_BIN, then the keel-serve.exe copy, then the build image only when no copy exists, and the suite re-ran clean (634 passed, 244 s); (1) the fifth fold lands the verb count at 35, and d0399 option A's stated landing of roughly 20 never followed from the counts written beside it - the same underived-number class as D0273's under-25 clause (issue338) one Decision later - issue507, resolver dcRemainingCliFamilies (whose DoD already said to put what remains to the human as a fork with the counts), the fork itself d0457 with the family census in its research field. Not tracked, and why: the every_positional_read_is_flag_guarded failure on cmd_github's first draft is an existing control firing as designed (D0388 class), not a gap; the plan-cover refusal on the paraphrased step name is the D0396 check doing its job - the step must be the plan's words; the keystone lock reading the github-intake process and skill as locked answered sprint 680's open question in the affirmative and d0456 is the record, no new control needed; the three cmdGithub* read and tooling sub-verbs emitted as write actions are issue501's class and its DoD was extended rather than a fourth issue opened. What went right: the fixture comparison's one-class result (command name only, stderr only) is what moving each arm verbatim into the router buys, and quoting the plan's step verbatim into the marker Decision is cheaper than re-asking."; }
    // RAN: retro-backlog guard PASS in keel gate guard --no-receipt . with the DELIVERED retro text in the tree; the two findings are the tracked items issue507 (record issue ... --resolver dcRemainingCliFamilies, #Resolves authored at record) and issue508 (--resolver channelFamilyFoldStory); the fork d0457 recorded and HELD proposed as a fork by record decision (third record attempt after two D0337 holds on the safety-change words, the text now carries NOT A PROCESS CHANGE); keel show authority-queue . -> one decisionAcceptance row, d0457; four not-tracked items each name their reason in the retro text
    part channelFamilyFoldRetroGateR1 : TestResult { :>> id = "c9e2dd8b-6b53-4e99-bbb1-18390ddd04b2"; :>> outcome = VerdictKind::proposed; :>> judgedAgainst = "ecd447e"; :>> judgedAt = "2026-09-12"; :>> judgedBy = "claudeFable5"; }
}
