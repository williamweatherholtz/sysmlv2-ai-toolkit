// ProjectDeliveryS429 — Sprint 429: judgeable deck: only the tapped option lights up, every decision card carries its own why, and short names become the convention (their 2026-08-23 feedback). EXECUTE. 1 pts.
package ProjectDeliveryS429 {
    private import EngineElement::*;
    private import EngineWork::*;
    private import EngineVerification::*;
    private import EngineRelationships::*;

    #CharteredBy dependency from judgeableDeckStory to d0203;

    part judgeableDeckStory : Story {
        :>> id = "75ea03ad-7ac9-4b62-b78b-ea888d123f31";
        :>> title = "Sprint 429: the deck earns the signature (1 pts)";
        :>> createdAt = "2026-08-23"; :>> createdBy = "claudeFable5"; :>> kind = WorkKind::code; :>> priority = WorkPriority::p0; :>> owner = "claudeFable5"; :>> estimatedPoints = 1;
    }

    action def DeliveryRunS429 {
        action storyJudgeableDeck;
        verification storyJudgeableDeckDoD : Test { :>> id = "bf9bc501-702a-46d0-acf2-66aaa5bb4043"; :>> method = VerificationMethod::test; :>> procedureText = "DELIVERED: dcDeckJudgeableCards (resolves issue233 + issue234, their direct feedback) and the shortNames convention (D0203, accepted on their verbatim direction). THE SELECTION BUG (issue233): accept styling keyed on data-v=accept, shared by every option button on a fork card, so any accepted fork lit ALL options - the human fought the UI and the inbox recorded ELEVEN contradictory d0201 rows (A/B/C within seconds), none bindable; the tap bound correctly in data and lied in pixels. FIX: JS stamps data-sel on the tapped option and clears siblings; generic accept styling restricted to non-option buttons. THE CONTEXT GAP (issue234): decision cards rendered title + 'needs your signature' and nothing else - a signature could only be a trust gesture. FIX: every decision card renders a collapsible panel with the decision's own context (why it came up) and decision text (what is being decided), read from the decision file at generation. INBOX ADJUDICATION, recorded honestly: of the 21 unprocessed rows, the CLEAN single-option taps bound (quote receipts d0198 OPTION A; guard bundling d0199; review sampling d0200 OPTION A) plus two finding accepts and two sittings; the eleven contradictory tap-to-sign (d0201) rows CANNOT bind and the choice is re-asked in chat under the new convention. VERIFIED: regenerated deck shows exactly one highlighted option per fork and a why-panel on both remaining decision cards (grep read-back x2); emitted-JS parse test green; suite and clippy green after a hand-repair of a scripted extraction (see review gate)."; }
        part storyJudgeableDeckDoDR1 : TestResult { :>> id = "f768fcfb-74d1-4359-bc3a-ad46dc49504e"; :>> outcome = VerdictKind::pass; :>> judgedAgainst = "71f645386eaae707123ee7016522851a1da61347"; :>> judgedAt = "2026-08-23"; :>> judgedBy = "claudeFable5"; }
    }

    verification judgeableDeckRefineGate : Test { :>> id = "d2438865-cfed-419d-bbea-9e52042c732c"; :>> title = "Sprint 429 refine gate (DoR)"; :>> createdAt = "2026-08-23"; :>> createdBy = "claudeFable5"; :>> method = VerificationMethod::inspect; :>> procedureText = "DoR. Their feedback IS the charter: the selection bug, the context gap, and the short-name convention, all in one sitting. 1 point."; }
    part judgeableDeckRefineGateR1 : TestResult { :>> id = "472adb36-d9a5-4a0b-b233-81e11e716df6"; :>> outcome = VerdictKind::pass; :>> judgedAgainst = "71f645386eaae707123ee7016522851a1da61347"; :>> judgedAt = "2026-08-23"; :>> judgedBy = "claudeFable5"; }
    verification judgeableDeckStandupGate : Test { :>> id = "62029241-38f9-4b4c-bc5f-e60562d536d8"; :>> title = "Sprint 429 standup gate"; :>> createdAt = "2026-08-23"; :>> createdBy = "claudeFable5"; :>> method = VerificationMethod::inspect; :>> procedureText = "Approach: fix the pixels where the data was already right (data-sel beside data-opt-chosen); pull deciding context from the decision file itself so the card can never drift from the record; record the convention as an accepted decision with their verbatim words rather than a memory-only rule. No blockers."; }
    part judgeableDeckStandupGateR1 : TestResult { :>> id = "141828ab-f691-4a5e-b356-8426baa2f9fc"; :>> outcome = VerdictKind::pass; :>> judgedAgainst = "71f645386eaae707123ee7016522851a1da61347"; :>> judgedAt = "2026-08-23"; :>> judgedBy = "claudeFable5"; }
    verification judgeableDeckImplementGate : Test { :>> id = "dee1c7f8-e4b6-4484-aef8-b7d5e8704ac1"; :>> title = "Sprint 429 implement gate"; :>> createdAt = "2026-08-23"; :>> createdBy = "claudeFable5"; :>> method = VerificationMethod::test; :>> procedureText = "Verified by running: regenerated deck greps - details class=why x2 (both pending decision cards), not([data-opt]) present in the CSS, one data-sel path in the JS; the eleven contradictory d0201 inbox rows were adjudicated non-binding while three clean taps were recorded with row-level provenance; cargo test deck suite + emitted-JS parse green; clippy pedantic+nursery clean."; }
    part judgeableDeckImplementGateR1 : TestResult { :>> id = "b7144d30-702d-4b9c-9e2e-8ac1b23f5a28"; :>> outcome = VerdictKind::pass; :>> judgedAgainst = "71f645386eaae707123ee7016522851a1da61347"; :>> judgedAt = "2026-08-23"; :>> judgedBy = "claudeFable5"; }
    verification judgeableDeckReviewGate : Test { :>> id = "58966f82-4b0e-43bb-8bd9-27a368366e67"; :>> title = "Sprint 429 review gate — three passes per D0172"; :>> createdAt = "2026-08-23"; :>> createdBy = "claudeFable5"; :>> method = VerificationMethod::inspect; :>> procedureText = "PASS 1, CLAIMS: the eleven-row count and mixed options are quoted from the inbox read-back; the render greps are from this session. PASS 2, BOUNDARY: the why-panel renders raw decision prose - a decision authored WITHOUT plain language still renders unjudgeable text, which is exactly what D0203 clause 1 exists to fix at authoring time; the card cannot repair a bad title. PASS 3, OWN DIFF: a scripted function extraction mangled deck.rs (duplicated block, orphaned braces) and was hand-repaired - the lesson, again, is that structural Rust edits belong to targeted Edit calls, not regex surgery; the compiler caught every fragment. WHAT A REVIEWER SHOULD ATTACK: adjudicating eleven contradictory taps as non-binding was a convener judgment - the alternative (latest-tap-wins would have picked OPTION B at 03:56:58.9) is defensible, and the human should know both readings existed; the chat re-ask resolves it either way."; }
    part judgeableDeckReviewGateR1 : TestResult { :>> id = "89717b9a-5101-441c-b063-6445d825d5e9"; :>> outcome = VerdictKind::pass; :>> judgedAgainst = "71f645386eaae707123ee7016522851a1da61347"; :>> judgedAt = "2026-08-23"; :>> judgedBy = "claudeFable5"; }
    verification judgeableDeckCloseOutGate : Test { :>> id = "ac0a8ac0-8e43-43ef-840c-d0cb9c207d5b"; :>> title = "Sprint 429 closeOut gate (autonomous, D0049)"; :>> createdAt = "2026-08-23"; :>> createdBy = "claudeFable5"; :>> method = VerificationMethod::inspect; :>> procedureText = "Autonomous closeOut (D0049). issues 233/234 resolve; D0203 accepted on their words; three decisions signed from clean taps (d0198 A, d0199, d0200 A); tap-to-sign (d0201) re-asked; validate + all 47 guards green."; }
    part judgeableDeckCloseOutGateR1 : TestResult { :>> id = "de45b8c1-4758-424e-a3d3-42efc42ef60c"; :>> outcome = VerdictKind::pass; :>> judgedAgainst = "71f645386eaae707123ee7016522851a1da61347"; :>> judgedAt = "2026-08-23"; :>> judgedBy = "claudeFable5"; }
    verification judgeableDeckRetroGate : Test { :>> id = "a72622b9-216a-4016-be07-7610d86a63f5"; :>> title = "Sprint 429 retro gate (autonomous, D0049)"; :>> createdAt = "2026-08-23"; :>> createdBy = "claudeFable5"; :>> method = VerificationMethod::analyze; :>> procedureText = "Autonomous retro (D0049). AVOIDABLE-ISSUE SCAN under rcRecurrence: issue233 is the unbindable-gesture class (issue223) recurring in PIXELS after being fixed in DATA - the practice extends: when a gesture surface changes, verify the visible state round-trip, not just the recorded one; a screenshot-level check belongs in the control-evaluation sprint. WELL: their three-part feedback became two resolved issues, one accepted convention, and a live deck fix inside one sitting - and the D0200 OPTION A signature arrived through the very fork-button pipeline sprint 419 built. Estimate 1 pt, delivered 1."; }
    part judgeableDeckRetroGateR1 : TestResult { :>> id = "5ebe0fea-c96e-4992-aa24-78e7d3c91d9f"; :>> outcome = VerdictKind::pass; :>> judgedAgainst = "71f645386eaae707123ee7016522851a1da61347"; :>> judgedAt = "2026-08-23"; :>> judgedBy = "claudeFable5"; }
}
