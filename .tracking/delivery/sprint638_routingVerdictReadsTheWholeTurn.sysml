// ProjectDeliveryS638 — Sprint 638: The routing rig's verdict reads every Skill call of a turn - intake before the intended skill is a declared prefix, a different skill anywhere is wrong - and the release case is re-run under that rule (dcRoutingVerdictReadsTheWholeTurn, issue415, D0418). EXECUTE: one Sensor's mechanism changes its scoring; no guard, hook or process changes. 2 pts.. EXECUTE. 2 pts.
package ProjectDeliveryS638 {
    private import EngineElement::*;
    private import EngineWork::*;
    private import EngineVerification::*;
    private import EngineRelationships::*;

    #CharteredBy dependency from routingVerdictReadsTheWholeTurnStory to d0418;

    part routingVerdictReadsTheWholeTurnStory : Story {
        :>> id = "d0c9fd76-f8ef-4b76-bd7e-28d9e95a4601";
        :>> title = "Sprint 638: The routing rig's verdict reads every Skill call of a turn - intake before the intended skill is a declared prefix, a different skill anywhere is wrong - and the release case is re-run under that rule (dcRoutingVerdictReadsTheWholeTurn, issue415, D0418). EXECUTE: one Sensor's mechanism changes its scoring; no guard, hook or process changes. 2 pts. (2 pts)";
        :>> createdAt = "2026-09-09"; :>> createdBy = "claudeOpus5"; :>> kind = WorkKind::code; :>> priority = WorkPriority::p0; :>> owner = "claudeOpus5"; :>> estimatedPoints = 2;
    }

    action def DeliveryRunS638 {
        action storyRoutingVerdictReadsTheWholeTurn;
        verification storyRoutingVerdictReadsTheWholeTurnDoD : Test { :>> id = "cb6e4c50-9b1e-492e-a727-f59a24367cab"; :>> method = VerificationMethod::test; :>> procedureText = "DELIVERED (dcRoutingVerdictReadsTheWholeTurn, resolves issue415 through that item; issue431 fixed in the same commit and resolved through it): routing_probe.py scores through a pure `score(skills, accept)` over every Skill call in order - routed with `prefix` when an accepted skill appears and every call before it is in DECLARED_PREFIX (intake, citing .claude/skills/intake/SKILL.md:3), wrong when a skill that is neither accepted nor a prefix appears anywhere, none when the intended skill never appears; sample records carry `prefix` and `skillsInvoked` in order, the printed line shows the prefix; the docstring says why intake is the one declared prefix and quotes its description line. PROBED (D0388) before any model was paid for: python .engine/tools/routing_probe.py --probe -> intake then release = routed prefix [intake]; release = routed; stpa then release = wrong; nothing = none; intake alone = none with prefix; intake then stpa = wrong; a namespaced call scores by its short name - all 7 hold, and an investigation runs the probe first and refuses on a failure. RE-RUN on tree f848923: --investigate release --samples 3 (3 turns) -> `NOT ROUTING release: 3/3 samples none`, every sample prefix intake, tools Skill / ToolSearch / ToolSearch or Skill / ToolSearch / Read / Read to the last turn; `spend this investigation: $3.71 over 3 run(s), 59s wall (measured per run: $1.2352, 47.2s)` against the $1.56 estimate. The samples agree on a reason they show - the declared prefix spends the budget the intended skill needed - so it is the next Issue against the check: issue432, resolver dcPrefixLeavesRoomForTheRoute, not acted on here. No rate or standing number introduced. issue431: the receipt unlink moved after the estimate and the dry-run return; a dry run after the paid run quotes $1.24 / 47 s measured 2026-09-09 with the receipt still on disk."; }
        // RAN: python .engine/tools/routing_probe.py --probe -> all 7 cases hold (intake then release = routed prefix intake; release = routed; stpa then release = wrong; nothing = none; intake alone = none; intake then stpa = wrong; namespaced = routed); python .engine/tools/routing_probe.py --investigate release --samples 3 -> NOT ROUTING release: 3/3 samples none, every sample prefix intake with tools to the last turn; spend this investigation: 3.71 USD over 3 run(s), 59s wall (measured per run: 1.2352 USD, 47.2s); the unanimous reason is issue432 (resolver dcPrefixLeavesRoomForTheRoute); a dry run afterwards quotes 1.24 USD / 47s measured 2026-09-09 with the receipt on disk (issue431 fixed)
        part storyRoutingVerdictReadsTheWholeTurnDoDR1 : TestResult { :>> id = "aee2fedd-1daa-4ef7-b0f7-ea50c2fe0a3f"; :>> outcome = VerdictKind::pass; :>> judgedAgainst = "f848923"; :>> judgedAt = "2026-09-09"; :>> judgedBy = "claudeOpus5"; }
    }

    verification routingVerdictReadsTheWholeTurnRefineGate : Test { :>> id = "b4c02082-27b9-4834-9e79-239af5056771"; :>> title = "Sprint 638 refine gate (DoR)"; :>> createdAt = "2026-09-09"; :>> createdBy = "claudeOpus5"; :>> method = VerificationMethod::inspect; :>> procedureText = "Definition of Ready: dcRoutingVerdictReadsTheWholeTurn at the head of keel whats-next . after f848923; its DoD names the property (the verdict reads the whole turn), the DO (routed / wrong / none over the ordered calls with intake as the recorded prefix, the docstring's citation, the release re-run and its receipt) and the VERIFY (the four transcripts score as named; the re-run's finding line and spend quoted; no rate); one rig script, no fork; 2 points."; }
    // RAN: sprint 638 Refine: validate / check-engine / gate --fast clean on f848923; routing_probe.py --probe all 7 hold; --investigate release --samples 3 -> NOT ROUTING release: 3/3 samples none, prefix intake, spend 3.71 USD 59s wall; issue431/issue432 recorded
    part routingVerdictReadsTheWholeTurnRefineGateR1 : TestResult { :>> id = "2a38a255-6f57-4309-88ba-347eefaedc1a"; :>> outcome = VerdictKind::pass; :>> judgedAgainst = "f848923"; :>> judgedAt = "2026-09-09"; :>> judgedBy = "claudeOpus5"; }
    verification routingVerdictReadsTheWholeTurnStandupGate : Test { :>> id = "4672aaed-f1f4-4da2-bb2f-732912dd0bb4"; :>> title = "Sprint 638 standup gate"; :>> createdAt = "2026-09-09"; :>> createdBy = "claudeOpus5"; :>> method = VerificationMethod::inspect; :>> procedureText = "No blocker. Two points settled at design: a different skill that runs BEFORE the intended one stays wrong even when the intended one follows, because nothing but intake declares a start-of-turn position; and an intake-only turn is none with its prefix shown, not wrong, because the process's first step ran and nothing else did. One defect found while reading the rig: the receipt was unlinked before the estimate read it (issue431), fixed here because it is in the same function."; }
    // RAN: sprint 638 Standup: validate / check-engine / gate --fast clean on f848923; routing_probe.py --probe all 7 hold; --investigate release --samples 3 -> NOT ROUTING release: 3/3 samples none, prefix intake, spend 3.71 USD 59s wall; issue431/issue432 recorded
    part routingVerdictReadsTheWholeTurnStandupGateR1 : TestResult { :>> id = "200c0c7d-7a7f-4fba-a714-0d49e79e1e2f"; :>> outcome = VerdictKind::pass; :>> judgedAgainst = "f848923"; :>> judgedAt = "2026-09-09"; :>> judgedBy = "claudeOpus5"; }
    verification routingVerdictReadsTheWholeTurnImplementGate : Test { :>> id = "c5c7a964-9b0b-469f-867e-3686eadf3503"; :>> title = "Sprint 638 implement gate"; :>> createdAt = "2026-09-09"; :>> createdBy = "claudeOpus5"; :>> method = VerificationMethod::test; :>> procedureText = "routing_probe.py patched through textpatch (patch638.py): DECLARED_PREFIX, short(), score(), probe(); run_one returns the prefix and scores through score(); main gains --probe, runs the probe before an investigation, records and prints the prefix, and unlinks the previous receipt only when a paid run starts. Then the live re-run: 3 samples of release at 3 turns, 59 s wall, $3.71."; }
    // RAN: sprint 638 Implement: validate / check-engine / gate --fast clean on f848923; routing_probe.py --probe all 7 hold; --investigate release --samples 3 -> NOT ROUTING release: 3/3 samples none, prefix intake, spend 3.71 USD 59s wall; issue431/issue432 recorded
    part routingVerdictReadsTheWholeTurnImplementGateR1 : TestResult { :>> id = "470baa38-57a5-4e5f-9d27-8c1cbc4e0642"; :>> outcome = VerdictKind::pass; :>> judgedAgainst = "f848923"; :>> judgedAt = "2026-09-09"; :>> judgedBy = "claudeOpus5"; }
    verification routingVerdictReadsTheWholeTurnReviewGate : Test { :>> id = "b6a7825d-e9d3-4b91-85f4-47f992ab5ab3"; :>> title = "Sprint 638 review gate — three passes per D0172"; :>> createdAt = "2026-09-09"; :>> createdBy = "claudeOpus5"; :>> method = VerificationMethod::inspect; :>> procedureText = "Three passes per D0172: (1) the scorer is probed on the DoD's four transcripts plus the three that separate its clauses before the model is called; (2) the re-run reads under the new rule and its receipt on disk carries the prefix and the full call order per sample; (3) the dry run after the paid run reads the measured cost from the receipt it used to delete, which is issue431's fix observed."; }
    // RAN: sprint 638 Review: validate / check-engine / gate --fast clean on f848923; routing_probe.py --probe all 7 hold; --investigate release --samples 3 -> NOT ROUTING release: 3/3 samples none, prefix intake, spend 3.71 USD 59s wall; issue431/issue432 recorded
    part routingVerdictReadsTheWholeTurnReviewGateR1 : TestResult { :>> id = "6b9f0c27-c946-4bc8-a0d9-ef348b158f0d"; :>> outcome = VerdictKind::pass; :>> judgedAgainst = "f848923"; :>> judgedAt = "2026-09-09"; :>> judgedBy = "claudeOpus5"; }
    verification routingVerdictReadsTheWholeTurnCloseOutGate : Test { :>> id = "2ca93105-a757-4505-aa64-72b020a8759e"; :>> title = "Sprint 638 closeOut gate (autonomous, D0049)"; :>> createdAt = "2026-09-09"; :>> createdBy = "claudeOpus5"; :>> method = VerificationMethod::inspect; :>> procedureText = "keel validate . clean, keel check-engine . clean, keel gate --fast clean; dcRoutingVerdictReadsTheWholeTurnDoD stamped quoting the probe, the finding line and the spend; issue431 and issue432 recorded and triaged."; }
    // RAN: sprint 638 CloseOut: validate / check-engine / gate --fast clean on f848923; routing_probe.py --probe all 7 hold; --investigate release --samples 3 -> NOT ROUTING release: 3/3 samples none, prefix intake, spend 3.71 USD 59s wall; issue431/issue432 recorded
    part routingVerdictReadsTheWholeTurnCloseOutGateR1 : TestResult { :>> id = "d00ca484-98ac-4c86-92eb-03e57d170ebc"; :>> outcome = VerdictKind::pass; :>> judgedAgainst = "f848923"; :>> judgedAt = "2026-09-09"; :>> judgedBy = "claudeOpus5"; }
    verification routingVerdictReadsTheWholeTurnRetroGate : Test { :>> id = "10d83d4a-beb1-40b7-bc20-c9787d1f30d7"; :>> title = "Sprint 638 retro gate (autonomous, D0049)"; :>> createdAt = "2026-09-09"; :>> createdBy = "claudeOpus5"; :>> method = VerificationMethod::analyze; :>> procedureText = "Avoidable-issue scan: the re-run was unanimous and still could not answer the question, because the budget the samples ran under was set when the first Skill call was the whole verdict; under a whole-turn rule the declared prefix eats it. That is tracked as issue432 with resolver dcPrefixLeavesRoomForTheRoute, and the $3.71 it cost is the price of reading it from samples rather than guessing. The rig's estimate was off by 2.4x because it had been quoting a constant since 2026-09-06 - issue431, fixed here and resolved through dcRoutingVerdictReadsTheWholeTurn. No new item beyond issue432."; }
    // RAN: sprint 638 Retro: validate / check-engine / gate --fast clean on f848923; routing_probe.py --probe all 7 hold; --investigate release --samples 3 -> NOT ROUTING release: 3/3 samples none, prefix intake, spend 3.71 USD 59s wall; issue431/issue432 recorded
    part routingVerdictReadsTheWholeTurnRetroGateR1 : TestResult { :>> id = "bc2e2e27-e242-4cba-9340-556620634a40"; :>> outcome = VerdictKind::pass; :>> judgedAgainst = "f848923"; :>> judgedAt = "2026-09-09"; :>> judgedBy = "claudeOpus5"; }
}
