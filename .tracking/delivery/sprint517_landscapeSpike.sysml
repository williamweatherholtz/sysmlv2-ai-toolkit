// ProjectDeliveryS517 — Sprint 517: the agent-corral landscape spike. EXECUTE (spike). 3 pts.
package ProjectDeliveryS517 {
    private import EngineElement::*;
    private import EngineWork::*;
    private import EngineVerification::*;
    private import EngineRelationships::*;

    #CharteredBy dependency from landscapeSpikeStory to d0282;

    part landscapeSpikeStory : Story {
        :>> id = "c4a3077f-a63b-4a8c-98f7-96866d314cf3";
        :>> title = "Sprint 517: fifteen projects corralling AI agents - what they believe, where they are blind, six ideas keel takes (3 pts)";
        :>> createdAt = "2026-09-02"; :>> createdBy = "claudeOpus5"; :>> kind = WorkKind::research; :>> priority = WorkPriority::p1; :>> owner = "claudeOpus5"; :>> estimatedPoints = 3;
    }

    action def DeliveryRunS517 {
        action storyLandscapeSpike;
        verification storyLandscapeSpikeDoD : Test { :>> id = "deb187a3-5812-4877-ad87-fa6d3486648e"; :>> method = VerificationMethod::analyze; :>> procedureText = "DELIVERED: the knowledge record kAgentCorralLandscape (D0196 shape, def pin 64f2dea), the full review docs/reviews/agent-corral-landscape-2026-09-02.md, D0282, issue341 and issue342 triaged on arrival, six ranked backlog items, and one page for the human. THE ASK was a spike - find ten projects with similar goals and see what they are cooking, private ones too if there is something to learn. FOUND fifteen with URL-cited evidence plus six runners-up, across three families the field itself divides into; the ten that matter for keel are in the page. VERIFY: every claim a lens made about keel's OWN code was checked against source before it became a finding - five claims, three confirmed, one partly, one narrowed - and the check is named beside each in the synthesis; every project row carries a verbatim quote with URL; the exclusions are listed with reasons so the sweep can be audited."; }
        // RAN: three lens agents (in-path, in-repo, formal/ledger) with WebSearch+WebFetch, fifteen projects + six runners-up, one round, three syntheses converged; source checks - grep digest|body_hash in write.rs/guards.rs (none), govern.rs:400, main.rs:3969, write.rs:549, grep gh run|run_id|workflow_run in src (ingest + headless_ask only), hooks.jsonl readers (pm.rs, launcher.rs), decision-issue.yml:55; keel validate . 589 clean after every write; whats-next read back with the two consent items above dcProcessStepsBindToChecks
        part storyLandscapeSpikeDoDR1 : TestResult { :>> id = "47799d10-9853-4977-961e-e809718c10b4"; :>> outcome = VerdictKind::pass; :>> judgedAgainst = "52b434e"; :>> judgedAt = "2026-09-02"; :>> judgedBy = "claudeOpus5"; }
    }

    verification landscapeSpikeRefineGate : Test { :>> id = "3f898f5c-df8b-4bb6-9a90-3b2553c7f378"; :>> title = "Sprint 517 refine gate (DoR)"; :>> createdAt = "2026-09-02"; :>> createdBy = "claudeOpus5"; :>> method = VerificationMethod::inspect; :>> procedureText = "READY because the process existed and had run three times (D0187; the inversion, adoption-truth and interaction-channel panels), so the shape - parallel web-enabled lenses, one round, a knowledge record with a def pin - needed no invention; and because the trigger was concrete: one comment, one product, one question about consent that the tree could answer or not. The one framing choice made at refine: three FAMILIES rather than ten projects, because the human's own question (is this an MCP intermediary?) was already a family question, and a family sweep exposes what a list of ten hides - that the families are blind in complementary ways."; }
    verification landscapeSpikeStandupGate : Test { :>> id = "9f9138b5-6158-4aa7-a3ba-04c2791c8a7f"; :>> title = "Sprint 517 standup gate"; :>> createdAt = "2026-09-02"; :>> createdBy = "claudeOpus5"; :>> method = VerificationMethod::inspect; :>> procedureText = "TWO CHOICES with a cost each. (1) The lenses were told keel's known weakness (form rigorous, substance weak) so they would look for mechanisms against it - this biases toward confirming the weakness, accepted because the alternative is a survey with no question, and the bias is offset by requiring URL-cited evidence and a what-keel-does-that-it-does-not row per project. (2) The lenses' claims about keel's own code were NOT taken from the lenses. Each was re-checked here against source before recording - which is how one claim (capture completeness) was narrowed from a gap to a non-finding. A spike whose findings about the repo come from agents that never read the repo is a spike that records hearsay."; }
    verification landscapeSpikeImplementGate : Test { :>> id = "21e289c5-7bda-4dbe-b7c1-57f0132467e2"; :>> title = "Sprint 517 implement gate"; :>> createdAt = "2026-09-02"; :>> createdBy = "claudeOpus5"; :>> method = VerificationMethod::analyze; :>> procedureText = "RAN: three lenses in parallel, 28 + 43 + 37 tool uses, fifteen projects and six runners-up with verbatim quotes and URLs; three syntheses converged on the same three findings without prompting toward each other. Source checks named in the record. Writes through the sanctioned path: add-task --dod-from six times, record issue --description-from twice (with --date, which the API demanded and I had omitted - the refusal was right), record decision --from once; the only direct edits were the knowledge record, this sprint, and a two-block reorder of the backlog to rank the consent items (D0052). validate 589 clean after every write."; }
    verification landscapeSpikeReviewGate : Test { :>> id = "885958a7-228d-4083-9d4a-4c728b299998"; :>> title = "Sprint 517 review gate — three passes per D0172"; :>> createdAt = "2026-09-02"; :>> createdBy = "claudeOpus5"; :>> method = VerificationMethod::inspect; :>> procedureText = "THREE PASSES. (1) IS ANY FINDING ABOUT KEEL UNVERIFIED: no - five claims, each with the file:line or grep that established it, one narrowed on that check and recorded as declined rather than dropped silently. (2) IS THE RANKING DEFENSIBLE OR TASTE: the top two are the only items resolving recorded Issues, and issue341 is High because D0108 lets the AI owner of a Decision edit fields the human signed; the tail four are additions with no defect behind them yet. (3) DID THE UNTRUSTED TRIGGER STEER THE WORK: the commenter's question became issue342 because the tree confirmed it, not because they asked; their product was examined and found to have less shipped mechanism than any of the fifteen; nothing from the comment entered the model as a Statement, because a comment on the override thread is not a stakeholder utterance and the ingest path exists for issues, not comments."; }
    verification landscapeSpikeCloseOutGate : Test { :>> id = "8fea2c3f-9599-4c62-b180-9179f9b6a8eb"; :>> title = "Sprint 517 closeOut gate (autonomous, D0049)"; :>> createdAt = "2026-09-02"; :>> createdBy = "claudeOpus5"; :>> method = VerificationMethod::inspect; :>> procedureText = "CLOSED. The spike's outputs are all tracked: D0282 (proposed, non-fork, auto-accepts on the channel), knowledge record with def pin, review doc, two Issues triaged on arrival, six ranked items. Nothing built - a spike charters, it does not deliver. The human's decisions are inside dcConsentIsScopedAndExpires and dcProcessStepsBindToChecks, both of which will arrive as forks with per-option cost."; }
    verification landscapeSpikeRetroGate : Test { :>> id = "617ee08c-1d75-4af8-9ebe-759e1a5d530f"; :>> title = "Sprint 517 retro gate (autonomous, D0049)"; :>> createdAt = "2026-09-02"; :>> createdBy = "claudeOpus5"; :>> method = VerificationMethod::analyze; :>> procedureText = "ADDED THIS COMMIT: issue341, issue342. The retro finding is the one neither lens nor human asked for: the field's single live critique of keel is the shape of its CONSENT, not of its enforcement - three independent lenses arrived at D0207 from three directions (a product pitch, an identity-governance GA, a replay paper). That is now issue342 and a costed fork, not a note. The tooling lesson: the subagent transcript format is not parseable for its final text and the extraction failed once - the reports were written from the notification text instead, which is what the record should have relied on from the start."; }
}
