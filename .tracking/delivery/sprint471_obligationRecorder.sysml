// ProjectDeliveryS471 - Sprint 471: the recorder that could not record without breaking the tree it reports on. EXECUTE. 1 pt.
package ProjectDeliveryS471 {
    private import EngineElement::*;
    private import EngineWork::*;
    private import EngineVerification::*;
    private import EngineRelationships::*;

    // D0176 defined the obligation record (write-API-only with recorded overrides); this sprint
    // makes the recorder able to write one without invalidating the tree it reports on.
    #CharteredBy dependency from obligationRecorderStory to d0176;

    part obligationRecorderStory : Story {
        :>> id = "c75802a6-83ad-4865-9b55-08088c52e4bf";
        :>> title = "Sprint 471: recording an obligation keeps the tree valid, and a test holds the property instead of a hand-repair (1 pt)";
        :>> createdAt = "2026-08-27"; :>> createdBy = "claudeOpus5"; :>> kind = WorkKind::code; :>> priority = WorkPriority::p1; :>> owner = "claudeOpus5"; :>> estimatedPoints = 1;
    }

    action def DeliveryRunS471 {
        action storyObligationRecorder;
        verification storyObligationRecorderDoD : Test { :>> id = "50167572-19dc-4a78-9321-b1ee43b8c2f1"; :>> method = VerificationMethod::test; :>> procedureText = "DELIVERED: dcObligationRecorderValidates (issue274). The obligation template carries EngineWork and EngineRelationships alongside EngineElement, so a recorded obligation no longer leaves an unresolved type reference to Issue. The half that was missing is the VERIFICATION: init_smoke's recording_an_obligation_keeps_the_tree_valid scaffolds a real project, records an obligation through the same library entry point the hooks call, and asserts validate stays clean. An assertion about which imports the template contains would pass just as well on a template whose imports are wrong for the next type the record grows, so the control is the RECORDING. The hand-repaired instance on disk keeps its added import and its comment now states what IS - the property is held by the test, not by the repair."; }
    // RAN: cargo test --release --test init_smoke => 2 passed 0 failed, incl the new recording_an_obligation_keeps_the_tree_valid; with the template's EngineWork import removed the same test FAILED with "recording an obligation invalidated the tree: ERROR ... override-58a0b47d.sysml:8 - unresolved type reference `Issue`", reproducing issue274's exact diagnostic, and passed again once restored; keel validate . => 526 tracking files clean.
        part storyObligationRecorderDoDR1 : TestResult { :>> id = "c2f393e4-2153-4272-9740-d8b9ee0112bf"; :>> outcome = VerdictKind::pass; :>> judgedAgainst = "e7d2683"; :>> judgedAt = "2026-08-27"; :>> judgedBy = "claudeOpus5"; }
    }

    verification obligationRecorderRefineGate : Test { :>> id = "cfb082c5-c99a-486b-8b1e-9fac26f12e0f"; :>> title = "Sprint 471 refine gate (DoR)"; :>> createdAt = "2026-08-27"; :>> createdBy = "claudeOpus5"; :>> method = VerificationMethod::inspect; :>> procedureText = "DoR: dcObligationRecorderValidates was ranked FIRST on the frontier after sprint 470 closed, so it was taken next per D0052. Found on inspection that the DO half - the template imports - had already landed in an earlier commit while the DoD's VERIFY half had not, which is why the item was still open. Resolver: dcObligationRecorderValidates. estimatedPoints=1."; }
    part obligationRecorderRefineGateR1 : TestResult { :>> id = "7b2c0f81-d527-427d-baa7-cedfc0902393"; :>> outcome = VerdictKind::pass; :>> judgedAgainst = "e7d2683"; :>> judgedAt = "2026-08-27"; :>> judgedBy = "claudeOpus5"; }
    verification obligationRecorderStandupGate : Test { :>> id = "d4495481-2940-40f5-b08f-a2bbd1660405"; :>> title = "Sprint 471 standup gate"; :>> createdAt = "2026-08-27"; :>> createdBy = "claudeOpus5"; :>> method = VerificationMethod::inspect; :>> procedureText = "Approach: add the control to init_smoke, which already owns the scaffold machinery, and drive record_obligation through the library rather than a CLI surface - there is no `keel record obligation` command, because the recorder is invoked by the hooks. Then disable-and-rerun to confirm the control is not hollow. No process-def, schema, or enforcement-surface change."; }
    part obligationRecorderStandupGateR1 : TestResult { :>> id = "4eb503e0-18b1-4f11-8739-9734ddd03ffb"; :>> outcome = VerdictKind::pass; :>> judgedAgainst = "e7d2683"; :>> judgedAt = "2026-08-27"; :>> judgedBy = "claudeOpus5"; }
    verification obligationRecorderImplementGate : Test { :>> id = "053ae2a3-f3db-4db6-8ab1-cc90bfc4bd8d"; :>> title = "Sprint 471 implement gate"; :>> createdAt = "2026-08-27"; :>> createdBy = "claudeOpus5"; :>> method = VerificationMethod::test; :>> procedureText = "Implemented the test; ran the disable-and-rerun proof. Also corrected the stale comment on the on-disk obligation instance, which still said in the present tense that the template omits the import - a claim the same commit makes false."; }
    // RAN: cargo test --release --test init_smoke => 2 passed 0 failed, incl the new recording_an_obligation_keeps_the_tree_valid; with the template's EngineWork import removed the same test FAILED with "recording an obligation invalidated the tree: ERROR ... override-58a0b47d.sysml:8 - unresolved type reference `Issue`", reproducing issue274's exact diagnostic, and passed again once restored; keel validate . => 526 tracking files clean.
    part obligationRecorderImplementGateR1 : TestResult { :>> id = "d17e0f43-c09a-4085-9aea-f7462a32a759"; :>> outcome = VerdictKind::pass; :>> judgedAgainst = "e7d2683"; :>> judgedAt = "2026-08-27"; :>> judgedBy = "claudeOpus5"; }
    verification obligationRecorderReviewGate : Test { :>> id = "8ce0e137-9229-4d67-b5af-7606a7d7c801"; :>> title = "Sprint 471 review gate"; :>> createdAt = "2026-08-27"; :>> createdBy = "claudeOpus5"; :>> method = VerificationMethod::inspect; :>> procedureText = "Diff reviewed. Two tests now cover the fresh-scaffold surface and BOTH were proven by disabling the code they guard: the issue291 namespace transform and this template. That pairing is the answer to the shape both sprint 104 and sprint 115 got wrong - they asserted the scaffold and never the scaffold plus an authored fact. Clean."; }
    part obligationRecorderReviewGateR1 : TestResult { :>> id = "f703a854-021d-4a47-8cdf-72502c34ae63"; :>> outcome = VerdictKind::pass; :>> judgedAgainst = "e7d2683"; :>> judgedAt = "2026-08-27"; :>> judgedBy = "claudeOpus5"; }
    verification obligationRecorderCloseOutGate : Test { :>> id = "78172f81-4d1c-4087-8aff-d26f24c0af48"; :>> title = "Sprint 471 closeOut gate (autonomous, D0049)"; :>> createdAt = "2026-08-27"; :>> createdBy = "claudeOpus5"; :>> method = VerificationMethod::inspect; :>> procedureText = "Autonomous closeOut (D0049): DoD recorded pass with its RAN receipt; the frontier was read back from keel whats-next. Self-evidencing (D0051): no human confirmation is claimed."; }
    part obligationRecorderCloseOutGateR1 : TestResult { :>> id = "325075f2-c661-4e63-b93b-8d11721bf16c"; :>> outcome = VerdictKind::pass; :>> judgedAgainst = "e7d2683"; :>> judgedAt = "2026-08-27"; :>> judgedBy = "claudeOpus5"; }
    verification obligationRecorderRetroGate : Test { :>> id = "8f6ac7b2-84ba-4486-892d-a01f6c8c8341"; :>> title = "Sprint 471 retro gate (autonomous, D0049)"; :>> createdAt = "2026-08-27"; :>> createdBy = "claudeOpus5"; :>> method = VerificationMethod::analyze; :>> procedureText = "Autonomous retro (D0049). WELL: the disable-and-rerun step is now applied to every control this session ships, and it earned its keep twice - both controls reproduced their original defect's exact diagnostic when the fix was stubbed out, which is the only evidence that distinguishes a control from a test that happens to pass. FINDING: this item sat on the frontier with its DO half already landed and its VERIFY half not, and nothing surfaced that split - the item simply read as not done. A partially-delivered item is indistinguishable from an untouched one on the frontier today. AVOIDABLE-ISSUE SCAN: the hand-repair comment asserting a present-tense defect outlived the defect by one commit; the same class as sprint 104's header claim corrected in sprint 470, and the second instance found in two sprints. Candidate forward control, stated not built: a check that a comment naming a defect as present has a matching open Issue. Estimate 1 pt held."; }
    part obligationRecorderRetroGateR1 : TestResult { :>> id = "2ce36255-1838-480b-9361-9a5fafed54d9"; :>> outcome = VerdictKind::pass; :>> judgedAgainst = "e7d2683"; :>> judgedAt = "2026-08-27"; :>> judgedBy = "claudeOpus5"; }
}
