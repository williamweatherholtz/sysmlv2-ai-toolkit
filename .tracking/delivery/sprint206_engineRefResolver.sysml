// ProjectDeliveryS206 — Sprint 206: engineRefResolver (D0112 phase 2, resolves issue067) — `keel
// check-engine`: kernel-free semantic reference-resolution for .engine instances, wired as the
// SKIP_VALIDATE-proof backstop (hook + CI). CHANGE (new subcommand + CI/hook) governed by D0112. 2 pt.
// AUTONOMOUS (D0049).
package ProjectDeliveryS206 {
    private import EngineElement::*;
    private import EngineWork::*;
    private import EngineVerification::*;
    private import EngineRequirements::*;
    private import EngineRelationships::*;

    #CharteredBy dependency from engineRefResolverStory to d0112;

    part engineRefResolverStory : Story {
        :>> id = "63940516-2c7d-4e8f-c206-51627384c001";
        :>> title = "Sprint 206: engineRefResolver (2 pt) - keel check-engine, kernel-free .engine ref-resolution + SKIP_VALIDATE-proof CI backstop (D0112 phase 2/issue067)";
        :>> createdAt = "2026-07-14"; :>> createdBy = "wweatherholtz"; :>> kind = WorkKind::code; :>> priority = WorkPriority::p2; :>> owner = "claudeOpus"; :>> estimatedPoints = 2;
    }

    action def DeliveryRunS206 {
        action storyEngineRefResolver;
        verification storyEngineRefResolverDoD : Test { :>> id = "63940516-2c7d-4e8f-c206-51627384c002"; :>> method = VerificationMethod::test; :>> procedureText = "Delivers D0112 phase 2 (accepted) + resolves issue067 (SKIP_VALIDATE has no kernel backstop). `keel check-engine` (lib::validate_engine_instances) registers ALL .engine packages then runs the SAME PackageRegistry::validate used for .tracking against the .engine INSTANCE files — KERNEL-FREE — catching unresolved type references + unknown import namespaces (the Rust registers all first, so cross-file refs resolve, the advantage over the per-file kernel). Wired as the SKIP_VALIDATE-proof backstop: ci.yml now runs keel validate + guard + check-engine (Rust-only CI catches a hook-skipped commit); .githooks/pre-commit runs check-engine locally (kernel-free). SCOPE: name/type EXISTENCE, not full type-conformance (kernel residual, phase 3 — kernel NOT removed). VERIFIED: check-engine clean on the live repo (0 false positives — no valid .engine file mis-flagged); a synthetic broken probe flagged BOTH `unknown import namespace NonexistentPackage` + `unresolved type reference TotallyMadeUpType`; is_engine_instance_file unit test; clippy --workspace --all-targets clean; cargo test (82) green; keel validate + guard green; doc-sync CLAUDE.md §5."; }
        part storyEngineRefResolverDoDR1 : TestResult { :>> id = "63940516-2c7d-4e8f-c206-51627384c003"; :>> outcome = VerdictKind::pass; :>> judgedAgainst = "0c9985a"; :>> judgedAt = "2026-07-14"; :>> judgedBy = "claudeOpus"; }
    }

    #Verify dependency from storyEngineRefResolverDoD to d0112;

    verification errRefineGate : Test { :>> id = "63940516-2c7d-4e8f-c206-51627384c004"; :>> title = "Sprint 206 refine gate (DoR)"; :>> createdAt = "2026-07-14"; :>> createdBy = "claudeOpus"; :>> method = VerificationMethod::inspect; :>> procedureText = "DoR: D0112 accepted; phase 2 = the .engine reference resolver, which the investigation showed is a SMALL reuse (PackageRegistry::validate already exists + validates .tracking; just point it at .engine instances). Resolves issue067. CHANGE (new subcommand + CI/hook) governed by D0112 #ProspectiveChange. estimatedPoints=2. #CharteredBy d0112. DoR met."; }
    part errRefineGateR1 : TestResult { :>> id = "63940516-2c7d-4e8f-c206-51627384c005"; :>> outcome = VerdictKind::pass; :>> judgedAgainst = "0c9985a"; :>> judgedAt = "2026-07-14"; :>> judgedBy = "claudeOpus"; }
    verification errStandupGate : Test { :>> id = "63940516-2c7d-4e8f-c206-51627384c006"; :>> title = "Sprint 206 standup gate"; :>> createdAt = "2026-07-14"; :>> createdBy = "claudeOpus"; :>> method = VerificationMethod::inspect; :>> procedureText = "Approach: validate_engine_instances (register all .engine, validate instance files via PackageRegistry::validate) + `keel check-engine` subcommand; wire into ci.yml + pre-commit; test false-positive-free live + prove the catch path with a probe. No blockers."; }
    part errStandupGateR1 : TestResult { :>> id = "63940516-2c7d-4e8f-c206-51627384c007"; :>> outcome = VerdictKind::pass; :>> judgedAgainst = "0c9985a"; :>> judgedAt = "2026-07-14"; :>> judgedBy = "claudeOpus"; }
    verification errImplementGate : Test { :>> id = "63940516-2c7d-4e8f-c206-51627384c008"; :>> title = "Sprint 206 implement gate"; :>> createdAt = "2026-07-14"; :>> createdBy = "claudeOpus"; :>> method = VerificationMethod::test; :>> procedureText = "check-engine + CI/hook wiring + test landed. Live repo clean (0 false positives); probe flags import + type-ref errors; clippy --workspace --all-targets clean; cargo test (82) green; keel validate + guard + check-engine green."; }
    part errImplementGateR1 : TestResult { :>> id = "63940516-2c7d-4e8f-c206-51627384c009"; :>> outcome = VerdictKind::pass; :>> judgedAgainst = "0c9985a"; :>> judgedAt = "2026-07-14"; :>> judgedBy = "claudeOpus"; }
    verification errReviewGate : Test { :>> id = "63940516-2c7d-4e8f-c206-51627384c00a"; :>> title = "Sprint 206 review gate"; :>> createdAt = "2026-07-14"; :>> createdBy = "claudeOpus"; :>> method = VerificationMethod::inspect; :>> procedureText = "Reviewed. Strong phase-2: the investigation found the resolver is a REUSE (PackageRegistry::validate already resolves references for .tracking) rather than a from-scratch SysML checker, so it's low-risk — and the false-positive question (the real risk) was settled empirically (live repo clean) plus a catch-path probe. Wiring it into CI is the actual fix for issue067: kernel-free Rust runs in the Rust-only CI, so SKIP_VALIDATE can no longer land an unresolved-ref .engine change undetected. Honest scope: name/type existence only; the kernel keeps the deep type-conformance residual (phase 3). Clean."; }
    part errReviewGateR1 : TestResult { :>> id = "63940516-2c7d-4e8f-c206-51627384c00b"; :>> outcome = VerdictKind::pass; :>> judgedAgainst = "0c9985a"; :>> judgedAt = "2026-07-14"; :>> judgedBy = "claudeOpus"; }
    verification errCloseOutGate : Test { :>> id = "63940516-2c7d-4e8f-c206-51627384c00c"; :>> title = "Sprint 206 closeOut gate (autonomous, D0049)"; :>> createdAt = "2026-07-14"; :>> createdBy = "claudeOpus"; :>> method = VerificationMethod::inspect; :>> procedureText = "Autonomous closeOut (D0049): DoD pass; issue067 resolved (engineRefResolver done). keel validate + guard + check-engine green; the kernel-free .engine ref-check now runs in the hook + CI. Self-evidencing (D0051). NEXT (D0112 phase 3, separately chartered): assess whether the kernel's remaining type-conformance residual catches anything real — if not, retire the kernel. Open frontier now only issue061 (needs a real design session)."; }
    part errCloseOutGateR1 : TestResult { :>> id = "63940516-2c7d-4e8f-c206-51627384c00d"; :>> outcome = VerdictKind::pass; :>> judgedAgainst = "0c9985a"; :>> judgedAt = "2026-07-14"; :>> judgedBy = "claudeOpus"; }
    verification errRetroGate : Test { :>> id = "63940516-2c7d-4e8f-c206-51627384c00e"; :>> title = "Sprint 206 retro gate (autonomous, D0049)"; :>> createdAt = "2026-07-14"; :>> createdBy = "claudeOpus"; :>> method = VerificationMethod::analyze; :>> procedureText = "Autonomous retro (D0049). WELL: investigate-before-implement paid off AGAIN — the phase-2 resolver turned out to be a REUSE of existing, already-tested machinery (PackageRegistry::validate) rather than a risky SysML-semantics rewrite, so a scary-sounding item became small + safe. The false-positive risk (the one real hazard) was retired empirically (live-clean + probe) BEFORE wiring. Wiring into the Rust-only CI is what actually closes issue067's SKIP_VALIDATE hole. This session I also learned (the hard way, a642269) to run the AUTHORITATIVE clippy (--workspace --all-targets) — did that here first, clean. AVOIDABLE-ISSUE SCAN: none new. Estimate 2 pt held. NEXT: only issue061 remains (real design session needed); D0112 phase 3 is optional/measured."; }
    part errRetroGateR1 : TestResult { :>> id = "63940516-2c7d-4e8f-c206-51627384c00f"; :>> outcome = VerdictKind::pass; :>> judgedAgainst = "0c9985a"; :>> judgedAt = "2026-07-14"; :>> judgedBy = "claudeOpus"; }
}
