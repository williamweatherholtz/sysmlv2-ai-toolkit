// ProjectDeliveryS691 — Sprint 691: Work dcDominanceRechosenUnderItsOwnRule (issue430): sweep DOMINANCE over both bench arms on one tree, apply D0364's rule to the verdict lines, and record what falls out. What fell out is the DoD's third branch - the rule itself is what has to move, or the hand-set bar does - so the sprint's deliverable is the measurement and a fork Decision (D0464) for the human, not a changed constant. EXECUTE; the constant is unchanged.. EXECUTE. 2 pts.
package ProjectDeliveryS691 {
    private import EngineElement::*;
    private import EngineWork::*;
    private import EngineVerification::*;
    private import EngineRelationships::*;

    #CharteredBy dependency from dominanceRuleOrDominanceBarStory to d0464;

    part dominanceRuleOrDominanceBarStory : Story {
        :>> id = "cf13aba7-a37f-4fb9-a9ff-57af448f8fc4";
        :>> title = "Sprint 691: Work dcDominanceRechosenUnderItsOwnRule (issue430): sweep DOMINANCE over both bench arms on one tree, apply D0364's rule to the verdict lines, and record what falls out. What fell out is the DoD's third branch - the rule itself is what has to move, or the hand-set bar does - so the sprint's deliverable is the measurement and a fork Decision (D0464) for the human, not a changed constant. EXECUTE; the constant is unchanged. (2 pts)";
        :>> createdAt = "2026-09-13"; :>> createdBy = "claudeFable5"; :>> kind = WorkKind::code; :>> priority = WorkPriority::p0; :>> owner = "claudeFable5"; :>> estimatedPoints = 2;
    }

    action def DeliveryRunS691 {
        action storyDominanceRuleOrDominanceBar;
        verification storyDominanceRuleOrDominanceBarDoD : Test { :>> id = "43847c9f-543f-4158-8584-d3a0fe69955c"; :>> method = VerificationMethod::test; :>> procedureText = "DELIVERED: eight DOMINANCE settings (0, 1.1, 1.25, 1.3, 1.35, 1.4, 1.45, 1.5) swept on the one-hop and two-hop arms of recall_bench.py against the tree at 33c398a, plus the bench's own tie line for 0 against 1.5 on both arms (COULD NOT CHOOSE, no case's outcome changed), plus the hand set (recall_ab.py) read afterwards at 1.5, 1.25 and 0. D0364's rule applied: every setting that buys a two-hop hit (1.1 through 1.45) moves the one-hop median 2 to 3 or 4 and is refused; the admissible settings 0 and 1.5 tie at 20/50 and the mechanism buys nothing under them; the hand set's bar is MET at 1.25 only (7/7 reachable) and NOT MET at both admissible settings (6/7). D0464 records the fork - OPTION A rule stands, DOMINANCE 1.5, the bar fails honestly; OPTION B the rule gains a weight and 1.25 stands - with every number and both verdict lines in its research line, held proposed, DependsOn D0364 and D0365. dcDominanceRechosenUnderItsOwnRule carries no result: its DoD says the choice is recorded, and the choice is the human's. A DOMINANCE=1.5 edit to knowledge.rs was made, verified (knowledge tests 8 passed, plain runs printed the tie's numbers) and REVERTED once the hand set read 6/7, because changing the constant would foreclose the fork."; }
        // RAN: RAN: recall_bench.py --sweep DOMINANCE=0,1.1,1.25,1.5 / 0,1.3,1.35,1.4 / 0,1.45 / 0,1.5 on both arms at 33c398a (logs s691/sweep_*.log, mid_*.log, tie_*.log); plain runs -> md 2 top-3 28/45 and md 5 top-3 2/20; recall_ab.py at 1.5 -> 6/7 NOT MET, at 1.25 -> 7/7 MET; keel record decision -> D0464 proposed FORK
        part storyDominanceRuleOrDominanceBarDoDR1 : TestResult { :>> id = "e0ef3fbc-1c1e-4e21-ba1c-981fd9ee9abf"; :>> outcome = VerdictKind::pass; :>> judgedAgainst = "33c398a"; :>> judgedAt = "2026-09-13"; :>> judgedBy = "claudeFable5"; }
    }

    verification dominanceRuleOrDominanceBarRefineGate : Test { :>> id = "2854253d-df19-4a03-82a7-28fd63a82a5b"; :>> title = "Sprint 691 refine gate (DoR)"; :>> createdAt = "2026-09-13"; :>> createdBy = "claudeFable5"; :>> method = VerificationMethod::inspect; :>> procedureText = "Chartered by D0464. Two points: eleven bench runs of about a minute each, one Decision, no code change kept. DoR: the DoD is on the backlog item (dcDominanceRechosenUnderItsOwnRuleDoD, method test) and names all three branches; issue430 carries #Resolves from it; recall_bench.py --sweep and recall_ab.py exist and probe green (D0388 pair, 6 cases hold). NOT A FORK here: the sprint records a fork, it does not take one; the fork is D0464's."; }
    // RAN: AI-examined inspect/analyze pass (D0312 B); sprint file section holds the examination
    part dominanceRuleOrDominanceBarRefineGateR1 : TestResult { :>> id = "931538d5-478d-4172-9a5f-b87c89fd32e1"; :>> outcome = VerdictKind::proposed; :>> judgedAgainst = "33c398a"; :>> judgedAt = "2026-09-13"; :>> judgedBy = "claudeFable5"; }
    verification dominanceRuleOrDominanceBarStandupGate : Test { :>> id = "09c72418-1b31-4179-ab96-5b19676812cc"; :>> title = "Sprint 691 standup gate"; :>> createdAt = "2026-09-13"; :>> createdBy = "claudeFable5"; :>> method = VerificationMethod::inspect; :>> procedureText = "Order: run the four-setting sweep on both arms against keel-serve.exe (the build at 860c078, knowledge.rs unchanged since D0365) with KEEL_BENCH_BIN so the bench names its binary; read the rule against the lines; sweep the unmeasured interval 1.3 to 1.4, then 1.45; get the tie between 0 and 1.5 as the bench's own verdict line rather than two equal summaries; locate the clause that took 1.25 (D0365's decision clause, not D0364's - the DoD mis-cites it); check knowledge.rs is outside the keystone lock (guards.rs is_enforcement_surface: guard source, hooks, CI yml only); edit the constant, clippy, knowledge tests, rebuild, refresh keel-serve.exe; VERIFY the plain runs against the tie's numbers; read the hand set afterwards; on 6/7 revert the constant and write the fork; record D0464 held with DependsOn edges; record the sprint; decision-surfacing; commit detached."; }
    // RAN: AI-examined inspect/analyze pass (D0312 B); sprint file section holds the examination
    part dominanceRuleOrDominanceBarStandupGateR1 : TestResult { :>> id = "d0740fa4-2838-449b-81ba-26711922c5e4"; :>> outcome = VerdictKind::proposed; :>> judgedAgainst = "33c398a"; :>> judgedAt = "2026-09-13"; :>> judgedBy = "claudeFable5"; }
    verification dominanceRuleOrDominanceBarImplementGate : Test { :>> id = "9341c0c0-06be-45e6-ac24-a517981e5856"; :>> title = "Sprint 691 implement gate"; :>> createdAt = "2026-09-13"; :>> createdBy = "claudeFable5"; :>> method = VerificationMethod::test; :>> procedureText = "No code change kept: git checkout -- keel-cli/src/view/knowledge.rs after the hand-set reading; git status --short shows only .engine/decisions/0464-dominanceRuleOrDominanceBar.sysml and this sprint. RAN: python .engine/tools/recall_bench.py --sweep DOMINANCE=0,1.1,1.25,1.5 -> one-hop 45/50 md 2/4/3/2 top-3 28/21/27/28, DISCRIMINATED median position moved; --hops 2 same sweep -> 20/24/23/20 md 5/3/4/5, DISCRIMINATED hits and median position moved; --sweep DOMINANCE=0,1.3,1.35,1.4 -> one-hop 45 md 2/3/3/3, two-hop 20/23/22/21 md 5/4/5/5; --sweep DOMINANCE=0,1.45 -> one-hop 45 md 2/3, two-hop 20/21 md 5/5; --sweep DOMINANCE=0,1.5 both arms -> COULD NOT CHOOSE, no case's outcome changed at any value; plain default run at build 33c398a -> median 2, top-3 in 28/45; plain --hops 2 -> median 5, top-3 in 2/20; recall_ab.py at 1.5 -> injection ON 6/8, bar NOT MET (6/7); KEEL_RECALL_DOMINANCE=1.25 -> 7/8, bar MET (7/7), d0129 at position 8 on the rebase question; KEEL_RECALL_DOMINANCE=0 -> 6/8, NOT MET. cargo clippy --workspace --all-targets -- -D warnings -> Finished and cargo test --release --lib -- knowledge -> 8 passed on the 1.5 edit before it was reverted. keel record decision --from d0464.md -> recorded D0464 (proposed), a FORK (carries options)."; }
    // RAN: RAN: recall_bench.py --sweep DOMINANCE=0,1.1,1.25,1.5 / 0,1.3,1.35,1.4 / 0,1.45 / 0,1.5 on both arms at 33c398a (logs s691/sweep_*.log, mid_*.log, tie_*.log); plain runs -> md 2 top-3 28/45 and md 5 top-3 2/20; recall_ab.py at 1.5 -> 6/7 NOT MET, at 1.25 -> 7/7 MET; keel record decision -> D0464 proposed FORK
    part dominanceRuleOrDominanceBarImplementGateR1 : TestResult { :>> id = "2f63ff55-e34b-4489-995f-0bfaa83a5fab"; :>> outcome = VerdictKind::pass; :>> judgedAgainst = "33c398a"; :>> judgedAt = "2026-09-13"; :>> judgedBy = "claudeFable5"; }
    verification dominanceRuleOrDominanceBarReviewGate : Test { :>> id = "c5a4574e-3308-475c-a801-875659f13b1c"; :>> title = "Sprint 691 review gate — three passes per D0172"; :>> createdAt = "2026-09-13"; :>> createdBy = "claudeFable5"; :>> method = VerificationMethod::inspect; :>> procedureText = "Three passes (D0172). Correctness: every number in D0464's research line is copied from a bench log written by the run that produced it, and the verdict lines are verbatim; the eleven runs read one tree (33c398a, no .tracking or .engine edit between the first sweep and the last hand-set read, D0464 recorded after); the binary changed once between runs (860c078 build to 33c398a build) and knowledge.rs is byte-identical across that change, which the plain runs' agreement with the earlier sweep confirms. Honesty: the sprint claims a measurement and a fork, not a resolution - issue430 stays open, dcDominanceRechosenUnderItsOwnRule has no result; the 1.5 edit's existence and reversal are stated, not omitted. Scope: D0364's rule and D0365's setting are not edited; the DoD's mis-citation of D0364 as the setting's home is stated in the standup and the fork names both Decisions; D0464 is NOT A PROCESS CHANGE (ranker constant and choosing rule, no enforcement surface) and says so."; }
    // RAN: AI-examined inspect/analyze pass (D0312 B); sprint file section holds the examination
    part dominanceRuleOrDominanceBarReviewGateR1 : TestResult { :>> id = "4ee21e27-4756-41ee-a203-68bd0828b736"; :>> outcome = VerdictKind::proposed; :>> judgedAgainst = "33c398a"; :>> judgedAt = "2026-09-13"; :>> judgedBy = "claudeFable5"; }
    verification dominanceRuleOrDominanceBarCloseOutGate : Test { :>> id = "acbbe703-968e-4b88-b3b3-e53cc1479ff2"; :>> title = "Sprint 691 closeOut gate (autonomous, D0049)"; :>> createdAt = "2026-09-13"; :>> createdBy = "claudeFable5"; :>> method = VerificationMethod::inspect; :>> procedureText = "Closes on gate validate, gate check-engine, gate guard --no-receipt ALL PASS and sync-claude --check over the index holding D0464 and this sprint; the working tree carries no source change; D0464 is in the authority queue and the decision-surfacing brief is republished with it (the pending set changed)."; }
    // RAN: AI-examined inspect/analyze pass (D0312 B); sprint file section holds the examination
    part dominanceRuleOrDominanceBarCloseOutGateR1 : TestResult { :>> id = "4bdba919-53bc-4b45-b00d-f67ae1b06980"; :>> outcome = VerdictKind::proposed; :>> judgedAgainst = "33c398a"; :>> judgedAt = "2026-09-13"; :>> judgedBy = "claudeFable5"; }
    verification dominanceRuleOrDominanceBarRetroGate : Test { :>> id = "02ac5339-6056-4944-8bda-ecdaf6a6355b"; :>> title = "Sprint 691 retro gate (autonomous, D0049)"; :>> createdAt = "2026-09-13"; :>> createdBy = "claudeFable5"; :>> method = VerificationMethod::analyze; :>> procedureText = "AVOIDABLE-ISSUE SCAN, no new item (D0131): the DoD named the third branch in advance and it is the branch that happened, so nothing here was unforeseen. Two things are stated rather than tracked. First, the DoD cited D0364 as the home of the SupersedeClause when the setting lives in D0365's decision clause; a DoD that names the wrong target would have misdirected a mechanical fix, and here it was caught by reading before writing - not an Issue, because D0464 names both and a future resolver reads D0464, not the DoD. Second, the constant was edited before the hand set was read, on the reading that the rule's outcome was mechanical; the DoD's own order (apply the rule, then verify) was followed, and the hand set is what D0365 says is read afterwards - the revert cost one rebuild and is the discipline working, not a defect. WHAT THE TIE LINE BOUGHT: without D0415's COULD NOT CHOOSE line naming no case's outcome changed, the 0-versus-1.5 tie would have been two equal summaries and the claim that 1.5 fires nowhere would have been an inference; the line made it a measurement."; }
    // RAN: AI-examined inspect/analyze pass (D0312 B); sprint file section holds the examination
    part dominanceRuleOrDominanceBarRetroGateR1 : TestResult { :>> id = "671924a9-5238-408e-9bb2-ff10a11ce771"; :>> outcome = VerdictKind::proposed; :>> judgedAgainst = "33c398a"; :>> judgedAt = "2026-09-13"; :>> judgedBy = "claudeFable5"; }
}
