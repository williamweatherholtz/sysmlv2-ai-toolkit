// ProjectDeliveryS293 — Sprint 293: D0108's coordination contract stops being convention
// (dcMechanizeOwnership, D0129). EXECUTE. 5 pts.
package ProjectDeliveryS293 {
    private import EngineElement::*;
    private import EngineWork::*;
    private import EngineVerification::*;
    private import EngineRelationships::*;

    #CharteredBy dependency from ownershipStory to d0144;

    part ownershipStory : Story {
        :>> id = "0d8001fd-0814-61fd-9b3e-0000003001fd";
        :>> title = "Sprint 293: ownership + attestation-authority guards — D0108 mechanized (5 pts)";
        :>> createdAt = "2026-08-15"; :>> createdBy = "claudeOpus5"; :>> kind = WorkKind::code; :>> priority = WorkPriority::p0; :>> owner = "claudeOpus5"; :>> estimatedPoints = 5;
    }

    action def DeliveryRunS293 {
        action storyOwnership;
        verification storyOwnershipDoD : Test { :>> id = "0d8001fe-0814-61fe-9b3e-0000003001fe"; :>> method = VerificationMethod::test; :>> procedureText = "Delivers dcMechanizeOwnership (srDcAuthorityFromRegistry, D0129). D0108's coordination contract — owner-of-record edits fields, a non-owner ADDS items and typed edges or SUPERSEDES, never overwrites in place — was CONVENTION ONLY: absent from every guard and every declared rule, enforced by CLAUDE.md prose plus a reminder hook, while in-place write paths exist that can clobber another actor's item. D0047 is explicit that manual vigilance is not a control. DELIVERED two hard guards, 29 -> 31 (22 hard-blocking). (1) `ownership`: compares each staged `.sysml` against its HEAD blob AST-TO-AST and fails a changed attribute on an item someone else created. AST rather than diff lines because a hunk does not know which item a line belongs to, and misattributing an edit is the one thing an ownership check must not do. Adding an item, adding an edge and superseding leave every existing item's fields untouched, so they pass BY CONSTRUCTION rather than via an exemption list that could drift. An unbound actor is a violation, not a pass — an unattributable edit is worse than a refused one. (2) `attestation-authority`: a disposition of a finding at or above Medium must be judged by a registered `Person`, extending to dispositions the human-only rule `confirmation-authenticity` already enforces for Decision acceptance. VERIFIED LIVE, both directions: editing a field of `issue057` (owned by wweatherholtz) as claudeOpus5 FAILS with the owner, the editor and the remedy named; adding a `#DependsOn` edge PASSES; editing an item I own PASSES; attestation-authority scans 20 dispositions and passes. clippy clean; 136 lib tests; validate 315 clean."; }
        part storyOwnershipDoDR1 : TestResult { :>> id = "0d8001ff-0814-61ff-9b3e-0000003001ff"; :>> outcome = VerdictKind::pass; :>> judgedAgainst = "1b2fd4f"; :>> judgedAt = "2026-08-15"; :>> judgedBy = "claudeOpus5"; }
    }

    verification moRefineGate : Test { :>> id = "0d800200-0814-6200-9b3e-000000300200"; :>> title = "Sprint 293 refine gate (DoR)"; :>> createdAt = "2026-08-15"; :>> createdBy = "claudeOpus5"; :>> method = VerificationMethod::inspect; :>> procedureText = "DoR. CONSUMER CHECK (dorConsumer, D0144) found that HALF the item was already built: `confirmation-authenticity` already checks that a Decision's acceptance names a `Person`-typed actor, via the `resultJudgedByHuman` predicate. So the attestation half needed EXTENDING to dispositions rather than building, and the scope narrowed accordingly. Reading the existing predicate before writing a new one is what turned a duplicate into an extension — the same finding as sprint 289's hook. estimatedPoints=5. DoR met."; }
    part moRefineGateR1 : TestResult { :>> id = "0d800201-0814-6201-9b3e-000000300201"; :>> outcome = VerdictKind::pass; :>> judgedAgainst = "1b2fd4f"; :>> judgedAt = "2026-08-15"; :>> judgedBy = "claudeOpus5"; }

    verification moStandupGate : Test { :>> id = "0d800202-0814-6202-9b3e-000000300202"; :>> title = "Sprint 293 standup gate"; :>> createdAt = "2026-08-15"; :>> createdBy = "claudeOpus5"; :>> method = VerificationMethod::inspect; :>> procedureText = "Approach: before writing the disposition guard, LOOK at what the repo already contains — 21 dispositions, 20 by wweatherholtz and one by claudeOpus. Reading that one rather than assuming it was a violation is what produced the correct threshold. No blockers."; }
    part moStandupGateR1 : TestResult { :>> id = "0d800203-0814-6203-9b3e-000000300203"; :>> outcome = VerdictKind::pass; :>> judgedAgainst = "1b2fd4f"; :>> judgedAt = "2026-08-15"; :>> judgedBy = "claudeOpus5"; }

    verification moImplementGate : Test { :>> id = "0d800204-0814-6204-9b3e-000000300204"; :>> title = "Sprint 293 implement gate"; :>> createdAt = "2026-08-15"; :>> createdBy = "claudeOpus5"; :>> method = VerificationMethod::test; :>> procedureText = "THE NEAR-MISS IS THE FINDING. I found one disposition judged by an AI (`issue043Disp1R1`, judgedBy claudeOpus) and my first read was 'a real violation the guard will catch'. Opening it showed its own text: 'Low doc-accuracy finding, AI-dispositioned (no human gate for Low, D0080)' — and issue043 is indeed `Severity::Low`, where D0080 explicitly permits AI disposition. A guard requiring a human on EVERY disposition would have failed correct, documented work and forced either a false attestation or a bypass, which is the issue081 dynamic that cost this project eight bad commits. The threshold is Medium and above, and the guard's doc comment records the specific case that set it, so nobody 'tightens' it later without meeting the same evidence."; }
    part moImplementGateR1 : TestResult { :>> id = "0d800205-0814-6205-9b3e-000000300205"; :>> outcome = VerdictKind::pass; :>> judgedAgainst = "1b2fd4f"; :>> judgedAt = "2026-08-15"; :>> judgedBy = "claudeOpus5"; }

    verification moReviewGate : Test { :>> id = "0d800206-0814-6206-9b3e-000000300206"; :>> title = "Sprint 293 review gate"; :>> createdAt = "2026-08-15"; :>> createdBy = "claudeOpus5"; :>> method = VerificationMethod::inspect; :>> procedureText = "Reviewed. The first live test PASSED when it should have failed, and the reason matters: I had edited an item I OWN, so the guard was right and my test was wrong. Re-running against `issue057` (owned by wweatherholtz) produced the failure. A test that passes for the wrong reason is worse than one that fails, and this is the second time this pass that a fixture rather than the code was at fault — both caught by asking why the result was what it was rather than accepting a green. LIMITATION, stated: the guard sees only STAGED files, so an unstaged working-tree edit is invisible until `git add`. That matches every other diff-aware guard here and is the point at which the check can be meaningful, but it is not a live editor-time control."; }
    part moReviewGateR1 : TestResult { :>> id = "0d800207-0814-6207-9b3e-000000300207"; :>> outcome = VerdictKind::pass; :>> judgedAgainst = "1b2fd4f"; :>> judgedAt = "2026-08-15"; :>> judgedBy = "claudeOpus5"; }

    verification moCloseOutGate : Test { :>> id = "0d800208-0814-6208-9b3e-000000300208"; :>> title = "Sprint 293 closeOut gate (autonomous, D0049)"; :>> createdAt = "2026-08-15"; :>> createdBy = "claudeOpus5"; :>> method = VerificationMethod::inspect; :>> procedureText = "Autonomous closeOut (D0049). dcMechanizeOwnership carries a passing DoD TestResult. Guards 29 -> 31; both verified live in both directions; both start at ZERO on this repo, so no grandfathering was needed or granted. Doc-sync rides the commit: guards.md gains both entries with the reasoning, and the counts in guards.md and CLAUDE.md §5 are corrected. clippy clean; 136 lib tests; validate 315 clean; check-engine clean; 31 guards green. No gate bypassed."; }
    part moCloseOutGateR1 : TestResult { :>> id = "0d800209-0814-6209-9b3e-000000300209"; :>> outcome = VerdictKind::pass; :>> judgedAgainst = "1b2fd4f"; :>> judgedAt = "2026-08-15"; :>> judgedBy = "claudeOpus5"; }

    verification moRetroGate : Test { :>> id = "0d80020a-0814-620a-9b3e-00000030020a"; :>> title = "Sprint 293 retro gate (autonomous, D0049)"; :>> createdAt = "2026-08-15"; :>> createdBy = "claudeOpus5"; :>> method = VerificationMethod::analyze; :>> procedureText = "Autonomous retro (D0049) under D0131's retroTrack. WELL: (1) the apparent violation was READ before being acted on, and it was not a violation — D0080 permits AI disposition below Medium, and a guard built on my first reading would have failed correct work and invited a bypass; (2) the consumer check found half the item already built, so the attestation half became an extension rather than a duplicate; (3) both guards start at zero on this repo, so no grandfathering was needed — the honest position, since neither codifies a NEW obligation, they enforce one D0108 has stated since June. AVOIDABLE-ISSUE 1: my first ownership test passed when it should have failed, because I edited an item I own. NO NEW ITEM, reason stated: the code was right and the fixture was wrong, and I caught it by asking why a green appeared rather than accepting it — which is the response contract working. It is the second fixture-not-code confusion this pass (sprint 290 was the first), and the operational lesson is the same: when testing a guard that keys on an ACTOR or an OWNER, choose the subject deliberately rather than reaching for the nearest item. Estimate 5 pts, delivered."; }
    part moRetroGateR1 : TestResult { :>> id = "0d80020b-0814-620b-9b3e-00000030020b"; :>> outcome = VerdictKind::pass; :>> judgedAgainst = "1b2fd4f"; :>> judgedAt = "2026-08-15"; :>> judgedBy = "claudeOpus5"; }
}
