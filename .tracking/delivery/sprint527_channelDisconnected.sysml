// ProjectDeliveryS527 — Sprint 527: the decision channel is disconnected; standing consent applies at record time. CHANGE. 3 pts.
package ProjectDeliveryS527 {
    private import EngineElement::*;
    private import EngineWork::*;
    private import EngineVerification::*;
    private import EngineRelationships::*;

    #CharteredBy dependency from channelDisconnectedStory to d0291;

    part channelDisconnectedStory : Story {
        :>> id = "c02ec5f2-393d-4eb8-8bc4-db2cdbf20658";
        :>> title = "Sprint 527: no GitHub issue per Decision - standing consent moves into keel record decision, the channel unit and its workflows go, github-intake stays (3 pts)";
        :>> createdAt = "2026-09-03"; :>> createdBy = "claudeOpus5"; :>> kind = WorkKind::code; :>> priority = WorkPriority::p0; :>> owner = "claudeOpus5"; :>> estimatedPoints = 3;
    }

    action def DeliveryRunS527 {
        action storyChannelDisconnected;
        verification storyChannelDisconnectedDoD : Test { :>> id = "19ed5b09-20ed-49af-ab28-194772d277b4"; :>> method = VerificationMethod::test; :>> procedureText = "DELIVERED BACKLOG ITEMS: dcChannelDisconnected. The human (st088): no GitHub issue notifications; disconnect that pipeline. MEASURED FIRST: the channel had auto-accepted 80 Decisions and recorded 2 of the human's comments - it was the acceptance mechanism, so it was relocated, not dropped. DONE: keel record decision accepts a non-fork at record time under the declared standing consent when github-actors.toml names exactly one decider, the note quoting the standing words; a fork stays proposed; no decider, nothing guessed. Deleted: decision-issue.yml, decision-record.yml, .github/scripts, the decision-channel process, skill, unit record, unit id and extras; decision-channel out of the adopted set; ctChannel and pmChannel out of the authored residue; three channel-only commands deprecated in the CLI facts; the shipped-workflows test and the four script-text tests whose subjects were deleted removed. Rewritten to what is: attestation-policy.toml's standing-consent comment, github-actors.toml's header, github-intake's framing, library-stewardship's worked example, the recorder actor's note, CLAUDE.md section 4. VERIFY: three record-time tests; D0291 itself accepted at record time and carrying the human's words as receipt; two workflows remain; 448 tests; the control-structure view reads the channel inert."; }
        // RAN: cargo test --test standing_consent_at_record_time 3/3; keel record decision -> D0291 accepted at record time, judge wweatherholtz; ls .github/workflows -> ci.yml release.yml; keel sync-claude 44/44; keel guard . ALL PASS; full suite 448/0; clippy clean; grep for the channel over live surfaces -> incident-history comments only
        part storyChannelDisconnectedDoDR1 : TestResult { :>> id = "3dd99e36-9502-4e79-83bd-62d37f693930"; :>> outcome = VerdictKind::pass; :>> judgedAgainst = "10f2571"; :>> judgedAt = "2026-09-03"; :>> judgedBy = "claudeOpus5"; }
    }

    verification channelDisconnectedRefineGate : Test { :>> id = "dac7a51e-e33e-444d-9224-d36d381aba1b"; :>> title = "Sprint 527 refine gate (DoR)"; :>> createdAt = "2026-09-03"; :>> createdBy = "claudeOpus5"; :>> method = VerificationMethod::inspect; :>> procedureText = "READY only after measuring the human's 'it wasn't really doing anything anyway' against the tree: 80 auto-acceptances and 2 human comments said otherwise. That measurement set the shape - disconnect the notifications, keep the consent, relocate the mechanism to the one place that still sees every Decision - and the single-decider rule fell out of asking who the judge would be in a scaffold that has declared nobody."; }
    verification channelDisconnectedStandupGate : Test { :>> id = "5cb51751-9b70-4fc3-9ca9-739add4f189e"; :>> title = "Sprint 527 standup gate"; :>> createdAt = "2026-09-03"; :>> createdBy = "claudeOpus5"; :>> method = VerificationMethod::inspect; :>> procedureText = "THREE CHOICES. (1) Record-time consent in the binary rather than a local script: D0221, and it is the one path every Decision takes. (2) Judge = the single declared decider, or nothing: the workflow hardcoded a login; a binary must not, and a scaffold with no decider must not invent one. (3) The D0291 Decision was accepted by the mechanism it defines - consistent with how every prior safety change was accepted by the channel - and ALSO carries the human's instruction as a quote receipt, because their words were the whole content. Said plainly in D0291: independence is weaker (no off-machine witness at acceptance), friction is lower; the human weighed it."; }
    verification channelDisconnectedImplementGate : Test { :>> id = "87e40505-c31a-49a6-a15e-6f12818bac21"; :>> title = "Sprint 527 implement gate"; :>> createdAt = "2026-09-03"; :>> createdBy = "claudeOpus5"; :>> method = VerificationMethod::test; :>> procedureText = "RAN: scaffold with zero deciders -> stays proposed and says '0 decider(s)'; fixture with one decider -> non-fork accepted with AUTO-ACCEPTED + standing words + judge 'you', fork with OPTION A/B stays proposed. Live: D0291 accepted at record time on this repo. Removal caught by three tests I then had to reconcile: the shipped-workflows test (subject deleted - removed), four script-text tests in github.rs (subject deleted - removed), the control-structure repo test (expected ctChannel - now pins the channel inert, which is true). The actors comment I first wrote claimed 82 records named the recorder; the count was 0 and the comment now says what the recorder did instead."; }
    verification channelDisconnectedReviewGate : Test { :>> id = "a28544bc-ec91-434f-895b-eadf763a2dce"; :>> title = "Sprint 527 review gate — three passes per D0172"; :>> createdAt = "2026-09-03"; :>> createdBy = "claudeOpus5"; :>> method = VerificationMethod::inspect; :>> procedureText = "THREE PASSES. (1) WHAT CONTROL WAS LOST, NAMED: the channel's independent recording on infrastructure the agent could not edit, and the public override thread; audit-history in CI still re-derives every verdict from committed truth, so the record cannot be silently rewritten - but nothing off-machine witnesses the moment of acceptance. D0291 says so. (2) ANY TOMBSTONE: none - every rewritten line states what is; incident comments naming the channel stay as history; the recorder actor's note says what it did and that no record names it. (3) DID github-intake SURVIVE INTACT: yes - pull, ingest, untrusted routing untouched; only its framing sentence lost the word 'decision-channel'."; }
    verification channelDisconnectedCloseOutGate : Test { :>> id = "d0cee327-75e6-4825-8b97-97d02cb968d2"; :>> title = "Sprint 527 closeOut gate (autonomous, D0049)"; :>> createdAt = "2026-09-03"; :>> createdBy = "claudeOpus5"; :>> method = VerificationMethod::inspect; :>> procedureText = "CLOSED. 31 processes ship. The library still publishes decision-channel; retiring it there is stewardship the human can ask for. The 12 pulled issues (st076-st087) remain untriaged - the next act."; }
    verification channelDisconnectedRetroGate : Test { :>> id = "98cbe2bb-b4ba-4516-9511-35fc433d0d5b"; :>> title = "Sprint 527 retro gate (autonomous, D0049)"; :>> createdAt = "2026-09-03"; :>> createdBy = "claudeOpus5"; :>> method = VerificationMethod::analyze; :>> procedureText = "no new item - already tracked: two findings. The scaffold ships standingConsent = d0207 in its policy, so a fresh project inherits THIS project's standing consent as a declaration - inert until it declares a decider, but a declaration it never made; that is the D0219 class (project data shipped as engine data) and belongs to dcVerificationByAuthority, where the policy file's per-project half is being redrawn. And removing a unit by hand happened for the second time (exec-summary, now decision-channel) - the retro of sprint 524 said an item on the second occurrence, so: dcProcessRemoveCommand is added below this sprint."; }
}
