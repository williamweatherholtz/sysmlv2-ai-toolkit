// ProjectDeliveryS141 — Sprint 141: consumerReadme (D0093) — rewrite README consumer-first (install ->
// keel init -> introduction -> orient) with an accurate engine-dev/self-build section; fix every stale
// ref (0001-0018->0096, state-cursor dropped, query.py/report.py retired, kernel-drives-validation ->
// Rust-authority, "parser is queued"->shipped). Surfaced a LICENSE/Cargo mismatch (flagged). 2 pts. AUTONOMOUS (D0049).
package ProjectDeliveryS141 {
    private import EngineElement::*;
    private import EngineWork::*;
    private import EngineVerification::*;
    private import EngineRelationships::*;

    #CharteredBy dependency from consumerReadmeStory to d0093;

    part consumerReadmeStory : Story {
        :>> id = "63940516-2c7d-4e8f-c141-51627384c001";
        :>> title = "Sprint 141: consumerReadme (2 pts) — consumer-first README + doc-sync stale refs (D0093)";
        :>> createdAt = "2026-06-23"; :>> createdBy = "wweatherholtz"; :>> kind = WorkKind::documentation; :>> priority = WorkPriority::p3; :>> owner = "claudeOpus"; :>> estimatedPoints = 2;
    }

    action def DeliveryRunS141 {
        action storyConsumerReadme;
        verification storyConsumerReadmeDoD : Test { :>> id = "63940516-2c7d-4e8f-c141-51627384c002"; :>> method = VerificationMethod::inspect; :>> procedureText = "The README was engine-DEV-focused + stale. FIX (doc-sync): rewrote README.md consumer-first — title 'Keel', a Quickstart (download keel from a GitHub Release OR build from source -> `keel init` -> enable .githooks gate -> introduction skill / `keel orient`), Core ideas, the `keel` toolchain table (no JVM), Where-things-live, then a clearly-separated 'This repository (engine source-of-record)' self-build section + Build-from-source. Fixed every stale ref: decisions 0001-0018 -> d0001-d0096; removed 'state cursor' (dropped D0045, computed); query.py/report.py (retired M4) -> the keel toolchain; 'kernel drives validation' -> Rust is the routine authority (D0048), kernel is dev-only + NOT shipped to keel init; 'standalone parser is queued work' -> shipped (keel IS the runtime); '47 model files' removed. License line matches the LICENSE file (MIT). VERIFY: README quickstart matches actual `keel init` behavior (incl the .githooks step from S139 + Release channel from the human's choice); grep for stale terms (0001-0018|state cursor|query.py|report.py|47 model|queued work|standalone parser) = NONE; keel validate 154 + guard all (13) green. NOTE (flagged, not resolved here): keel-cli Cargo `license = 'MIT OR Apache-2.0'` but the LICENSE file is MIT-only — a licensing DECISION for the human (add LICENSE-APACHE or narrow Cargo to MIT)."; }
        part storyConsumerReadmeDoDR1 : TestResult { :>> id = "63940516-2c7d-4e8f-c141-51627384c003"; :>> outcome = VerdictKind::pass; :>> judgedAgainst = "58609fe"; :>> judgedAt = "2026-06-23"; :>> judgedBy = "claudeOpus"; }
    }

    verification consumerReadmeRefineGate : Test { :>> id = "63940516-2c7d-4e8f-c141-51627384c004"; :>> title = "Sprint 141 refine gate (DoR)"; :>> createdAt = "2026-06-23"; :>> createdBy = "claudeOpus"; :>> method = VerificationMethod::inspect; :>> procedureText = "DoR: deployment-readiness #5. README is engine-dev-focused + stale; consumers need an install/init quickstart. Resolver: consumerReadme. estimatedPoints=2. #CharteredBy d0093. DoD accepted."; }
    part consumerReadmeRefineGateR1 : TestResult { :>> id = "63940516-2c7d-4e8f-c141-51627384c005"; :>> outcome = VerdictKind::pass; :>> judgedAgainst = "58609fe"; :>> judgedAt = "2026-06-23"; :>> judgedBy = "claudeOpus"; }
    verification consumerReadmeStandupGate : Test { :>> id = "63940516-2c7d-4e8f-c141-51627384c006"; :>> title = "Sprint 141 standup gate"; :>> createdAt = "2026-06-23"; :>> createdBy = "claudeOpus"; :>> method = VerificationMethod::inspect; :>> procedureText = "Approach (doc-sync skill): rewrite README consumer-first; verify against actual keel subcommands + the S138/S139 scaffold behavior + the human's GitHub-Releases choice; grep stale terms = 0. No code/.sysml change. No blockers."; }
    part consumerReadmeStandupGateR1 : TestResult { :>> id = "63940516-2c7d-4e8f-c141-51627384c007"; :>> outcome = VerdictKind::pass; :>> judgedAgainst = "58609fe"; :>> judgedAt = "2026-06-23"; :>> judgedBy = "claudeOpus"; }
    verification consumerReadmeImplementGate : Test { :>> id = "63940516-2c7d-4e8f-c141-51627384c008"; :>> title = "Sprint 141 implement gate"; :>> createdAt = "2026-06-23"; :>> createdBy = "claudeOpus"; :>> method = VerificationMethod::inspect; :>> procedureText = "Rewrote README.md. VERIFY: stale-term grep = NONE; quickstart matches keel init (.githooks + Release/build-from-source); toolchain table matches the actual subcommands; keel validate 154 + guard all (13) PASS."; }
    part consumerReadmeImplementGateR1 : TestResult { :>> id = "63940516-2c7d-4e8f-c141-51627384c009"; :>> outcome = VerdictKind::pass; :>> judgedAgainst = "58609fe"; :>> judgedAt = "2026-06-23"; :>> judgedBy = "claudeOpus"; }
    verification consumerReadmeReviewGate : Test { :>> id = "63940516-2c7d-4e8f-c141-51627384c00a"; :>> title = "Sprint 141 review gate"; :>> createdAt = "2026-06-23"; :>> createdBy = "claudeOpus"; :>> method = VerificationMethod::inspect; :>> procedureText = "Diff reviewed. README now leads with the consumer path (install -> init -> introduction -> orient) the deployment model targets, with the self-build narrative clearly demarcated as the engine's source-of-record — and every stale claim corrected (the doc surface had drifted far: 0001-0018, state cursor, kernel-drives-validation, parser-queued). Honest about the Release channel (download OR build-from-source until v0.1.0 ships). Surfaced + flagged the LICENSE-vs-Cargo license mismatch as a human decision rather than silently picking. Clean."; }
    part consumerReadmeReviewGateR1 : TestResult { :>> id = "63940516-2c7d-4e8f-c141-51627384c00b"; :>> outcome = VerdictKind::pass; :>> judgedAgainst = "58609fe"; :>> judgedAt = "2026-06-23"; :>> judgedBy = "claudeOpus"; }
    verification consumerReadmeCloseOutGate : Test { :>> id = "63940516-2c7d-4e8f-c141-51627384c00c"; :>> title = "Sprint 141 closeOut gate (autonomous, D0049)"; :>> createdAt = "2026-06-23"; :>> createdBy = "claudeOpus"; :>> method = VerificationMethod::inspect; :>> procedureText = "Autonomous closeOut (D0049): DoD pass; README consumer-first + stale-free; keel validate 154 + guard all (13) green. Self-evidencing (D0051). Deployment-readiness 5/8 done; introductionDryRun + serveDownstreamDegrade remain of the internal set."; }
    part consumerReadmeCloseOutGateR1 : TestResult { :>> id = "63940516-2c7d-4e8f-c141-51627384c00d"; :>> outcome = VerdictKind::pass; :>> judgedAgainst = "58609fe"; :>> judgedAt = "2026-06-23"; :>> judgedBy = "claudeOpus"; }
    verification consumerReadmeRetroGate : Test { :>> id = "63940516-2c7d-4e8f-c141-51627384c00e"; :>> title = "Sprint 141 retro gate (autonomous, D0049)"; :>> createdAt = "2026-06-23"; :>> createdBy = "claudeOpus"; :>> method = VerificationMethod::analyze; :>> procedureText = "Autonomous retro (D0049). WELL: the README rewrite doubled as a doc-drift audit — it had accumulated many stale claims (decision range, state cursor, kernel-drives-validation, parser-queued) that the consumer-first reframe forced us to correct, and the stale-term grep is now a quick check. AVOIDABLE-ISSUE SCAN: surfaced a real LICENSE/Cargo license mismatch (LICENSE=MIT, Cargo=MIT OR Apache-2.0) — NOT resolved here (licensing is a human decision: add LICENSE-APACHE or narrow Cargo); flagged for the human + worth a small follow-up task. NON-blocking: the README's Release link presupposes releaseTag010; build-from-source covers the gap until then. Estimate 2 pts held. introductionDryRun next."; }
    part consumerReadmeRetroGateR1 : TestResult { :>> id = "63940516-2c7d-4e8f-c141-51627384c00f"; :>> outcome = VerdictKind::pass; :>> judgedAgainst = "58609fe"; :>> judgedAt = "2026-06-23"; :>> judgedBy = "claudeOpus"; }
}
