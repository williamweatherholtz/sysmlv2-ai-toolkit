// ProjectDeliveryS243 — Sprint 243: system-bound analysis views — sibling / children / ancestry slices
// with a shifting focus (srViewerSystemBoundViews, D0126). keel /api/relations + the viewer context menu.
// EXECUTE. 2 pts.
package ProjectDeliveryS243 {
    private import EngineElement::*;
    private import EngineWork::*;
    private import EngineVerification::*;
    private import EngineRelationships::*;

    #CharteredBy dependency from viewerSystemBoundViewsStory to d0126;

    part viewerSystemBoundViewsStory : Story {
        :>> id = "63940516-2c7d-4e8f-c243-51627384c001";
        :>> title = "Sprint 243: viewerSystemBoundViews (2 pts) - sibling/children/ancestry dynamic views with a shifting focus";
        :>> createdAt = "2026-07-17"; :>> createdBy = "wweatherholtz"; :>> kind = WorkKind::code; :>> priority = WorkPriority::p2; :>> owner = "claudeOpus"; :>> estimatedPoints = 2;
    }

    action def DeliveryRunS243 {
        action storyViewerSystemBoundViews;
        verification storyViewerSystemBoundViewsDoD : Test { :>> id = "63940516-2c7d-4e8f-c243-51627384c002"; :>> method = VerificationMethod::demo; :>> procedureText = "Delivers srViewerSystemBoundViews (D0126) — the human's (2026-07-17) sibling/children/ancestry system-bound analyses as dynamic views with a shifting focus. KEEL (v1.15.0, d21ee73): view::relations_json + GET /api/relations?focus=&kind=siblings|children|ancestry computes a directional/relational cut of the typed graph — children (downstream closure), ancestry (upstream closure = the trace chain to the governing Need/Decision), siblings (same-type items sharing a parent, i.e. the same incoming-edge source). Rendered in the slice subgraph shape so the client draws it identically; pure computed view, cached per fingerprint (no stored state). VIEWER (89668f7): the node context menu gains Children ↓ / Ancestry ↑ / Siblings ⇄; relationView() re-anchors the graph + working set on the computed slice, shifting the focus, and the existing detail/critique/supersede actions apply per item (VMC). VERIFY (demo, live): ancestry of an SR reaches its parent Need; siblings returns the 5 co-satisfying SRs; children of a leaf = itself; context menu carries all three; graph re-anchors; 0 console errors. clippy + validate + guard + check-engine green. This realises the human's insight that elements superpose + compose linearly along typed edges, so each analysis is a directional slice."; }
        part storyViewerSystemBoundViewsDoDR1 : TestResult { :>> id = "63940516-2c7d-4e8f-c243-51627384c003"; :>> outcome = VerdictKind::pass; :>> judgedAgainst = "d21ee73"; :>> judgedAt = "2026-07-17"; :>> judgedBy = "claudeOpus"; }
    }

    verification sbRefineGate : Test { :>> id = "63940516-2c7d-4e8f-c243-51627384c004"; :>> title = "Sprint 243 refine gate (DoR)"; :>> createdAt = "2026-07-17"; :>> createdBy = "claudeOpus"; :>> method = VerificationMethod::inspect; :>> procedureText = "DoR: human chose system-bound views first (of the 2026-07-17 direction). Scope: children/ancestry (directional slices) + siblings (same-type shared-parent) as a computed endpoint + context-menu actions. #CharteredBy d0126. estimatedPoints=2. DoR met."; }
    part sbRefineGateR1 : TestResult { :>> id = "63940516-2c7d-4e8f-c243-51627384c005"; :>> outcome = VerdictKind::pass; :>> judgedAgainst = "d21ee73"; :>> judgedAt = "2026-07-17"; :>> judgedBy = "claudeOpus"; }
    verification sbStandupGate : Test { :>> id = "63940516-2c7d-4e8f-c243-51627384c006"; :>> title = "Sprint 243 standup gate"; :>> createdAt = "2026-07-17"; :>> createdBy = "claudeOpus"; :>> method = VerificationMethod::inspect; :>> procedureText = "Approach: reuse configurable_slice (Down=children, Up=ancestry); siblings = shared-parent + same-type set; one /api/relations endpoint in the slice subgraph shape; viewer relationView() clears + re-anchors. No blockers."; }
    part sbStandupGateR1 : TestResult { :>> id = "63940516-2c7d-4e8f-c243-51627384c007"; :>> outcome = VerdictKind::pass; :>> judgedAgainst = "d21ee73"; :>> judgedAt = "2026-07-17"; :>> judgedBy = "claudeOpus"; }
    verification sbImplementGate : Test { :>> id = "63940516-2c7d-4e8f-c243-51627384c008"; :>> title = "Sprint 243 implement gate"; :>> createdAt = "2026-07-17"; :>> createdBy = "claudeOpus"; :>> method = VerificationMethod::demo; :>> procedureText = "Implemented (keel@d21ee73, viewer@89668f7). Live-verified: siblings (6), children, ancestry all re-anchor from the context menu; 0 console errors. clippy + validate + guard + check-engine green."; }
    part sbImplementGateR1 : TestResult { :>> id = "63940516-2c7d-4e8f-c243-51627384c009"; :>> outcome = VerdictKind::pass; :>> judgedAgainst = "d21ee73"; :>> judgedAt = "2026-07-17"; :>> judgedBy = "claudeOpus"; }
    verification sbReviewGate : Test { :>> id = "63940516-2c7d-4e8f-c243-51627384c00a"; :>> title = "Sprint 243 review gate"; :>> createdAt = "2026-07-17"; :>> createdBy = "claudeOpus"; :>> method = VerificationMethod::inspect; :>> procedureText = "Reviewed. The three analyses are pure computed views over the existing traversal engine (no stored state, no new truth) — exactly the 'dynamic views with a shifting focus' the human described. Uniform subgraph shape keeps the client rendering identical to a slice. VMC follows from the existing per-item actions. Clean."; }
    part sbReviewGateR1 : TestResult { :>> id = "63940516-2c7d-4e8f-c243-51627384c00b"; :>> outcome = VerdictKind::pass; :>> judgedAgainst = "d21ee73"; :>> judgedAt = "2026-07-17"; :>> judgedBy = "claudeOpus"; }
    verification sbCloseOutGate : Test { :>> id = "63940516-2c7d-4e8f-c243-51627384c00c"; :>> title = "Sprint 243 closeOut gate (autonomous, D0049)"; :>> createdAt = "2026-07-17"; :>> createdBy = "claudeOpus"; :>> method = VerificationMethod::inspect; :>> procedureText = "Autonomous closeOut (D0049): sibling/children/ancestry views delivered + verified (srViewerSystemBoundViews). Self-evidencing. REMAINING of the 2026-07-17 direction: viewerCreateLinkage (create + edges); srViewerRelationshipGrammar + srViewerScopedAuthoring (the metamodel Decision — scope-aware creation), pending design + human acceptance."; }
    part sbCloseOutGateR1 : TestResult { :>> id = "63940516-2c7d-4e8f-c243-51627384c00d"; :>> outcome = VerdictKind::pass; :>> judgedAgainst = "d21ee73"; :>> judgedAt = "2026-07-17"; :>> judgedBy = "claudeOpus"; }
    verification sbRetroGate : Test { :>> id = "63940516-2c7d-4e8f-c243-51627384c00e"; :>> title = "Sprint 243 retro gate (autonomous, D0049)"; :>> createdAt = "2026-07-17"; :>> createdBy = "claudeOpus"; :>> method = VerificationMethod::analyze; :>> procedureText = "Autonomous retro (D0049). WELL: recognised the analyses ARE directional slices + reused configurable_slice rather than new traversal code; kept them pure computed views in the slice shape so the viewer renders them with the existing path (minimal client code). Confirmed feasibility against the actual model (closed edge algebra + EdgeRule layer) before building. AVOIDABLE-ISSUE: the static server dropped again mid-session (restarted) — recurring minor friction; not worth a control yet. LESSON: name the primitive (a slice) and the feature collapses to a thin wrapper. Estimate 2 pts. NEXT: viewerCreateLinkage, then the relationship-grammar Decision."; }
    part sbRetroGateR1 : TestResult { :>> id = "63940516-2c7d-4e8f-c243-51627384c00f"; :>> outcome = VerdictKind::pass; :>> judgedAgainst = "d21ee73"; :>> judgedAt = "2026-07-17"; :>> judgedBy = "claudeOpus"; }
}
