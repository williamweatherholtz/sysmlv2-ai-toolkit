// ProjectDeliveryS306 — Sprint 306: ACT on the five serve-discipline critique findings, by
// SUPERSEDING rather than overwriting. EXECUTE. 8 pts.
package ProjectDeliveryS306 {
    private import EngineElement::*;
    private import EngineWork::*;
    private import EngineVerification::*;
    private import EngineRelationships::*;

    #CharteredBy dependency from serveReworkStory to issue123;

    part serveReworkStory : Story {
        :>> id = "0d8002d0-0814-62d0-9b3e-0000003002d0";
        :>> title = "Sprint 306: act on issue121-125 — five corrected serve-discipline requirements (8 pts)";
        :>> createdAt = "2026-08-15"; :>> createdBy = "claudeOpus5"; :>> kind = WorkKind::modeling; :>> priority = WorkPriority::p0; :>> owner = "claudeOpus5"; :>> estimatedPoints = 8;
    }

    action def DeliveryRunS306 {
        action storyServeRework;
        verification storyServeReworkDoD : Test { :>> id = "0d8002d1-0814-62d1-9b3e-0000003002d1"; :>> method = VerificationMethod::inspect; :>> procedureText = "Delivers dcServeRequirementRework. The human dispositioned ALL FIVE findings ACT (wweatherholtz, 2026-08-15, verbatim: 'act on all, proceed including through the entire backlog please (unless issue was based on a deprecated feature)'), recorded through `keel apply-review` as five #Dispositions-linked confirmations; the undispositioned >= Medium count fell 67 -> 62. THE CORRECTIONS ARE SUPERSEDING ITEMS, NOT EDITS, and that was forced by a control rather than chosen: all five originals are owned by wweatherholtz, D0108 permits a non-owner to ADD items and typed edges or to SUPERSEDE but never to overwrite another actor's fields, and the `ownership` guard enforces exactly that. It is also the better record — the originals stay readable as what was asked, and the sprint 305 critiques stay #Verify-linked to them, so finding and correction remain legible together. DELIVERED, one corrected requirement per finding: srServeLaunchContract (C1) resolves the output schema from a DECLARED CONTRACT beside the process definitions — the pattern critique-policy.toml and attestation-policy.toml already use — and adds 'no declared schema, no launch', which removes the case where a target is launchable but unvalidatable; srServeSingleSpawnPoint (C2) replaces an untestable universal negative with a structural property a check can assert — exactly one spawn point, taking a validated target VALUE rather than a string; srServeApproveGateHuman (C3) binds the approval to an actor whose KIND is human under the declared attestation policy, kind checked before role, and names the recorded artefact; srServeOutputValidation (C4) requires side effects isolated until output validates, recorded as facts where isolation is impossible, and an explicit error that NAMES what was left behind; srServeBoundedReachableContext (C5) bounds the reachable surface as well as the passed-in context, and requires any unenforceable residual to be stated rather than implied. Plus 5 #Supersede, 5 satisfy carrying the same Needs forward, and 4 #DependsOn tiers. ownership guard 935 scanned, 0 violations — no field of another actor's item was touched. validate 331 clean; 33 guards green."; }
        part storyServeReworkDoDR1 : TestResult { :>> id = "0d8002d2-0814-62d2-9b3e-0000003002d2"; :>> outcome = VerdictKind::pass; :>> judgedAgainst = "b05548a"; :>> judgedAt = "2026-08-15"; :>> judgedBy = "claudeOpus5"; }
    }

    verification srRefineGate : Test { :>> id = "0d8002d3-0814-62d3-9b3e-0000003002d3"; :>> title = "Sprint 306 refine gate (DoR)"; :>> createdAt = "2026-08-15"; :>> createdBy = "claudeOpus5"; :>> method = VerificationMethod::inspect; :>> procedureText = "DoR. The ACT disposition is recorded and is the authorisation. The human's caveat — 'unless issue was based on a deprecated feature' — was checked against each of the five: none rests on a deprecated feature. All five target requirements for keel serve, a component NOT YET BUILT, so every correction is to a specification of future work rather than to a description of something retired. That check mattered for C1 in particular, where the fix could have been read as depending on `producedArtifact`; it does not, it introduces a declared contract instead. estimatedPoints=8."; }
    part srRefineGateR1 : TestResult { :>> id = "0d8002d4-0814-62d4-9b3e-0000003002d4"; :>> outcome = VerdictKind::pass; :>> judgedAgainst = "b05548a"; :>> judgedAt = "2026-08-15"; :>> judgedBy = "claudeOpus5"; }

    verification srStandupGate : Test { :>> id = "0d8002d5-0814-62d5-9b3e-0000003002d5"; :>> title = "Sprint 306 standup gate"; :>> createdAt = "2026-08-15"; :>> createdBy = "claudeOpus5"; :>> method = VerificationMethod::inspect; :>> procedureText = "Approach: record the disposition FIRST so the authorisation precedes the work; check the ownership rule before writing anything, since the obvious move (edit the five statements) is the one D0108 forbids; author corrections as superseding items; read the consequences back from tooling rather than assuming them. No blockers."; }
    part srStandupGateR1 : TestResult { :>> id = "0d8002d6-0814-62d6-9b3e-0000003002d6"; :>> outcome = VerdictKind::pass; :>> judgedAgainst = "b05548a"; :>> judgedAt = "2026-08-15"; :>> judgedBy = "claudeOpus5"; }

    verification srImplementGate : Test { :>> id = "0d8002d7-0814-62d7-9b3e-0000003002d7"; :>> title = "Sprint 306 implement gate"; :>> createdAt = "2026-08-15"; :>> createdBy = "claudeOpus5"; :>> method = VerificationMethod::test; :>> procedureText = "C1 DESERVED MORE THOUGHT THAN 'ADD A FIELD'. The finding said the model cannot hold an output schema, and the obvious fix — add one to frozen `schema/core` — needs its own Decision and sign-off, which would have stalled the whole disposition. The alternative the resolver named, re-scoping the requirement to the launchable set alone, was WORSE: it would have removed the foundation srServeOutputValidation stands on and quietly gutted a safety-relevant requirement to make a metric go green. The answer taken is neither: a DECLARED CONTRACT beside the process definitions, which is this engine's established pattern for exactly this shape (critique-policy.toml, attestation-policy.toml — both read at request time, both downstream-overridable, both part of the declared model without touching frozen core). The added 'no declared schema, no launch' clause is the part that actually closes the hole, because it makes the unvalidatable-target case unrepresentable rather than merely discouraged. READ BACK RATHER THAN ASSUMED, and the numbers moved the WRONG WAY on purpose: sr_verified_pct fell 91% -> 84% and critique-coverage governed rose 65 -> 70, because five NEW requirements exist that nothing verifies and nothing has critiqued. That is honest — a corrected requirement is not a verified one — and the alternative, editing in place, would have kept the metrics flat while silently inheriting the old critiques' pass verdicts for text they never examined."; }
    part srImplementGateR1 : TestResult { :>> id = "0d8002d8-0814-62d8-9b3e-0000003002d8"; :>> outcome = VerdictKind::pass; :>> judgedAgainst = "b05548a"; :>> judgedAt = "2026-08-15"; :>> judgedBy = "claudeOpus5"; }

    verification srReviewGate : Test { :>> id = "0d8002d9-0814-62d9-9b3e-0000003002d9"; :>> title = "Sprint 306 review gate"; :>> createdAt = "2026-08-15"; :>> createdBy = "claudeOpus5"; :>> method = VerificationMethod::inspect; :>> procedureText = "Reviewed. TWO RESIDUALS ARE STATED RATHER THAN HIDDEN. First, the five corrected requirements are authored by claudeOpus5 and therefore CANNOT BE CRITIQUED BY claudeOpus5 — D0080 independence forbids it — so they enter the model uncritiqued and will stay that way until a different critic runs the Core-3 over them. Claiming the findings are closed while the replacements are unexamined would be exactly the self-assurance this engine exists to prevent. Second, acting on the findings SURFACED A DEFECT IN THE VIEW that measures them: critique-coverage counts superseded elements as governed while compute_coverage and compute_tier_satisfaction both exclude them, so the retired originals now sit in the denominator permanently. Recorded as issue127 with dcCritiqueCoverageSupersede, and NOT fixed here, because changing what a computed view counts is a section 3a change that needs sign-off — fixing a metric in the same commit that moves it is how a number stops being trustworthy."; }
    part srReviewGateR1 : TestResult { :>> id = "0d8002da-0814-62da-9b3e-0000003002da"; :>> outcome = VerdictKind::pass; :>> judgedAgainst = "b05548a"; :>> judgedAt = "2026-08-15"; :>> judgedBy = "claudeOpus5"; }

    verification srCloseOutGate : Test { :>> id = "0d8002db-0814-62db-9b3e-0000003002db"; :>> title = "Sprint 306 closeOut gate (autonomous, D0049)"; :>> createdAt = "2026-08-15"; :>> createdBy = "claudeOpus5"; :>> method = VerificationMethod::inspect; :>> procedureText = "Autonomous closeOut (D0049); the ACT authorisation is the human's recorded disposition on all five findings. issue121-125 resolve through dcServeRequirementRework. validate 331 clean; 33 guards green including ownership at 935 scanned with zero violations; check-engine clean. The five superseded originals and their critiques remain in the model, unedited."; }
    part srCloseOutGateR1 : TestResult { :>> id = "0d8002dc-0814-62dc-9b3e-0000003002dc"; :>> outcome = VerdictKind::pass; :>> judgedAgainst = "b05548a"; :>> judgedAt = "2026-08-15"; :>> judgedBy = "claudeOpus5"; }

    verification srRetroGate : Test { :>> id = "0d8002dd-0814-62dd-9b3e-0000003002dd"; :>> title = "Sprint 306 retro gate (autonomous, D0049)"; :>> createdAt = "2026-08-15"; :>> createdBy = "claudeOpus5"; :>> method = VerificationMethod::analyze; :>> procedureText = "Autonomous retro (D0049) under D0131's retroTrack. WELL: (1) checking the ownership rule BEFORE writing changed the whole shape of the work — the obvious move was to edit five statements, D0108 forbids exactly that for a non-owner, and the guard would have caught it after the fact; catching it before meant the corrections arrived as superseding items, which is both permitted and the better record; (2) the human's caveat about deprecated features was applied as a real check rather than acknowledged, and is recorded per-finding in the DoR; (3) the metrics moving the WRONG way was reported as the honest consequence instead of being engineered around, and the tempting alternative — edit in place, keep the numbers flat, inherit pass verdicts for text the critiques never read — is named explicitly so a successor sees why it was refused. AVOIDABLE-ISSUE: none new this sprint; the /tmp defect from sprint 305 did not recur because the Write tool was used for both scripts, which is the remedy dcScratchPathControl will automate. OBSERVED: 62 >= Medium findings remain undispositioned model-wide. The human's 'act on all' was given in reply to a report presenting FIVE findings, and was recorded against those five only — stretching one word across 62 findings they have never read would be a fabricated attestation, which is the one thing this engine must never do."; }
    part srRetroGateR1 : TestResult { :>> id = "0d8002de-0814-62de-9b3e-0000003002de"; :>> outcome = VerdictKind::pass; :>> judgedAgainst = "b05548a"; :>> judgedAt = "2026-08-15"; :>> judgedBy = "claudeOpus5"; }
}
