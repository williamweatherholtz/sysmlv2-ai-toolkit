// ProjectDeliveryS675 — Sprint 675: The bytes the tests, guards and hooks read are the bytes git would commit. On 2026-09-10 a translating writer left 140 eol=lf paths CRLF on disk, git called the tree clean because it normalises at the add, and five tests read anchors that were not there (issue478). Now a tracked path whose working-copy ending differs from the ending its .gitattributes declares is a named refusal in three places - guard working-tree-eol, keel suite --touched (receipt outcome eol-mismatch) and keel land (refuses before the gate, naming the changed paths first) - and the guard receipt's key covers an eol-only rewrite that status calls clean.. EXECUTE. 3 pts.
package ProjectDeliveryS675 {
    private import EngineElement::*;
    private import EngineWork::*;
    private import EngineVerification::*;
    private import EngineRelationships::*;

    #CharteredBy dependency from workingTreeEolMatchesTheAttributeStory to d0447;

    part workingTreeEolMatchesTheAttributeStory : Story {
        :>> id = "87dd7239-02c6-470c-8ccc-79ca36936ffa";
        :>> title = "Sprint 675: The bytes the tests, guards and hooks read are the bytes git would commit. On 2026-09-10 a translating writer left 140 eol=lf paths CRLF on disk, git called the tree clean because it normalises at the add, and five tests read anchors that were not there (issue478). Now a tracked path whose working-copy ending differs from the ending its .gitattributes declares is a named refusal in three places - guard working-tree-eol, keel suite --touched (receipt outcome eol-mismatch) and keel land (refuses before the gate, naming the changed paths first) - and the guard receipt's key covers an eol-only rewrite that status calls clean. (3 pts)";
        :>> createdAt = "2026-09-11"; :>> createdBy = "claudeOpus5"; :>> kind = WorkKind::code; :>> priority = WorkPriority::p0; :>> owner = "claudeOpus5"; :>> estimatedPoints = 3;
    }

    action def DeliveryRunS675 {
        action storyWorkingTreeEolMatchesTheAttribute;
        verification storyWorkingTreeEolMatchesTheAttributeDoD : Test { :>> id = "04bdbb89-68b6-43fd-82f2-6846ddb43ea0"; :>> method = VerificationMethod::test; :>> procedureText = "Forward guard working-tree-eol (guards.rs, constraint def workingTreeEol in guard-constraints.sysml, row in guards.md) runs git ls-files --eol -z once and fails naming every path whose w/ column is lf, crlf or mixed and differs from the eol= in its attr/ column; undeclared endings and empty paths are not judged; a tree git cannot list scans zero. crate::eol holds the census; touched::compute reads it once and the touched receipt writes outcome = eol-mismatch with the paths and eol_ms; sync::cmd_land refuses before the tree gate with the line naming the paths this push changed first. receipt::key gains (len, mtime) of every tracked path. Suite and land synopses in cli_facts.rs and commands.sysml name the refusal. Tests: working_tree_eol integration pair (conforming fixture passes and never names the CRLF .bat; one eol=lf file rewritten CRLF fails naming exactly it; suite --touched and land refuse on the same fixture and the restored tree lands) plus guards::working_tree_eol_tests, eol::, touched::, receipt:: unit tests. Measured on this host: git ls-files --eol 0.79 s, the guard 0.87 s over 1,743 declared paths."; }
        // RAN: verifier receipt batch3 head=40190c5: keel suite --touched -> 710 passed 0 failed 700 s (touched-1789134894.log); eol_scanned 1756 eol_ms 542; keel guard working-tree-eol -> pass; working_tree_eol pair in the touched set
        part storyWorkingTreeEolMatchesTheAttributeDoDR1 : TestResult { :>> id = "75339a34-1e75-492d-8d74-a04500d1ffbf"; :>> outcome = VerdictKind::pass; :>> judgedAgainst = "40190c5"; :>> judgedAt = "2026-09-11"; :>> judgedBy = "claudeOpus5"; }
    }

    verification workingTreeEolMatchesTheAttributeRefineGate : Test { :>> id = "d906a274-7bdf-489e-abe6-5cf3024e276f"; :>> title = "Sprint 675 refine gate (DoR)"; :>> createdAt = "2026-09-11"; :>> createdBy = "claudeOpus5"; :>> method = VerificationMethod::inspect; :>> procedureText = "Chartered by D0447 (proposed, HELD process-change: a new forward guard and a refusal in suite and land wait for the human's word, D0337; NOT A FORK - issue478's resolver named the shape). Built by a parallel implementer in a worktree, integrated by the manager. 3 points: a new module, four modules touched, a guard with its constraint def, two test tiers."; }
    // RAN: verifier receipt batch3 head=40190c5: keel suite --touched -> 710 passed 0 failed 700 s (touched-1789134894.log); validate exit 0; check-engine exit 0; guard ALL PASS exit 0; chartered by d0447 (proposed, HELD process-change); 3 points; task dcWorkingTreeEolMatchesTheAttribute
    part workingTreeEolMatchesTheAttributeRefineGateR1 : TestResult { :>> id = "a79794b6-0692-4eed-a398-78290c686ed2"; :>> outcome = VerdictKind::proposed; :>> judgedAgainst = "40190c5"; :>> judgedAt = "2026-09-11"; :>> judgedBy = "claudeOpus5"; }
    verification workingTreeEolMatchesTheAttributeStandupGate : Test { :>> id = "94d68a3f-692d-449c-b99a-a2485764f749"; :>> title = "Sprint 675 standup gate"; :>> createdAt = "2026-09-11"; :>> createdBy = "claudeOpus5"; :>> method = VerificationMethod::inspect; :>> procedureText = "Order: eol.rs (census) then guards.rs (the guard, GUARD_NAMES, run_one) then touched.rs (compute reads the census, receipt fields) then sync.rs (before_gate/after_gate split) then receipt.rs (key) then the facts, the constraint def, the docs row, the tests. Blocker met and fixed in the build: the first integration run asserted that git status calls a fresh CRLF rewrite clean, but git reports M until the next add refreshes the index - exactly issue478's shape, where the commit's add had run; the tests add before asserting clean. Blocker met in integration: the guard's first run on the MAIN tree found 141 violations (64 decisions, 36 delivery files, 10 validate tools, 5 workflows and others) - the issue478 residue the worktree never had because it was a fresh checkout; rewritten to LF bytes by a byte replace, then git add re-stat of the identical blobs, zero content diff."; }
    // RAN: verifier receipt batch3 head=40190c5: keel suite --touched -> 710 passed 0 failed 700 s (touched-1789134894.log); validate exit 0; check-engine exit 0; guard ALL PASS exit 0; first main-tree run found 141 CRLF paths (issue478 residue), rewritten to LF, zero content diff; issue491 recorded
    part workingTreeEolMatchesTheAttributeStandupGateR1 : TestResult { :>> id = "8577d809-cbfe-4b5e-988e-16a37fe220fc"; :>> outcome = VerdictKind::proposed; :>> judgedAgainst = "40190c5"; :>> judgedAt = "2026-09-11"; :>> judgedBy = "claudeOpus5"; }
    verification workingTreeEolMatchesTheAttributeImplementGate : Test { :>> id = "184a5b8e-1843-44f8-ba68-912507d5aca8"; :>> title = "Sprint 675 implement gate"; :>> createdAt = "2026-09-11"; :>> createdBy = "claudeOpus5"; :>> method = VerificationMethod::test; :>> procedureText = "keel-cli/src/eol.rs (new): the census over git ls-files --eol -z, judged endings only. keel-cli/src/guards.rs: working-tree-eol in GUARD_NAMES and run_one, working_tree_eol_tests. keel-cli/src/touched.rs: compute reads the census; render_receipt writes outcome eol-mismatch, eol_mismatch, eol_ms. keel-cli/src/sync.rs: cmd_land's before_gate refusal line. keel-cli/src/receipt.rs: key over ls-files -z (len, mtime). keel-cli/src/lib.rs: the module. keel-cli/src/cli_facts.rs and .engine/cli/commands.sysml: suite and land synopses. .engine/rules/guard-constraints.sysml: constraint def workingTreeEol. .engine/docs/guards.md: the row. .tracking/architecture/control-map.sysml: gWorkingTreeEol bound to ehz4 and ehz8. keel-cli/tests/working_tree_eol.rs: the pair."; }
    // RAN: verifier receipt batch3 head=40190c5: keel suite --touched -> 710 passed 0 failed 700 s (touched-1789134894.log); validate exit 0; check-engine exit 0; guard ALL PASS exit 0; working_tree_eol integration pair and guards::working_tree_eol_tests in the touched set; eol_scanned 1756
    part workingTreeEolMatchesTheAttributeImplementGateR1 : TestResult { :>> id = "f6492c3f-37a2-430a-b7bf-c16f9e52e7fe"; :>> outcome = VerdictKind::pass; :>> judgedAgainst = "40190c5"; :>> judgedAt = "2026-09-11"; :>> judgedBy = "claudeOpus5"; }
    verification workingTreeEolMatchesTheAttributeReviewGate : Test { :>> id = "6e3c2fdd-a4d1-460d-bcdb-518b3e174958"; :>> title = "Sprint 675 review gate — three passes per D0172"; :>> createdAt = "2026-09-11"; :>> createdBy = "claudeOpus5"; :>> method = VerificationMethod::inspect; :>> procedureText = "Delivered: the condition that cost a verifier's receipt five phantom failures on 2026-09-10 is a named refusal at every surface that reads the working tree, under one second per run. On this tree the guard went red on its first run and named 141 paths nobody knew were CRLF - the control found its own defect on day one, which is the PROVEN state D0360 asks for. Residual: elapsed cost is one git call per run, recorded as eol_ms so the budget can be read back; a project whose .gitattributes declares nothing scans zero and is never judged."; }
    // RAN: verifier receipt batch3 head=40190c5: keel suite --touched -> 710 passed 0 failed 700 s (touched-1789134894.log); validate exit 0; check-engine exit 0; guard ALL PASS exit 0; guard working-tree-eol pass on main after the rewrite; eol_ms 542
    part workingTreeEolMatchesTheAttributeReviewGateR1 : TestResult { :>> id = "809686f8-0b04-4267-85e8-b61e2ebce5c2"; :>> outcome = VerdictKind::proposed; :>> judgedAgainst = "40190c5"; :>> judgedAt = "2026-09-11"; :>> judgedBy = "claudeOpus5"; }
    verification workingTreeEolMatchesTheAttributeCloseOutGate : Test { :>> id = "10e0e55f-adcc-49ab-8182-4d7c76e29490"; :>> title = "Sprint 675 closeOut gate (autonomous, D0049)"; :>> createdAt = "2026-09-11"; :>> createdBy = "claudeOpus5"; :>> method = VerificationMethod::inspect; :>> procedureText = "Sprint 675 closes on the verifier's receipt only (D0425). dcWorkingTreeEolMatchesTheAttribute gets its DoD result. D0447 stays proposed for the human (D0337). The 141 rewritten paths are byte-identical to the index and appear in no diff."; }
    // RAN: verifier receipt batch3 head=40190c5: keel suite --touched -> 710 passed 0 failed 700 s (touched-1789134894.log); validate exit 0; check-engine exit 0; guard ALL PASS exit 0; dcWorkingTreeEolMatchesTheAttributeDoDR1 recorded at 40190c5; D0447 stays proposed for the human
    part workingTreeEolMatchesTheAttributeCloseOutGateR1 : TestResult { :>> id = "fe233a79-290f-4f11-9cf5-cd24bf90240f"; :>> outcome = VerdictKind::proposed; :>> judgedAgainst = "40190c5"; :>> judgedAt = "2026-09-11"; :>> judgedBy = "claudeOpus5"; }
    verification workingTreeEolMatchesTheAttributeRetroGate : Test { :>> id = "98b362a8-c834-47c5-aaef-a04128b51b7e"; :>> title = "Sprint 675 retro gate (autonomous, D0049)"; :>> createdAt = "2026-09-11"; :>> createdBy = "claudeOpus5"; :>> method = VerificationMethod::analyze; :>> procedureText = "AVOIDABLE-ISSUE SCAN: No new item - already tracked: issue478 (this sprint resolves it) and issue491 (the implementer's stop hook ran the main tree's binary against the worktree and reported a red the worktree's own binary did not; resolver dcCliSurfaceGuardNamesAStaleBinary, recorded this commit). FINDING: the D0388 pair was chosen before the real tree was read and the real tree then failed the guard - the fixture negative and the live positive disagreed about the state of main, and the guard was right. That is the order D0388 asks for, and it is why the 141 paths were found by the control instead of by the next phantom failure."; }
    // RAN: verifier receipt batch3 head=40190c5: keel suite --touched -> 710 passed 0 failed 700 s (touched-1789134894.log); validate exit 0; check-engine exit 0; guard ALL PASS exit 0; retro names issue478 (resolved here) and issue491 (already tracked); no new item
    part workingTreeEolMatchesTheAttributeRetroGateR1 : TestResult { :>> id = "ddd7ac03-f53d-4e36-8274-c98844c564af"; :>> outcome = VerdictKind::proposed; :>> judgedAgainst = "40190c5"; :>> judgedAt = "2026-09-11"; :>> judgedBy = "claudeOpus5"; }
}
