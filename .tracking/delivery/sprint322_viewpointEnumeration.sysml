// ProjectDeliveryS322 — Sprint 322: one answer to "what viewpoints exist". EXECUTE. 3 pts.
package ProjectDeliveryS322 {
    private import EngineElement::*;
    private import EngineWork::*;
    private import EngineVerification::*;
    private import EngineRelationships::*;

    #CharteredBy dependency from vpEnumStory to d0047;

    part vpEnumStory : Story {
        :>> id = "0d8003d0-0814-63d0-9b3e-0000003003d0";
        :>> title = "Sprint 322: the viewpoint-renderer guard judges every declared Viewpoint (3 pts)";
        :>> createdAt = "2026-08-17"; :>> createdBy = "claudeOpus5"; :>> kind = WorkKind::code; :>> priority = WorkPriority::p0; :>> owner = "claudeOpus5"; :>> estimatedPoints = 3;
    }

    action def DeliveryRunS322 {
        action storyVpEnum;
        verification storyVpEnumDoD : Test { :>> id = "0d8003d1-0814-63d1-9b3e-0000003003d1"; :>> method = VerificationMethod::test; :>> procedureText = "Resolves issue139 via dcViewpointEnumeration. The `viewpoint-renderer` HARD GUARD and `concern-coverage` each read `.engine/views/viewpoint-registry.sysml` by hardcoded filename and text-scanned its lines, while the Model globs the whole views directory — so the engine held TWO answers to 'what viewpoints exist' and the guard held the smaller one. Both now source `view::declared_viewpoints`, one enumeration from the model, which is also what `surfaces_json` already used. VERIFIED IN THE DIRECTION THAT WAS BROKEN, twice: with a probe viewpoint in a second views file naming `keel definitely-not-a-real-command`, the guard reported 32 scanned / 0 violations BEFORE and 33 scanned / 1 violation AFTER, and concern-coverage went from not mentioning it to counting it; the probe was deleted both times and the real corpus reads 32/32 unchanged, as it must, since all 32 live in the registry. Made permanent by `a_viewpoint_outside_the_registry_file_is_still_judged`, which builds a two-file tree and asserts the FAILING direction. ALSO FIXED IN PASSING: a Viewpoint declaring NO renderer at all was previously invisible to the guard — the text scan only saw viewpoints that had the line — and is now a violation, because a declared lens nothing can render is a concern claimed and not served. clippy clean; 228 tests; validate 350 clean; check-engine clean; 34 guards green."; }
        part storyVpEnumDoDR1 : TestResult { :>> id = "0d8003d2-0814-63d2-9b3e-0000003003d2"; :>> outcome = VerdictKind::pass; :>> judgedAgainst = "105da24"; :>> judgedAt = "2026-08-17"; :>> judgedBy = "claudeOpus5"; }
    }

    verification veRefineGate : Test { :>> id = "0d8003d3-0814-63d3-9b3e-0000003003d3"; :>> title = "Sprint 322 refine gate (DoR)"; :>> createdAt = "2026-08-17"; :>> createdBy = "claudeOpus5"; :>> method = VerificationMethod::inspect; :>> procedureText = "DoR. THE BACKLOG WAS REORDERED to rank dcViewpointEnumeration ahead of dcUnitPortabilityScope, because declaration order IS priority (D0052) and reordering is the sanctioned way to change it — not a field and not a note. The reason is a real prerequisite rather than a preference: making viewpoints portable means splitting the registry into one file per viewpoint, and doing that BEFORE this fix would have silently disabled the hard guard for all 32 of them, since none would then be in the file it read. This sprint also carries dcMachineScopeRestatement, whose work landed as D0158 in sprint 321 and whose DoD result is recorded here — named in this record because `sprint-coverage` requires a done task to appear in a delivery file, and it correctly FAILED the gate until it did. estimatedPoints=3."; }
    part veRefineGateR1 : TestResult { :>> id = "0d8003d4-0814-63d4-9b3e-0000003003d4"; :>> outcome = VerdictKind::pass; :>> judgedAgainst = "105da24"; :>> judgedAt = "2026-08-17"; :>> judgedBy = "claudeOpus5"; }

    verification veStandupGate : Test { :>> id = "0d8003d5-0814-63d5-9b3e-0000003003d5"; :>> title = "Sprint 322 standup gate"; :>> createdAt = "2026-08-17"; :>> createdBy = "claudeOpus5"; :>> method = VerificationMethod::inspect; :>> procedureText = "Approach: extract ONE enumeration (`declared_viewpoints`, model-sourced) and point all three consumers at it, rather than fixing each reader to glob the directory — three globs would be three chances to diverge again, which is the defect this is repairing. Return a named struct rather than a tuple so a fourth consumer cannot mis-order the fields. No blockers."; }
    part veStandupGateR1 : TestResult { :>> id = "0d8003d6-0814-63d6-9b3e-0000003003d6"; :>> outcome = VerdictKind::pass; :>> judgedAgainst = "105da24"; :>> judgedAt = "2026-08-17"; :>> judgedBy = "claudeOpus5"; }

    verification veImplementGate : Test { :>> id = "0d8003d7-0814-63d7-9b3e-0000003003d7"; :>> title = "Sprint 322 implement gate"; :>> createdAt = "2026-08-17"; :>> createdBy = "claudeOpus5"; :>> method = VerificationMethod::test; :>> procedureText = "THE DEFECT WAS PROVEN BEFORE IT WAS FIXED, with a probe file rather than by reading — and the reading alone would have left it a suspicion, because both readers LOOK correct in isolation: each reads the registry, and the registry is where viewpoints go. What made it a defect is that a THIRD path (the model) answered differently, and only running all three exposed it. FOUR THINGS THE COMPILER CAUGHT, each a real signal rather than noise: `quoted_attr` became dead code once the text scan went (so its unit assertion went with it — attribute reading is the model's job now); GuardReport has no Debug, so `{r:?}` in the new test would not compile; and my inserted struct's doc block ORPHANED concern_coverage's own doc, which clippy caught as a missing `# Errors` section — a docs lint catching a misplaced insertion is exactly the kind of accident a mechanical edit produces. The permanent test asserts scanned==2 and one violation naming the stray viewpoint, so a regression fails loudly rather than reporting a smaller number."; }
    part veImplementGateR1 : TestResult { :>> id = "0d8003d8-0814-63d8-9b3e-0000003003d8"; :>> outcome = VerdictKind::pass; :>> judgedAgainst = "105da24"; :>> judgedAt = "2026-08-17"; :>> judgedBy = "claudeOpus5"; }

    verification veReviewGate : Test { :>> id = "0d8003d9-0814-63d9-9b3e-0000003003d9"; :>> title = "Sprint 322 review gate"; :>> createdAt = "2026-08-17"; :>> createdBy = "claudeOpus5"; :>> method = VerificationMethod::inspect; :>> procedureText = "Reviewed. THE SEVERITY WAS RIGHT AT HIGH: this was a hard guard reporting PASS over a set it could not see, which is worse than a missing guard — a missing guard is a known gap, while this one answered confidently about 32 of 33 viewpoints and its number looked healthy. It is the third instance of one shape this session, and naming the pattern is the point: issue109 was an edge whose endpoint resolved to nothing, issue136 was a resolver of the wrong kind, and this is an enumeration narrower than the thing it claims to audit. All three passed every gate. What they have in common is that the CHECK and the SUBJECT were sourced differently, so a single answer computed twice is the structural remedy rather than a sharper check."; }
    part veReviewGateR1 : TestResult { :>> id = "0d8003da-0814-63da-9b3e-0000003003da"; :>> outcome = VerdictKind::pass; :>> judgedAgainst = "105da24"; :>> judgedAt = "2026-08-17"; :>> judgedBy = "claudeOpus5"; }

    verification veCloseOutGate : Test { :>> id = "0d8003db-0814-63db-9b3e-0000003003db"; :>> title = "Sprint 322 closeOut gate (autonomous, D0049)"; :>> createdAt = "2026-08-17"; :>> createdBy = "claudeOpus5"; :>> method = VerificationMethod::inspect; :>> procedureText = "Autonomous closeOut (D0049). issue139 resolved; issue137 resolved in sprint 321 with its backlog result recorded here; issue138 remains open with dcUnitPortabilityScope now unblocked and ranked next. clippy clean; 228 tests; validate 350 clean; check-engine clean; 34 guards ALL PASS. No doc claim changed: guards.md describes what viewpoint-renderer checks, not which file it reads, and that description is now more true than it was."; }
    part veCloseOutGateR1 : TestResult { :>> id = "0d8003dc-0814-63dc-9b3e-0000003003dc"; :>> outcome = VerdictKind::pass; :>> judgedAgainst = "105da24"; :>> judgedAt = "2026-08-17"; :>> judgedBy = "claudeOpus5"; }

    verification veRetroGate : Test { :>> id = "0d8003dd-0814-63dd-9b3e-0000003003dd"; :>> title = "Sprint 322 retro gate (autonomous, D0049)"; :>> createdAt = "2026-08-17"; :>> createdBy = "claudeOpus5"; :>> method = VerificationMethod::analyze; :>> procedureText = "Autonomous retro (D0049) under D0131's retroTrack. WELL: (1) the defect was found by SCOPING a different item — I went to decide viewpoint portability and discovered that doing it would have disabled a guard, which is the argument for deciding before building rather than a happy accident; (2) proven with a probe and re-proven after the fix, in the failing direction both times, then made permanent by a test; (3) the backlog was REORDERED rather than annotated, so the prerequisite is expressed in the one place the frontier actually reads. AVOIDABLE-ISSUE: `sprint-coverage` failed the gate because I recorded dcMachineScopeRestatement as done in sprint 321's commit without naming it in any delivery record. The guard was RIGHT and its message said exactly what to do. What is worth carrying: recording a backlog task's DoD result is not one write but two — the result AND the sprint record that covers it — and I have now split that pair twice in three sprints, the earlier instance being dcResolverKindGuard and dcRootArmSweep in sprint 319. NO NEW ITEM: the control exists, blocks the commit, and names the missing half; the remedy is to record the result in the same edit as the sprint that did the work. Estimate 3 pts, delivered."; }
    part veRetroGateR1 : TestResult { :>> id = "0d8003de-0814-63de-9b3e-0000003003de"; :>> outcome = VerdictKind::pass; :>> judgedAgainst = "105da24"; :>> judgedAt = "2026-08-17"; :>> judgedBy = "claudeOpus5"; }
}
