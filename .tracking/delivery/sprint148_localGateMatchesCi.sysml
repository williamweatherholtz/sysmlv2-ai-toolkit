// ProjectDeliveryS148 — Sprint 148: localGateMatchesCi (D0047, resolves issue048) — the lightweight
// preventative measure from the Sprint 147 CI failure: make the local pre-commit hook run the FULL
// `keel guard` (all enforced honest-state guards) so the local gate matches CI's `guard all`, instead
// of a curated per-path subset that omitted viewpoint-renderer/etc. EXECUTE (a D0047 correction). 2 pts. AUTONOMOUS (D0049).
package ProjectDeliveryS148 {
    private import EngineElement::*;
    private import EngineWork::*;
    private import EngineVerification::*;
    private import EngineRelationships::*;

    #CharteredBy dependency from localGateMatchesCiStory to d0047;

    part localGateMatchesCiStory : Story {
        :>> id = "63940516-2c7d-4e8f-c148-51627384c001";
        :>> title = "Sprint 148: localGateMatchesCi (2 pts) — pre-commit runs the full `keel guard` so local == CI (D0047/issue048)";
        :>> createdAt = "2026-06-24"; :>> createdBy = "wweatherholtz"; :>> kind = WorkKind::code; :>> priority = WorkPriority::p2; :>> owner = "claudeOpus"; :>> estimatedPoints = 2;
    }

    action def DeliveryRunS148 {
        action storyLocalGateMatchesCi;
        verification storyLocalGateMatchesCiDoD : Test { :>> id = "63940516-2c7d-4e8f-c148-51627384c002"; :>> method = VerificationMethod::test; :>> procedureText = "Retro of the Sprint 147 CI failure (D0049 AVOIDABLE-ISSUE SCAN + D0047 corrections-become-guards). The local .githooks/pre-commit ran a CURATED per-path guard subset and never ran viewpoint-renderer/manifest-coverage/critic-independence/process-skill/actors, so a viewpoint-renderer violation passed the hook and only failed CI (init_smoke `guard all`). FIX (lightweight): the hook now runs the FULL `keel guard` (all enforced honest-state guards — kernel-free, <1s) whenever any .sysml changes; removed the per-guard guard_run helper + its calls. VERIFY: hook syntax OK (sh -n); `keel guard` 12 ALL PASS; the hook now exercises viewpoint-renderer locally (would have caught issue048's violation pre-push); kernel validators + clippy blocks unchanged. The second root cause (cherry-picked `git add` left guards.rs unstaged) is BEHAVIORAL — addressed via memory (stage with `git add -A`; check `gh run` after every push), not a guard (the hook reads the working tree, so it cannot catch an unstaged file; CI is the backstop + the post-push check)."; }
        part storyLocalGateMatchesCiDoDR1 : TestResult { :>> id = "63940516-2c7d-4e8f-c148-51627384c003"; :>> outcome = VerdictKind::pass; :>> judgedAgainst = "fc87492"; :>> judgedAt = "2026-06-24"; :>> judgedBy = "claudeOpus"; }
    }

    verification localGateMatchesCiRefineGate : Test { :>> id = "63940516-2c7d-4e8f-c148-51627384c004"; :>> title = "Sprint 148 refine gate (DoR)"; :>> createdAt = "2026-06-24"; :>> createdBy = "claudeOpus"; :>> method = VerificationMethod::inspect; :>> procedureText = "DoR: Sprint 147 CI failure (issue048) revealed the local gate diverges from CI. Lightweight preventative dictated (D0047): hook runs full `keel guard`. estimatedPoints=2. #CharteredBy d0047. DoR met."; }
    part localGateMatchesCiRefineGateR1 : TestResult { :>> id = "63940516-2c7d-4e8f-c148-51627384c005"; :>> outcome = VerdictKind::pass; :>> judgedAgainst = "fc87492"; :>> judgedAt = "2026-06-24"; :>> judgedBy = "claudeOpus"; }
    verification localGateMatchesCiStandupGate : Test { :>> id = "63940516-2c7d-4e8f-c148-51627384c006"; :>> title = "Sprint 148 standup gate"; :>> createdAt = "2026-06-24"; :>> createdBy = "claudeOpus"; :>> method = VerificationMethod::inspect; :>> procedureText = "Approach: replace the curated guard_run blocks with a single `keel guard` (all) run on any .sysml change; keep kernel validators + .tracking validate + clippy; remove the now-unused guard_run helper. Behavioral half -> memory. No blockers."; }
    part localGateMatchesCiStandupGateR1 : TestResult { :>> id = "63940516-2c7d-4e8f-c148-51627384c007"; :>> outcome = VerdictKind::pass; :>> judgedAgainst = "fc87492"; :>> judgedAt = "2026-06-24"; :>> judgedBy = "claudeOpus"; }
    verification localGateMatchesCiImplementGate : Test { :>> id = "63940516-2c7d-4e8f-c148-51627384c008"; :>> title = "Sprint 148 implement gate"; :>> createdAt = "2026-06-24"; :>> createdBy = "claudeOpus"; :>> method = VerificationMethod::test; :>> procedureText = "Hook now runs `keel guard` (all) on any .sysml change; guard_run helper removed. VERIFIED: sh -n OK; `keel guard` 12 ALL PASS; viewpoint-renderer now in the local gate. clippy + keel validate green."; }
    part localGateMatchesCiImplementGateR1 : TestResult { :>> id = "63940516-2c7d-4e8f-c148-51627384c009"; :>> outcome = VerdictKind::pass; :>> judgedAgainst = "fc87492"; :>> judgedAt = "2026-06-24"; :>> judgedBy = "claudeOpus"; }
    verification localGateMatchesCiReviewGate : Test { :>> id = "63940516-2c7d-4e8f-c148-51627384c00a"; :>> title = "Sprint 148 review gate"; :>> createdAt = "2026-06-24"; :>> createdBy = "claudeOpus"; :>> method = VerificationMethod::inspect; :>> procedureText = "Diff reviewed. Running the full `keel guard` locally is the right lightweight fix — the Rust guards are kernel-free + fast, so there is no reason to run a divergent subset; local now mirrors CI. Honest about the limit: the hook reads the working tree, so it can't catch an unstaged file (the second root cause) — that is correctly handled behaviorally (git add -A + post-push `gh run` check), with CI as the backstop. Clean, proportionate."; }
    part localGateMatchesCiReviewGateR1 : TestResult { :>> id = "63940516-2c7d-4e8f-c148-51627384c00b"; :>> outcome = VerdictKind::pass; :>> judgedAgainst = "fc87492"; :>> judgedAt = "2026-06-24"; :>> judgedBy = "claudeOpus"; }
    verification localGateMatchesCiCloseOutGate : Test { :>> id = "63940516-2c7d-4e8f-c148-51627384c00c"; :>> title = "Sprint 148 closeOut gate (autonomous, D0049)"; :>> createdAt = "2026-06-24"; :>> createdBy = "claudeOpus"; :>> method = VerificationMethod::inspect; :>> procedureText = "Autonomous closeOut (D0049): DoD pass; local gate now matches CI. `keel guard` 12 ALL PASS; clippy + validate green. Self-evidencing (D0051). Resolves issue048."; }
    part localGateMatchesCiCloseOutGateR1 : TestResult { :>> id = "63940516-2c7d-4e8f-c148-51627384c00d"; :>> outcome = VerdictKind::pass; :>> judgedAgainst = "fc87492"; :>> judgedAt = "2026-06-24"; :>> judgedBy = "claudeOpus"; }
    verification localGateMatchesCiRetroGate : Test { :>> id = "63940516-2c7d-4e8f-c148-51627384c00e"; :>> title = "Sprint 148 retro gate (autonomous, D0049)"; :>> createdAt = "2026-06-24"; :>> createdBy = "claudeOpus"; :>> method = VerificationMethod::analyze; :>> procedureText = "Autonomous retro (D0049). WELL: this sprint IS the retro-driven preventative the human asked for — a caught CI failure converted into a lightweight, durable measure (D0047). AVOIDABLE-ISSUE SCAN: root cause 1 (curated local guard subset) -> guard fix (hook runs all); root cause 2 (cherry-picked git-add) -> behavioral memory (the hook can't catch unstaged files, so don't pretend a guard can — use git add -A + check CI). LESSON: a local gate that is a SUBSET of CI will eventually let CI-only violations through; keep the local gate == CI for the fast (kernel-free) checks, and CHECK CI after every push (don't rely on the human's GitHub emails). Estimate 2 pts held. issue048 resolved."; }
    part localGateMatchesCiRetroGateR1 : TestResult { :>> id = "63940516-2c7d-4e8f-c148-51627384c00f"; :>> outcome = VerdictKind::pass; :>> judgedAgainst = "fc87492"; :>> judgedAt = "2026-06-24"; :>> judgedBy = "claudeOpus"; }
}
