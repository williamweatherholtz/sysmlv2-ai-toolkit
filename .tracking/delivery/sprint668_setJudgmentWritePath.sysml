// ProjectDeliveryS668 — Sprint 668: The human's judging half of D0312 B: keel judge-set records their verdict on the SAMPLED proposed results of one .tracking file in one sitting - one command, one deck card - while every item is written INDIVIDUALLY with its own pass or fail result and its own <test>Attest<N> quote receipt (D0198), so issue158's count-accepted-as-a-card cannot recur (D0443). Until now 26 AI-examined ceremony gates from sprints 663-667 stood proposed with no write path but a hand-edited line to judge them, and every AI-recorded inspect or analyze gate from here on joins them.. EXECUTE. 5 pts.
package ProjectDeliveryS668 {
    private import EngineElement::*;
    private import EngineWork::*;
    private import EngineVerification::*;
    private import EngineRelationships::*;

    #CharteredBy dependency from setJudgmentWritePathStory to d0443;

    part setJudgmentWritePathStory : Story {
        :>> id = "30237cac-d3e5-466d-abae-c232350e28a5";
        :>> title = "Sprint 668: The human's judging half of D0312 B: keel judge-set records their verdict on the SAMPLED proposed results of one .tracking file in one sitting - one command, one deck card - while every item is written INDIVIDUALLY with its own pass or fail result and its own <test>Attest<N> quote receipt (D0198), so issue158's count-accepted-as-a-card cannot recur (D0443). Until now 26 AI-examined ceremony gates from sprints 663-667 stood proposed with no write path but a hand-edited line to judge them, and every AI-recorded inspect or analyze gate from here on joins them. (5 pts)";
        :>> createdAt = "2026-09-11"; :>> createdBy = "claudeOpus5"; :>> kind = WorkKind::code; :>> priority = WorkPriority::p0; :>> owner = "claudeOpus5"; :>> estimatedPoints = 5;
    }

    action def DeliveryRunS668 {
        action storySetJudgmentWritePath;
        verification storySetJudgmentWritePathDoD : Test { :>> id = "fed7a6d7-3d83-431a-87e4-bb58dd086307"; :>> method = VerificationMethod::test; :>> procedureText = "keel judge-set <file> (--words|--note) --by <human> --date [--verdict pass|fail] [--fail a,b] [--all] writes for each sampled unjudged proposal a <test>R<n+1> TestResult (judgedBy the human, createdBy the recorder, judgedAgainst HEAD) and a <test>Attest<k> confirmation companion quoting the human verbatim plus its own pass; the set is computed from attestation-policy.toml [proposedJudgment] sampling (a share or a count) over result-uuid order with judged proposals counted into the sample first, an absent rule samples everything, --all judges every unjudged proposal; keel attestation reports proposed, sampled, judged and awaiting as separate numbers with the rule; from an agent session a note without the human's quoted words is refused writing nothing and a judge-set:no-quote ledger line, and without the confirmationRecord delegation quoted words are refused as no recording delegation; judge-set joins HUMAN_ONLY_WRITE_COMMANDS and HUMAN_AUTHORITY_COMMANDS so an AI-kind judge is refused before any line is built; the deck shows one judgment card per file with a sampled set awaiting, tapping /api/judge-set with the device receipt appended as an acceptance tap is; the verb is a CliCommand fact, in COMMAND_NAMES, in --help, and the two census write-path rows exist. D0388 pair in attestation.rs: known-positive - six proposals under a 50% rule sample three by uuid and judge none; known-negative - one human pass on a proposal reads as judged and counted first, and a tree of plain passes proposes nothing. Integration test judge_set_records_each_item: four proposals with 50% sampling judge two (one --fail), the file validates and passes confirmation-authenticity and attestation-substance, a second plain call writes nothing, --all judges the rest, the census reads 4/4/4/0, the no-quote and no-delegation refusals hold with the ledger line named. validate, check-engine, guard --no-receipt (stpa-currency warning grows by cmdJudgeSet), sync-claude --check and clippy -D warnings clean."; }
        // RAN: keel suite --touched at 829e0f0: 730 passed, 0 failed, 692 s (judge_set_records_each_item 3 tests in the set); validate, check-engine, guard, sync-claude --check, clippy all green per VERIFIER_RECEIPT 2026-09-11
        part storySetJudgmentWritePathDoDR1 : TestResult { :>> id = "5acabded-ac5a-46b2-9009-987677e96e56"; :>> outcome = VerdictKind::pass; :>> judgedAgainst = "829e0f0"; :>> judgedAt = "2026-09-11"; :>> judgedBy = "claudeOpus5"; }
    }

    verification setJudgmentWritePathRefineGate : Test { :>> id = "1a26e7ec-0ce6-4a9f-8102-2fe435d25398"; :>> title = "Sprint 668 refine gate (DoR)"; :>> createdAt = "2026-09-11"; :>> createdBy = "claudeOpus5"; :>> method = VerificationMethod::inspect; :>> procedureText = "Chartered by D0443 (proposed, process-change: a new write verb, a new policy key and two census rows, so the commit carries the marked Decision and the human's word accepts it; NOT A FORK - D0312 B chose the shape). Sized 5 points: a new verb across twelve files (attestation, write, main, deck, serve, census, control_structure, activation, cli_facts, cli_surface, commands.sysml, the policy) with a unit pair, a write test pair and a three-case integration test. Read before design: write.rs accept_decision_locked and refuse_ai_judgment are the channel; main.rs verdict_channel_refusal was hard-wired to decisionAcceptance and the read-back WARN, so it takes the delegation class and a read-back flag; attestation.rs proposed_count was the only reader of VerdictKind::proposed; deck.rs collect had two card classes; serve.rs KEEL_API_WRITE_ENDPOINTS is the census's list of write endpoints. FINDING 4 of sprint 663's retro (D0049 autonomy vs D0312 B proposed) resolves here by cost: the human judges one sampled set per file, not one item per gate. DoR: points set, charter edge set, DoD authored, dcProposedOutcomeTier done."; }
    // RAN: keel validate . 762 tracking files clean; charter edge and points read from the sprint file at 829e0f0
    part setJudgmentWritePathRefineGateR1 : TestResult { :>> id = "26ee778a-b93d-4efb-93a3-b88a04e90109"; :>> outcome = VerdictKind::proposed; :>> judgedAgainst = "829e0f0"; :>> judgedAt = "2026-09-11"; :>> judgedBy = "claudeOpus5"; }
    verification setJudgmentWritePathStandupGate : Test { :>> id = "2403ad0c-e989-44e4-920a-0d242193f8c5"; :>> title = "Sprint 668 standup gate"; :>> createdAt = "2026-09-11"; :>> createdBy = "claudeOpus5"; :>> method = VerificationMethod::inspect; :>> procedureText = "Order: attestation.rs (Proposal, SamplingRule, proposals_in, sample, ProposalCounts, the pair) then write.rs (SetJudgment, judge_set, max_numbered, HUMAN_ONLY_WRITE_COMMANDS) then main.rs (verdict_channel_refusal parametrised, judge_set_items, cmd_judge_set, dispatch) then the surfaces (deck card, /api/judge-set, census rows, control_structure, activation GRANTS, cli_facts, cli_surface, commands.sysml, the policy section); every edit through Write-tool apply scripts because the pre-bash hook denies a heredoc with a backslash (D0309); clippy pedantic on every pass; the integration test copied from accept_honours_delegation's harness; release build only after no cargo or keel-land process is running (issue477); refresh keel-serve.exe; then the verifier (test-verify, touched run detached, pair = attestation.rs six_proposals_under_a_half_rule_sample_three_by_uuid_and_judge_none and a_human_result_is_judged_and_counted_into_the_sample_first_and_passes_propose_nothing) and the recorder from its receipt only (D0425), evidence without the receipt marker (issue476)."; }
    // RAN: keel validate . 762 clean and keel check-engine . clean at 829e0f0 per VERIFIER_RECEIPT 2026-09-11
    part setJudgmentWritePathStandupGateR1 : TestResult { :>> id = "e003ff5c-bbf6-4c30-a5fa-61bbae59e476"; :>> outcome = VerdictKind::proposed; :>> judgedAgainst = "829e0f0"; :>> judgedAt = "2026-09-11"; :>> judgedBy = "claudeOpus5"; }
    verification setJudgmentWritePathImplementGate : Test { :>> id = "fcab6c10-de17-4916-a787-1a50fe60f3b8"; :>> title = "Sprint 668 implement gate"; :>> createdAt = "2026-09-11"; :>> createdBy = "claudeOpus5"; :>> method = VerificationMethod::test; :>> procedureText = "keel-cli/src/attestation.rs: Proposal, SamplingRule::{Share,Count} with parse and quota, sampling_rule, proposals_in_text/proposals_in (a proposal is judged when a later human pass or fail on the same test exists), sample, ProposalCounts with awaiting, proposal_counts; cmd prints the proposals line and the judge-set hint, JSON gains proposals. keel-cli/src/write.rs: SetJudgment, judge_set/judge_set_locked (file lock, refuse_ai_judgment, verdict and Test-exists checks, per item R<n+1> + Attest<k> + Attest<k>R1 before the file's last brace, write_atomic), max_numbered, judge_set_tests; HUMAN_ONLY_WRITE_COMMANDS = accept, judge-set. keel-cli/src/main.rs: verdict_channel_refusal(verb, doing, args, tty, delegation_class, read_back); judge_set_items; cmd_judge_set; dispatch. keel-cli/src/deck.rs: judgment_cards, the judgment class and verb, the saveLocal branch to /api/judge-set. keel-cli/src/serve.rs: JudgeSetReq, api_judge_set, the endpoint in KEEL_API_WRITE_ENDPOINTS. keel-cli/src/view/census.rs: judge-set:no-quote and judge-set:no-delegation rows. keel-cli/src/view/control_structure.rs: HUMAN_AUTHORITY_COMMANDS gains judge-set. keel-cli/src/activation.rs: GRANTS gains sampling. keel-cli/src/cli_facts.rs (110 facts), cli_surface.rs (71 names), .engine/cli/commands.sysml cliJudgeSet. .engine/contracts/attestation-policy.toml [proposedJudgment] sampling = 50%. keel-cli/tests/judge_set_records_each_item.rs. .engine/decisions/0443. No guard, hook or CI file moves."; }
    // RAN: keel suite --touched at 829e0f0: 730 passed, 0 failed, 692 s, log touched-1789115573.log; D0388 pair six_proposals_under_a_half_rule_sample_three_by_uuid_and_judge_none PASS and a_human_result_is_judged_and_counted_into_the_sample_first_and_passes_propose_nothing PASS; cargo clippy -D warnings pass
    part setJudgmentWritePathImplementGateR1 : TestResult { :>> id = "f7803b16-bc40-4d66-880d-317b8de77900"; :>> outcome = VerdictKind::pass; :>> judgedAgainst = "829e0f0"; :>> judgedAt = "2026-09-11"; :>> judgedBy = "claudeOpus5"; }
    verification setJudgmentWritePathReviewGate : Test { :>> id = "21b28b34-1d92-4df7-94f6-d00bb561154d"; :>> title = "Sprint 668 review gate — three passes per D0172"; :>> createdAt = "2026-09-11"; :>> createdBy = "claudeOpus5"; :>> method = VerificationMethod::inspect; :>> procedureText = "Delivered: the human judges a sampled set with one command or one tap and every item lands on its own line with its own quote; the sample is computed from the tree and unchoosable by the writer; the census names the three numbers and the rule; the agent's act is bound by the same two channel controls as keel accept, now with judge-set's own ledger names. Verified by the verifier's receipt only (D0425): validate, check-engine, guard --no-receipt, sync-claude --check, clippy, the D0388 pair, the integration test, and the touched run (keel-cli/src moved, so the lib's unit tests and every integration test naming a changed module are in the set) read after exit with at, stems, lib and head checked. The DoD result is written by the recorder from that receipt. Not delivered: the 26 standing proposals are not judged - that is the human's, per file, with keel judge-set; and dcReplayableDemoStaysAPass (the demo clause of D0312 B) is the next item."; }
    // RAN: keel guard --no-receipt . ALL PASS with the expected stpa-currency WARN naming cmdJudgeSet; keel sync-claude --check matches; per VERIFIER_RECEIPT 2026-09-11
    part setJudgmentWritePathReviewGateR1 : TestResult { :>> id = "ba89e2c3-14bb-4676-8124-2845224d11d0"; :>> outcome = VerdictKind::proposed; :>> judgedAgainst = "829e0f0"; :>> judgedAt = "2026-09-11"; :>> judgedBy = "claudeOpus5"; }
    verification setJudgmentWritePathCloseOutGate : Test { :>> id = "c97a89f0-1acf-451e-a6c1-7bb8b426154c"; :>> title = "Sprint 668 closeOut gate (autonomous, D0049)"; :>> createdAt = "2026-09-11"; :>> createdBy = "claudeOpus5"; :>> method = VerificationMethod::inspect; :>> procedureText = "Sprint 668 closes on the verifier's receipt only (D0425). The backlog item dcSetJudgmentWritePath gets its DoD result. D0443 stays proposed for the human (D0337); its acceptance and the first keel judge-set run over a sprint file are theirs. The stpa-currency warning now names cmdJudgeSet in the human->model edge - a new human control action no stpa-self run has analysed, which is the guard doing what D0313 built it for."; }
    // RAN: verifier receipt green on every line at 829e0f0; DoD result written from the same receipt
    part setJudgmentWritePathCloseOutGateR1 : TestResult { :>> id = "455a4fc6-35ed-4675-8b56-94e1dbe4c94f"; :>> outcome = VerdictKind::proposed; :>> judgedAgainst = "829e0f0"; :>> judgedAt = "2026-09-11"; :>> judgedBy = "claudeOpus5"; }
    verification setJudgmentWritePathRetroGate : Test { :>> id = "9b82ead3-b911-4382-ab5d-110c3605267a"; :>> title = "Sprint 668 retro gate (autonomous, D0049)"; :>> createdAt = "2026-09-11"; :>> createdBy = "claudeOpus5"; :>> method = VerificationMethod::analyze; :>> procedureText = "AVOIDABLE-ISSUE SCAN: three new Issues this sprint - issue478, resolved by dcWorkingTreeEolMatchesTheAttribute (FINDING 6), issue479, resolved by dcRunningReceiptNamesItsProcess (FINDING 7), and issue480, resolved by dcRecorderRefusesAReceiptNotBoundToItsDispatch (FINDING 8), all added to the backlog in this commit; the other recurrable constraint met (FINDING 3) is issue477, carried by dcLandTestsTheCommitItPushes, and FINDINGS 1, 2, 4 and 5 are observations with no action owed. FINDING 6 (D0047, found by the verifier not the primary): the first verifier receipt read the touched run 725 passed, 5 failed - a router test and four lib fixture scans no changed line could reach - and the cause was the working tree's LINE ENDINGS: every file the sprint's Python apply scripts (pathlib.write_text) and the harness Write tool wrote came out CRLF against a .gitattributes that says lf, git would have normalised them at commit, but the touched run and land test the working tree (issue477), so a newline-brace-newline anchor and four fixture counts read 0. Stripping the CRs passed all five; no control read the tree's endings against the attribute, so the verdict depended on which tool last wrote a file - that is the control issue478's resolver adds, and the D0425 split earned its cost here: the primary had run the same five tests green on its own tree and would have called it done. FINDING 7 (D0047, the third receipt-reading defect in three sprints after issue468 and issue469): the second verifier dispatch read the touched run as DID NOT COMPLETE while two cargo runs it had itself launched were alive - it searched the process list for a name it guessed and read the running stub's at as staleness; the primary established the misread with one tasklist and the run finished 730 passed, 0 failed, 692 s. The skill says wait for exit and the agent did not; an instruction is not a control, so the stub gains the child's pid and keel suite --status answers running / finished / died (issue479). FINDING 8 (D0047): the verifier returned its amended green receipt twice without writing the file; the recorder read the first dispatch's red receipt off the disk and refused - correctly, and only because the stale file was red. Nothing binds a receipt to the dispatch that asked for it (issue480), and the recorder's procedure has no skill to hold that check - dcRecorderRefusesAReceiptNotBoundToItsDispatch gives it one. Three of this sprint's eight findings are the verifier-recorder channel failing in a way the primary caught by hand: the D0425 split moved the checking, and the checking now needs its own controls. FINDING 1: the integration fixture's first draft imported EngineBuild::*, a package no scaffold declares, so validate over the written tree failed while the write itself and both refusals held - the fixture, not the verb, was wrong, and the test caught it because the DoD made validate over the WRITTEN tree an assertion rather than trusting the writer; a write path test that does not validate its output is half a test. FINDING 2: the attestation.rs fixture's trim_end_matches('}/n') stripped repeatedly and swallowed a result's closing brace, merging two lines - a strip_suffix fixed it; the D0388 pair's known-negative found it because it counted judged and the count was wrong, which is the argument for a pair that counts rather than one that asserts non-empty. FINDING 3 (D0425, second sprint running): the primary held every source edit until the previous land's cargo exited; the constraint is issue477's and its resolver dcLandTestsTheCommitItPushes stands in the backlog. FINDING 4: verdict_channel_refusal existed for one verb with the Decision read-back inlined; parametrising it for judge-set was the whole channel cost - the design that kept accept's controls out of a new copy is the one the census's write-path rows depend on, since a copied check would have needed its own row and its own evidence. FINDING 5, tension carried forward: D0443 says the sample is drawn per FILE, and the ceremony gates of one sprint live in one file, so a 50% rule reads roughly half of each sprint's five gates - whether that is the right load is the human's to set in the policy, and the census reports the rule so the setting is visible."; }
    // RAN: keel guard retro-backlog . PASS: retro names issue478, issue479 and issue480 with their resolvers added this commit
    part setJudgmentWritePathRetroGateR1 : TestResult { :>> id = "d05dc1f2-e42a-492b-a318-ab76da79ab35"; :>> outcome = VerdictKind::proposed; :>> judgedAgainst = "829e0f0"; :>> judgedAt = "2026-09-11"; :>> judgedBy = "claudeOpus5"; }
}
