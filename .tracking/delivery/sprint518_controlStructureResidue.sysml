// ProjectDeliveryS518 — Sprint 518: the system definition begins - the authored residue of keel's control structure, and the computed rest chartered. EXECUTE. 2 pts.
package ProjectDeliveryS518 {
    private import EngineElement::*;
    private import EngineWork::*;
    private import EngineVerification::*;
    private import EngineRelationships::*;

    #CharteredBy dependency from controlStructureResidueStory to nKeelIsADefinedSystem;

    part controlStructureResidueStory : Story {
        :>> id = "6d1e4b2a-9c37-4f58-b0e2-3a7d8c5f1e94";
        :>> title = "Sprint 518: keel's control structure - the irreducible residue authored, everything derivable chartered as a computed view (2 pts)";
        :>> createdAt = "2026-09-02"; :>> createdBy = "claudeOpus5"; :>> kind = WorkKind::modeling; :>> priority = WorkPriority::p0; :>> owner = "claudeOpus5"; :>> estimatedPoints = 2;
    }

    action def DeliveryRunS518 {
        action storyControlStructureResidue;
        verification storyControlStructureResidueDoD : Test { :>> id = "7e2f5c3b-ad48-4069-c1f3-4b8e9d602fa5"; :>> method = VerificationMethod::inspect; :>> procedureText = "DELIVERED: st065 and st066 recorded verbatim with three derived stories (us069 architecture, us070 process, us071 process); engine-control-structure.sysml holding ONLY what cannot be derived - 8 Controller anchors, 6 ControlledProcess anchors, 5 ProcessModels whose beliefs name the Issues that make a belief false, and one dependency per hazard to the process it is a state of; four items chartered and ranked - dcCliCommandFactsAuthored and dcControlStructureIsComputed at the head of the frontier (the human's stated first step), dcStpaProcessForKeel and dcVerificationByAuthority as the forks that follow; issue344 (CliCommand facts claimed, never authored) and issue345 (priority-inversion has nowhere to record a deliberate rank) triaged on arrival. NOT delivered, on purpose: 19 control actions and 9 feedback paths I had authored as prose - the human corrected mid-turn that the analysis must be computed from existing facts, and two guards had already refused the same thing from the other side (attribute-vocabulary: no text attribute on the control-loop types, 42 values would be LOST; parser-coverage: 42 doc statements invisible to every view). VERIFY: validate 593 clean; all guards pass; whats-next reads the two head items back in the human's order."; }
        // RAN: keel validate . (593 clean) after each write; keel guard . ALL PASS; keel whats-next . head = dcCliCommandFactsAuthored, dcControlStructureIsComputed; guard attribute-vocabulary 42 violations on the prose version and parser-coverage 49 > 7 on the doc version, both read before the residue was cut
        part storyControlStructureResidueDoDR1 : TestResult { :>> id = "8f306d4c-be59-417a-d204-5c9f0e713ab6"; :>> outcome = VerdictKind::pass; :>> judgedAgainst = "52b434e"; :>> judgedAt = "2026-09-02"; :>> judgedBy = "claudeOpus5"; }
    }

    verification controlStructureResidueRefineGate : Test { :>> id = "90417e5d-cf6a-428b-e315-6da01f824bc7"; :>> title = "Sprint 518 refine gate (DoR)"; :>> createdAt = "2026-09-02"; :>> createdBy = "claudeOpus5"; :>> method = VerificationMethod::inspect; :>> procedureText = "READY because the schema for STPA step 2 already existed (EngineSafety: Controller, ControlledProcess, ControlAction, Feedback, ProcessModel) with steps 1 and 3 instantiated and step 2 empty - the human's observation that keel has no defined system was checkable and true: zero Controller instances. The wiring the structure describes was read before anything was authored: five hook events, four git hooks, six CI steps, two channel workflows, the branch-protection API (no required checks, no reviews)."; }
    verification controlStructureResidueStandupGate : Test { :>> id = "a1528f6e-d07b-4c9c-f426-7eb12a935cd8"; :>> title = "Sprint 518 standup gate"; :>> createdAt = "2026-09-02"; :>> createdBy = "claudeOpus5"; :>> method = VerificationMethod::inspect; :>> procedureText = "ONE COURSE CORRECTION, recorded rather than smoothed over. The first version authored 47 parts with a prose body each - a control-structure DOCUMENT, which Invariant 1 forbids and which the human named directly: computed from existing facts, as far as possible. The guards had refused it twice already for adjacent reasons. The residue kept is exactly what no fact source yields: which processes are controlled (a partition), which authorities exist (anchors the computed actions attach to), what each believes (a judgment), and which process each hazard lives in. The 19 actions and 9 feedback paths are now the DoD of dcControlStructureIsComputed, each with the fact it derives from named."; }
    verification controlStructureResidueImplementGate : Test { :>> id = "b2639a7f-e18c-4dad-0537-8fc23ba46de9"; :>> title = "Sprint 518 implement gate"; :>> createdAt = "2026-09-02"; :>> createdBy = "claudeOpus5"; :>> method = VerificationMethod::inspect; :>> procedureText = "RAN: record statement twice, record story three times, add-task five times with --dod-from, record issue twice with --date - all through the write API; the residue file generated from a committed-to-scratch generator so the same data drives the transform when statement lands on the control-loop types. Gate read after every write. The prose attempt cost two guard refusals and the human's correction; the residue passed first time."; }
    verification controlStructureResidueReviewGate : Test { :>> id = "c374ab80-f29d-4ebe-1648-9ad34cb57ef0"; :>> title = "Sprint 518 review gate — three passes per D0172"; :>> createdAt = "2026-09-02"; :>> createdBy = "claudeOpus5"; :>> method = VerificationMethod::inspect; :>> procedureText = "THREE PASSES. (1) IS ANYTHING IN THE RESIDUE DERIVABLE: the controller anchors are the borderline - the hook boundary, commit gate, CI and channel could be discovered from their config files; kept as anchors because a computed action needs a stable name to attach to and a fresh project with no hooks still has the authority, inert. (2) DO THE BELIEFS OVERCLAIM: each false belief names its Issue (issue343, issue342, issue 43 downstream, D0266); no belief is marked false without a recorded fact behind it. (3) DOES THE RANKING FOLLOW THE HUMAN: their words put the system definition first; the two items that ARE the definition sit at the head, the two forks that need it sit below the High-issue fork they depend on, and the 30 inversion warnings that remain are the guard asking for a justification it has no field for - issue345."; }
    verification controlStructureResidueCloseOutGate : Test { :>> id = "d485bc91-03ae-4fff-2759-abe45cd68f01"; :>> title = "Sprint 518 closeOut gate (autonomous, D0049)"; :>> createdAt = "2026-09-02"; :>> createdBy = "claudeOpus5"; :>> method = VerificationMethod::inspect; :>> procedureText = "CLOSED. The definition's authored half is in the tree; its computed half is the head of the frontier with its prerequisite in front of it. The verification revamp and the STPA process are chartered as forks and wait, by the human's own ordering, on the structure they bind to."; }
    verification controlStructureResidueRetroGate : Test { :>> id = "e596cda2-14bf-4000-386a-bcf56de79a12"; :>> title = "Sprint 518 retro gate (autonomous, D0049)"; :>> createdAt = "2026-09-02"; :>> createdBy = "claudeOpus5"; :>> method = VerificationMethod::analyze; :>> procedureText = "ADDED THIS COMMIT: issue344, issue345. The finding about my own work: I authored a document when the invariant says author facts, and the guards caught it before the human did - but for adjacent reasons, not the real one. There is no control that refuses an authored analysis as such; there cannot be one that reads intent. What there IS: the two guards that fired are the shape of control that catches it anyway, and issue345 is the one place where a guard asked for a fact and had nowhere to receive it."; }
}
