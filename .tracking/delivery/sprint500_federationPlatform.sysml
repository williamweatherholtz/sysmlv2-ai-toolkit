// ProjectDeliveryS500 — Sprint 500: the federation test platform, the GitHub intake path, and the three defects building them exposed. EXECUTE. 13 pts.
package ProjectDeliveryS500 {
    private import EngineElement::*;
    private import EngineWork::*;
    private import EngineVerification::*;
    private import EngineRelationships::*;

    #CharteredBy dependency from federationPlatformStory to d0263;

    part federationPlatformStory : Story {
        :>> id = "f73273ea-4ca8-416c-af5a-10624949cedf";
        :>> title = "Sprint 500: nine federation claims, two panel rounds, three defects found (13 pts)";
        :>> createdAt = "2026-08-30"; :>> createdBy = "claudeOpus5"; :>> kind = WorkKind::code; :>> priority = WorkPriority::p0; :>> owner = "claudeOpus5"; :>> estimatedPoints = 13;
    }

    action def DeliveryRunS500 {
        action storyFederationPlatform;
        verification storyFederationPlatformDoD : Test { :>> id = "a25b2dd3-0987-4008-88be-b82c04bfae1c"; :>> method = VerificationMethod::test; :>> procedureText = "DELIVERED, in the sequence the human specified (st040): reconnaissance, design (D0262), panel, implement, re-panel. THE SUITE: keel-cli/tests/federation.rs, 11 cases over 9 claims - first commit at four path shapes, numbering reset, namespace hygiene, a vocabulary-leak check, library pickup, a downstream-authored unit reaching a sibling through an ISOLATED library, the live GitHub contract, verbatim idempotent ingestion, armed-not-present controls, and migration when the engine moves. THE INGESTION PATH (st041): keel github-ingest + the githubIntake process + its skill + `github` on StatementChannel + `sourceUrl` on Statement, kernel-validated 19/19. THREE DEFECTS FOUND AND FIXED: issue313 (a fresh project cannot commit at depth - init now names the risk and remedy), issue314 (keel migrate silently REVERTED a project's adoption choice; project-owned contracts are now added, never overwritten), issue315 (shell backticks in --description executed for the THIRD time; record issue gains --description-from FILE). VERIFY: federation 11/11; workspace 430 passed 0 failed; clippy -D warnings clean; keel guard 0 violations; live ingest of GH#38 recorded st042 and a re-ingest REFUSED.: DELIVERED BACKLOG ITEMS: <items>. <what done means, verified how>."; }
        // RAN: // RAN: federation 11/11; workspace 430 passed 0 failed; clippy clean; validate_schema 19/19 kernel; live github-ingest of GH#38 -> st042 with re-ingest REFUSED; keel guard 0 violations
        part storyFederationPlatformDoDR1 : TestResult { :>> id = "7da0d513-4320-483e-91d9-6483649a4dde"; :>> outcome = VerdictKind::pass; :>> judgedAgainst = "6146f43"; :>> judgedAt = "2026-08-30"; :>> judgedBy = "claudeOpus5"; }
    }

    verification federationPlatformRefineGate : Test { :>> id = "b5f89cf5-db3b-4688-b1f4-b1156ee01466"; :>> title = "Sprint 500 refine gate (DoR)"; :>> createdAt = "2026-08-30"; :>> createdBy = "claudeOpus5"; :>> method = VerificationMethod::inspect; :>> procedureText = "READY: reconnaissance ran BEFORE the design and changed it twice - F1 exists in its deep-path form only because the shallow version passed and the deep one did not, and F6/F7 are construction rather than verification because the upstream path turned out not to exist. A design written from memory would have asserted a loop that was never there and called it covered."; }
    verification federationPlatformStandupGate : Test { :>> id = "d7a991f3-c61d-4883-b904-816a7ff74737"; :>> title = "Sprint 500 standup gate"; :>> createdAt = "2026-08-30"; :>> createdBy = "claudeOpus5"; :>> method = VerificationMethod::inspect; :>> procedureText = "No blocker. The dependency worth naming: the ingestion path needed a SCHEMA change (github on StatementChannel, sourceUrl on Statement) and the intake process forbids force-fitting into `other` - so the schema went through validate_schema.py against the kernel (19/19) before any Rust was written. The write path needed no change to accept the new channel, because check_member derives the accepted set from the schema (D0150) - the design paying off rather than a coincidence."; }
    verification federationPlatformImplementGate : Test { :>> id = "be92c268-9a39-4c49-b226-2f62f933bbe6"; :>> title = "Sprint 500 implement gate"; :>> createdAt = "2026-08-30"; :>> createdBy = "claudeOpus5"; :>> method = VerificationMethod::test; :>> procedureText = "RAN: cargo test --test federation -> 11/11. cargo test --workspace --release -> 430 passed, 0 failed. cargo clippy --workspace --all-targets -D warnings -> clean (four lints fixed by moving code, never suppressed). validate_schema.py -> 19/19 against the kernel. LIVE, not fixtured: keel github-ingest against the real repository recorded GH#38 as st042 with its URL, and an immediate re-ingest REFUSED naming the URL. THE ASSERTIONS THAT COULD FAIL AND DID: F9 failed three times before passing - twice because migrate correctly refuses (no git, dirty tree) and once because it found issue314, a real defect. F5 failed because it asserted a title the command does not print. Three of the first-run failures were MY TESTS being wrong while the product was right, which is recorded because a suite whose early failures are all product defects is usually asserting what its author already believed."; }
    verification federationPlatformReviewGate : Test { :>> id = "4ed6920f-c692-4942-8765-72673da99aa9"; :>> title = "Sprint 500 review gate — three passes per D0172"; :>> createdAt = "2026-08-30"; :>> createdBy = "claudeOpus5"; :>> method = VerificationMethod::inspect; :>> procedureText = "THE PANEL RAN TWICE, which is the review. ROUND 2 over the design (pf41-pf45): four standing defeaters, two UNSOUND - the claims tested only a project's birth, and the network policy would have reported green while never touching GitHub. Both were fixed before a line was written; F9 exists because of the first and found issue314. ROUND 3 over the built suite (pf46-pf50): one verdict got WORSE, not better - F3b's vocabulary check is a hand-picked list of four strings, which is the overfit lens applied to the measurability fix, and it is recorded UNSOUND rather than defended. pf46 records a NARROWING: at depth the claim was weakened from 'can commit' to 'is warned', which is honest but strictly less than F1 claims elsewhere and a green run would not show it."; }
    verification federationPlatformCloseOutGate : Test { :>> id = "f0d8631b-c3b8-411d-9e63-493e38b61d15"; :>> title = "Sprint 500 closeOut gate (autonomous, D0049)"; :>> createdAt = "2026-08-30"; :>> createdBy = "claudeOpus5"; :>> method = VerificationMethod::inspect; :>> procedureText = "CLOSED with its residuals named. The seven questions have empirical answers: numbering resets cleanly, purpose separation holds at the namespace level, processes are picked up, a downstream-authored unit reaches a sibling, ingestion works live and idempotently, initialisation is complete but WARNS at depth rather than working there, and the upstream issue path now exists where it did not. Open: pf46 (depth remains uncommittable), pf49 (the manifest checks existence, not execution), pf50 (the vocabulary list must be derived, not listed)."; }
    verification federationPlatformRetroGate : Test { :>> id = "cbbbd590-4566-4c6d-85ae-5bc7d12031b4"; :>> title = "Sprint 500 retro gate (autonomous, D0049)"; :>> createdAt = "2026-08-30"; :>> createdBy = "claudeOpus5"; :>> method = VerificationMethod::analyze; :>> procedureText = "FINDING, and it is about the method rather than the product: the panel-before-implementation step paid for itself in a single claim. pf42 called the design unsound for testing only a project's birth; F9 was added for its second week; F9 found issue314, where an engine upgrade silently reverts a project's adoption choices - a control turned off by the project coming back on, or one it had on being turned off, with no Decision anywhere. Nothing else in this session would have found that: it is invisible to every guard, because the guards run inside a project and this is a change made TO the project from outside. SECOND FINDING, uncomfortable: the same shell-backtick trap fired for the THIRD time while recording these very findings, corrupting issue314's description and running keel deactivate against this repository. My own memory carries the warning verbatim and it did not help. D0224 fixed the instance (record decision) and not the class (every write path taking prose by argument); record issue is fixed here and the class is named in issue315 rather than claimed as closed."; }
}
