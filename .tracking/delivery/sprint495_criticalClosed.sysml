// ProjectDeliveryS495 — Sprint 495: the Critical closes with its owed proof; the intake resolver discharges on its landed evidence. EXECUTE. 3 pts.
package ProjectDeliveryS495 {
    private import EngineElement::*;
    private import EngineWork::*;
    private import EngineVerification::*;
    private import EngineRelationships::*;

    #CharteredBy dependency from criticalClosedStory to d0258;

    part criticalClosedStory : Story {
        :>> id = "b871ec28-644c-40bb-aec7-4a23e4378b18";
        :>> title = "Sprint 495: dcRenameIsAChange + dcIntakeHasAWritePath discharge - the first two items of the assessed frontier (3 pts)";
        :>> createdAt = "2026-08-29"; :>> createdBy = "claudeOpus5"; :>> kind = WorkKind::code; :>> priority = WorkPriority::p0; :>> owner = "claudeOpus5"; :>> estimatedPoints = 3;
    }

    action def DeliveryRunS495 {
        action storyCriticalClosed;
        verification storyCriticalClosedDoD : Test { :>> id = "763747c5-0d71-4476-8450-6483b5ed4424"; :>> method = VerificationMethod::test; :>> procedureText = "The assessed frontier's first two items, worked under D0258's fresh ranking. dcRenameIsAChange (CRITICAL issue273): the guard-side fix predated this sprint; the DoD owed its discriminating VERIFY, delivered as keystone_sees_renames.rs 3/3 - a git-confirmed R09x rename of a locked file with a blocking->warning downgrade FAILS naming the path; a fresh init's first commit still PASSES (issue272 survives); a non-ASCII C-quoted rename still FAILS. dcIntakeHasAWritePath (issues 289+300): discharges on its four landed unit tests plus thirty-six live Statements and fifty-two UserStories recorded through the API this arc. VERIFY: probe 3/3; intake_write suite 4/4; clippy; full suite 0 FAILED; issues 273/289/300 compute closed.: DELIVERED BACKLOG ITEMS: <items>. <what done means, verified how>."; }
        // RAN: // RAN: keystone_sees_renames 3/3; intake_write 4/4; clippy clean; workspace suite 0 FAILED; guard sprint-coverage green with this record
        part storyCriticalClosedDoDR1 : TestResult { :>> id = "356806d4-0ba8-429b-a637-83133caaa2e0"; :>> outcome = VerdictKind::pass; :>> judgedAgainst = "fd7a064"; :>> judgedAt = "2026-08-29"; :>> judgedBy = "claudeOpus5"; }
    }

    verification criticalClosedRefineGate : Test { :>> id = "5862ce88-cbbb-42af-897d-3bc38a655e9e"; :>> title = "Sprint 495 refine gate (DoR)"; :>> createdAt = "2026-08-29"; :>> createdBy = "claudeOpus5"; :>> method = VerificationMethod::inspect; :>> procedureText = "READY: both items led the frontier after the D0258 severity reorder; both DoDs were authored by prior sittings with explicit VERIFY clauses, so this sprint's scope was reading those clauses and delivering exactly what they owed - no scope invention."; }
    verification criticalClosedStandupGate : Test { :>> id = "ae300fbe-36db-48ae-ba0e-968e32f89a55"; :>> title = "Sprint 495 standup gate"; :>> createdAt = "2026-08-29"; :>> createdBy = "claudeOpus5"; :>> method = VerificationMethod::inspect; :>> procedureText = "One fixture lesson: the probe's first rename staged D+A because a 3-line file's one-word change fell below git's similarity threshold - the in-fixture R-assertion caught it before a vacuous pass could ship (the reverify-probe lesson, now standard practice). And the python-replace-on-Rust-strings escaping trap no-oped silently AGAIN; the Edit tool is the recorded remedy (memory: syntax-bearing content uses the Write/Edit tools)."; }
    verification criticalClosedImplementGate : Test { :>> id = "ba203fd0-9cd0-42a0-9065-12779044841c"; :>> title = "Sprint 495 implement gate"; :>> createdAt = "2026-08-29"; :>> createdBy = "claudeOpus5"; :>> method = VerificationMethod::test; :>> procedureText = "RAN: cargo test --release -p keel-cli --test keystone_sees_renames -> 3/3 (after the fixture strengthened to a real R09x); cargo test -p keel-cli --lib intake_write -> 4/4; clippy -D warnings clean; cargo test --workspace --release -> 0 FAILED; keel guard -> sprint-coverage was the LAST failure, resolved by this very record naming both tasks."; }
    verification criticalClosedReviewGate : Test { :>> id = "cce704a5-a99b-414e-b3e2-f1b076df1eec"; :>> title = "Sprint 495 review gate — three passes per D0172"; :>> createdAt = "2026-08-29"; :>> createdBy = "claudeOpus5"; :>> method = VerificationMethod::inspect; :>> procedureText = "THREE PASSES. (1) THE PROBE DISCRIMINATES: the fixture ASSERTS git staged an R rename before testing the guard, so a below-threshold D+A cannot masquerade as coverage of the rename class. (2) NO DOUBLE CREDIT: the guard fix itself was Fable's panel-driven work; this sprint claims only the owed proof and says so in the stamped evidence. (3) THE INTAKE DISCHARGE IS EVIDENCE-BACKED, not ceremonial: every VERIFY clause in its DoD maps to a named landed test or a live record count."; }
    verification criticalClosedCloseOutGate : Test { :>> id = "f875831b-430a-437c-8285-edf73593a071"; :>> title = "Sprint 495 closeOut gate (autonomous, D0049)"; :>> createdAt = "2026-08-29"; :>> createdBy = "claudeOpus5"; :>> method = VerificationMethod::inspect; :>> procedureText = "CLOSED. Criticals on the frontier: zero. Frontier 21 -> 18. issues 273, 289, 300 compute closed. Next by assessed order: activateDoesNotLoseFacts (High, issue293), then the recall pair."; }
    verification criticalClosedRetroGate : Test { :>> id = "9aabf189-cf81-460d-9731-004ad857da78"; :>> title = "Sprint 495 retro gate (autonomous, D0049)"; :>> createdAt = "2026-08-29"; :>> createdBy = "claudeOpus5"; :>> method = VerificationMethod::analyze; :>> procedureText = "FINDING: the frontier's Critical turned out to be a PROOF debt, not a code debt - the fix had landed days ago and nothing tracked that its DoD's VERIFY was never run. CORRECTED THE SAME DAY, and the correction is the finding worth keeping: I wrote that this was 'the same shape as sprint 483' and it is NOT. Sprint 483 was finished AND verified with its receipt never written - the model served finished work as open. The Critical was the opposite: the code had landed but the DoD's required two-direction VERIFY had never been run, and no test covered the rename class at all (confirmed: keystone_sees_renames.rs is the first). Proof is part of done here, the DoD said so explicitly, and the frontier was RIGHT to hold it open. Calling a correct flag a 'proof debt found by the frontier' framed the model as erring when it was not - and that framing, repeated, becomes pressure to relax done to mean 'code landed', which is precisely the move that turned issue272's fix into issue273's Critical. ONE real instance in 496 sprints, not a pattern. NEW CONTROL FILED anyway, because the one instance has a cheap invariant behind it: guard 55 sprint-closure (D0260), a ratchet on a record already at 496/496, exempting the in-progress sprint so it cannot become the issue272 lockout, armed by four probes including the refuse case."; }
}
