// ProjectDeliveryS252 — Sprint 252: the priority-inversion guard (issue084, D0130). Recorded ORDER
// vs recorded SEVERITY. Caught its own author's ordering on first run. EXECUTE. 2 pts.
package ProjectDeliveryS252 {
    private import EngineElement::*;
    private import EngineWork::*;
    private import EngineVerification::*;
    private import EngineRelationships::*;

    #CharteredBy dependency from priorityInversionStory to d0130;

    part priorityInversionStory : Story {
        :>> id = "0d6a0001-0813-4a01-9b3e-0000001a0001";
        :>> title = "Sprint 252: priority-inversion guard — a ready item outranking >= High work (2 pts)";
        :>> createdAt = "2026-08-13"; :>> createdBy = "claudeOpus5"; :>> kind = WorkKind::code; :>> priority = WorkPriority::p0; :>> owner = "claudeOpus5"; :>> estimatedPoints = 2;
    }

    action def DeliveryRunS252 {
        action storyPriorityInversion;
        verification storyPriorityInversionDoD : Test { :>> id = "0d6a0002-0813-4a02-9b3e-0000001a0002"; :>> method = VerificationMethod::test; :>> procedureText = "Delivers dcPriorityInversion (issue084/D0130). DEFECT CLOSED: D0052 makes declaration order the priority and requires auto-following the ranked frontier, but nothing compared recorded ORDER against recorded SEVERITY, so a mis-ordered backlog was indistinguishable from a curated one — keelArchViews (issue069, Low) ranked #1 by append accident while dcStaleKernelInstanceGate (issue081, High) ranked 14th. BUILT: guard `priority-inversion` (21 guards; 17 hard + 4 warning-only) reporting a ready item that outranks work resolving a >= High Issue, computed from orient's priority-ordered ready set plus each task's #Resolves-linked Issue severity. WARNING-level and never blocking: deferring a High item behind an enabler can be correct, so the value is VISIBILITY, not enforcement. Threshold >= High so ordinary Medium/Low triage ordering makes no noise; relative order AMONG >= High items is left alone as judgment. VERIFY (measured): on first run it flagged FOUR inversions in the reordering this same thread had authored in sprint 248 — dcDeclaredMarkers resolves issue077 (High) yet ranked 8th, below keelInLoopGates, dcEnrollment, dcWorkClaim and dcLandLoop, all issue-free. Fixed by REORDERING the file (dcDeclaredMarkers moved to #4), not by rationalising; guard then reports 0. clippy clean; 154 tests incl. two new pure-function tests (flags lower/no-severity items ranked above a High one; clean when severity matches order and among peer >= High items); validate + all 21 guards + check-engine green at f1e4469."; }
        part storyPriorityInversionDoDR1 : TestResult { :>> id = "0d6a0003-0813-4a03-9b3e-0000001a0003"; :>> outcome = VerdictKind::pass; :>> judgedAgainst = "f1e4469"; :>> judgedAt = "2026-08-13"; :>> judgedBy = "claudeOpus5"; }
    }

    verification piRefineGate : Test { :>> id = "0d6a0004-0813-4a04-9b3e-0000001a0004"; :>> title = "Sprint 252 refine gate (DoR)"; :>> createdAt = "2026-08-13"; :>> createdBy = "claudeOpus5"; :>> method = VerificationMethod::inspect; :>> procedureText = "DoR: taken from the top of the ranked frontier by ORDER (D0052), chartered by the accepted d0130. Scope: the computed check + fixing whatever it finds. The DoD's own acceptance criterion — that the pre-reorder state reproduces a flag and the reordered state is clean — was satisfied in an unplanned way: the reordered state was NOT clean, so the criterion did real work instead of rubber-stamping. estimatedPoints=2. DoR met."; }
    part piRefineGateR1 : TestResult { :>> id = "0d6a0005-0813-4a05-9b3e-0000001a0005"; :>> outcome = VerdictKind::pass; :>> judgedAgainst = "f1e4469"; :>> judgedAt = "2026-08-13"; :>> judgedBy = "claudeOpus5"; }

    verification piStandupGate : Test { :>> id = "0d6a0006-0813-4a06-9b3e-0000001a0006"; :>> title = "Sprint 252 standup gate"; :>> createdAt = "2026-08-13"; :>> createdBy = "claudeOpus5"; :>> method = VerificationMethod::inspect; :>> procedureText = "Approach: reuse orient's ready set rather than re-deriving readiness, so the guard and the frontier can never disagree about what is ready; read severity through the existing #Resolves edge instead of inventing a priority field (priority stays ORDER, per D0052 — this only reports disagreement). Set the threshold at >= High so the guard reports contradictions, not preferences. No blockers."; }
    part piStandupGateR1 : TestResult { :>> id = "0d6a0007-0813-4a07-9b3e-0000001a0007"; :>> outcome = VerdictKind::pass; :>> judgedAgainst = "f1e4469"; :>> judgedAt = "2026-08-13"; :>> judgedBy = "claudeOpus5"; }

    verification piImplementGate : Test { :>> id = "0d6a0008-0813-4a08-9b3e-0000001a0008"; :>> title = "Sprint 252 implement gate"; :>> createdAt = "2026-08-13"; :>> createdBy = "claudeOpus5"; :>> method = VerificationMethod::test; :>> procedureText = "Implemented at f1e4469. The four findings on first run were treated as a real defect in the backlog and fixed by moving declarations, then the guard was re-run to confirm 0 — the same read-back-the-computed-answer discipline the response contract now mandates. dcDeclaredMarkers now ranks #4 and needs frozen-schema sign-off; per D0052 that is surfaced for the human while work proceeds with the next item needing none, rather than the item being demoted to make the frontier look tidy."; }
    part piImplementGateR1 : TestResult { :>> id = "0d6a0009-0813-4a09-9b3e-0000001a0009"; :>> outcome = VerdictKind::pass; :>> judgedAgainst = "f1e4469"; :>> judgedAt = "2026-08-13"; :>> judgedBy = "claudeOpus5"; }

    verification piReviewGate : Test { :>> id = "0d6a000a-0813-4a0a-9b3e-0000001a000a"; :>> title = "Sprint 252 review gate"; :>> createdAt = "2026-08-13"; :>> createdBy = "claudeOpus5"; :>> method = VerificationMethod::inspect; :>> procedureText = "Reviewed. This is the third consecutive control whose FIRST RUN found more than the instance that motivated it (duplicate-identity found 26, verification-trace found 103, priority-inversion found 4 in a reordering I had just called curated). The consistent lesson is that a defect noticed once is almost never isolated, and that the author of a fix is a poor judge of its scope. Correct here: the finding was against MY OWN work from four sprints earlier and was fixed rather than argued with. Weakness accepted: the guard cannot distinguish a deliberate deferral from an accidental one, which is why it warns and its message explicitly invites 'if that is deliberate say so' — a deliberate deferral should be recorded as a Decision, not left implicit in file order."; }
    part piReviewGateR1 : TestResult { :>> id = "0d6a000b-0813-4a0b-9b3e-0000001a000b"; :>> outcome = VerdictKind::pass; :>> judgedAgainst = "f1e4469"; :>> judgedAt = "2026-08-13"; :>> judgedBy = "claudeOpus5"; }

    verification piCloseOutGate : Test { :>> id = "0d6a000c-0813-4a0c-9b3e-0000001a000c"; :>> title = "Sprint 252 closeOut gate (autonomous, D0049)"; :>> createdAt = "2026-08-13"; :>> createdBy = "claudeOpus5"; :>> method = VerificationMethod::inspect; :>> procedureText = "Autonomous closeOut (D0049). dcPriorityInversion carries a passing DoD TestResult at f1e4469; validate + all 21 guards + check-engine green; 154 tests; clippy clean; the frontier is now inversion-free. Three of the four tracking-mechanism controls from sprint 248 are delivered (verification-trace, attestation-substance, priority-inversion); dcRetroToBacklog remains. SURFACED FOR THE HUMAN: dcDeclaredMarkers now ranks #4 and requires frozen-schema sign-off (§2.5) before it can be executed."; }
    part piCloseOutGateR1 : TestResult { :>> id = "0d6a000d-0813-4a0d-9b3e-0000001a000d"; :>> outcome = VerdictKind::pass; :>> judgedAgainst = "f1e4469"; :>> judgedAt = "2026-08-13"; :>> judgedBy = "claudeOpus5"; }

    verification piRetroGate : Test { :>> id = "0d6a000e-0813-4a0e-9b3e-0000001a000e"; :>> title = "Sprint 252 retro gate (autonomous, D0049)"; :>> createdAt = "2026-08-13"; :>> createdBy = "claudeOpus5"; :>> method = VerificationMethod::analyze; :>> procedureText = "Autonomous retro (D0049), under the issue085 obligation. WELL: (1) the guard was pointed at the current state immediately and its finding accepted against my own prior work rather than rationalised — the fix was a file reorder, which is what D0052 says reprioritising IS; (2) the DoD's acceptance criterion did real work: it predicted the reordered state would be clean, it was not, and that discovery was the sprint's main value. AVOIDABLE-ISSUE 1: in sprint 248 I hand-curated a priority order and described it as correct without any check — the very failure issue084 describes, committed while writing issue084. That is now guarded, so no new item; recorded here because the guard existing does not erase that the ordering shipped wrong for four sprints. OBSERVATION (no item): three consecutive controls have each found far more on first run than the instance that motivated them (26, 103, 4-in-my-own-work). The pattern is strong enough that the next control should be built expecting a corpus-wide finding, and its DoD should say so rather than predicting a count. Estimate 2 pts, delivered."; }
    part piRetroGateR1 : TestResult { :>> id = "0d6a000f-0813-4a0f-9b3e-0000001a000f"; :>> outcome = VerdictKind::pass; :>> judgedAgainst = "f1e4469"; :>> judgedAt = "2026-08-13"; :>> judgedBy = "claudeOpus5"; }
}
