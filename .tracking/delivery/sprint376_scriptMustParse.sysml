// ProjectDeliveryS376 — Sprint 376: the deck's script NEVER parsed. Three syntax errors, found in one
// node --check the moment the instrument was finally read. EXECUTE. 3 pts.
package ProjectDeliveryS376 {
    private import EngineElement::*;
    private import EngineWork::*;
    private import EngineVerification::*;
    private import EngineRelationships::*;

    #CharteredBy dependency from scriptParseStory to d0171;

    part scriptParseStory : Story {
        :>> id = "0d800730-0814-6730-9b3e-000000300730";
        :>> title = "Sprint 376: deck v5 — the first version whose script parses (3 pts)";
        :>> createdAt = "2026-08-21"; :>> createdBy = "claudeOpus5"; :>> kind = WorkKind::code; :>> priority = WorkPriority::p0; :>> owner = "claudeOpus5"; :>> estimatedPoints = 3;
    }

    action def DeliveryRunS376 {
        action storyScriptParse;
        verification storyScriptParseDoD : Test { :>> id = "0d800731-0814-6731-9b3e-000000300731"; :>> method = VerificationMethod::test; :>> procedureText = "DELIVERED BACKLOG ITEMS: dcEmittedJsMustParse declared and cleared. THE HUMAN READ THE INSTRUMENT - script did not finish - AND ASKED WHY, and the answer took one mechanical check that had been available all along: node --check on the extracted script found THREE syntax errors. (1) Sprint 372's regex fix appended an end-of-line comment inside a single-line .then(), commenting out its closing braces. (2) A stray fragment of a replaced multi-line push survived an old edit as a bare line. (3) A heredoc-eaten backslash-n split L.join's string literal in two - the shell-mangling class, fossilised in the artifact since the earliest versions. A SYNTAX ERROR RUNS NOTHING, so the script was dead in EVERY version: all four button reports were this one defect, and the three real contract fixes shipped along the way were untestable. FIXED: the .then() is multi-line so no line-scoped edit can swallow structure; the fragment deleted; the join uses String.fromCharCode(10), which no authoring layer can eat. node --check now PASSES and is pass ZERO of the skill's checklist. Published as deck v5, visible in the sub-line. The demo remains theirs. validate 408 clean; check-engine clean; 38 guards ALL PASS."; }
        part storyScriptParseDoDR1 : TestResult { :>> id = "0d800732-0814-6732-9b3e-000000300732"; :>> outcome = VerdictKind::pass; :>> judgedAgainst = "1b78b12"; :>> judgedAt = "2026-08-21"; :>> judgedBy = "claudeOpus5"; }
    }

    verification spRefineGate : Test { :>> id = "0d800733-0814-6733-9b3e-000000300733"; :>> title = "Sprint 376 refine gate (DoR)"; :>> createdAt = "2026-08-21"; :>> createdBy = "claudeOpus5"; :>> method = VerificationMethod::inspect; :>> procedureText = "DoR. The self-report marker built in sprint 371 finally did its one job: the human read `script did NOT finish` and asked why. The route was mechanical from there - extract, node --check, read the line number. Scoped to: fix the three errors in the generator, make the parse check pass zero of the checklist, publish v5. estimatedPoints=3."; }
    part spRefineGateR1 : TestResult { :>> id = "0d800734-0814-6734-9b3e-000000300734"; :>> outcome = VerdictKind::pass; :>> judgedAgainst = "1b78b12"; :>> judgedAt = "2026-08-21"; :>> judgedBy = "claudeOpus5"; }

    verification spStandupGate : Test { :>> id = "0d800735-0814-6735-9b3e-000000300735"; :>> title = "Sprint 376 standup gate"; :>> createdAt = "2026-08-21"; :>> createdBy = "claudeOpus5"; :>> method = VerificationMethod::inspect; :>> procedureText = "Approach: run the parser, fix what it names, run it again until silent - three iterations, three distinct errors, no theorizing between them. The contrast with the previous four rounds is the lesson: each earlier round built a plausible mechanism from the contract and shipped it; this round asked a parser and was done in minutes. No blockers."; }
    part spStandupGateR1 : TestResult { :>> id = "0d800736-0814-6736-9b3e-000000300736"; :>> outcome = VerdictKind::pass; :>> judgedAgainst = "1b78b12"; :>> judgedAt = "2026-08-21"; :>> judgedBy = "claudeOpus5"; }

    verification spImplementGate : Test { :>> id = "0d800737-0814-6737-9b3e-000000300737"; :>> title = "Sprint 376 implement gate"; :>> createdAt = "2026-08-21"; :>> createdBy = "claudeOpus5"; :>> method = VerificationMethod::test; :>> procedureText = "ALL THREE ERRORS WERE MY OWN EDITS, and each is an instance of a class this session already named. The .then() comment: a line-scoped regex appending an end-of-line comment - on a single-line statement the comment eats the rest of the statement, which is a NEW corollary now in the skill. The stray fragment: an anchor-based replace that left part of the old text - the anchor-edit class, occurrence four. The split string: heredoc backslash-eating, occurrence EIGHT, fossilised in the published artifact possibly since v1. THE VERIFICATION GAP IS THE REAL FINDING: every audit grepped strings - marker present, marker last, counts right - and a file full of correct strings parses as nothing. I checked spelling, never grammar, across four rounds and five publishes. The parse check now precedes every string check because a parse failure makes them all meaningless. THE HONEST CAVEAT: node --check validates syntax, not runtime - a throw at line one would still kill the listeners and only the marker would say so. Syntax was the killer here; the marker plus the debug log covers the runtime half."; }
    part spImplementGateR1 : TestResult { :>> id = "0d800738-0814-6738-9b3e-000000300738"; :>> outcome = VerdictKind::pass; :>> judgedAgainst = "1b78b12"; :>> judgedAt = "2026-08-21"; :>> judgedBy = "claudeOpus5"; }

    verification spReviewGate : Test { :>> id = "0d800739-0814-6739-9b3e-000000300739"; :>> title = "Sprint 376 review gate — three passes per D0172"; :>> createdAt = "2026-08-21"; :>> createdBy = "claudeOpus5"; :>> method = VerificationMethod::inspect; :>> procedureText = "PASS 1, CLAIMS: node --check exits 0 on the extracted script; 51/51 cards and notes carry data-id; zero synced text writes; v5 visible - all counted from the emitted file, and the FIRST of these is now the one that gates the rest. PASS 2, BOUNDARY: the extractor was itself born broken (my inline python -c mangled its own path expression - shell-mangling in the diagnostic tooling) and was rewritten as a file; the check runs on the emitted artifact, so a generator change cannot skip it silently. PASS 3, THE SPRINT'S OWN DIFF: the multi-line .then() rewrite was re-checked with node rather than assumed - it is exactly the shape my regex broke, and editing it by hand under time pressure is how the class recurs. WHAT A REVIEWER SHOULD ATTACK: I claimed three rounds of fixes were REAL contract violations, but with the script dead the whole time, none was ever falsified - the load-time write, the async isolation and the data-id addressing are all still inferences. If v5's taps latch, all three inferences become moot in the best way; if they fail, the debug log finally RUNS and will say why."; }
    part spReviewGateR1 : TestResult { :>> id = "0d80073a-0814-673a-9b3e-00000030073a"; :>> outcome = VerdictKind::pass; :>> judgedAgainst = "1b78b12"; :>> judgedAt = "2026-08-21"; :>> judgedBy = "claudeOpus5"; }

    verification spCloseOutGate : Test { :>> id = "0d80073b-0814-673b-9b3e-00000030073b"; :>> title = "Sprint 376 closeOut gate (autonomous, D0049)"; :>> createdAt = "2026-08-21"; :>> createdBy = "claudeOpus5"; :>> method = VerificationMethod::inspect; :>> procedureText = "Autonomous closeOut (D0049). issue191 recorded and cleared by dcEmittedJsMustParse; the skill gains rule 0 (the emitted script must parse, node --check, before every string check) with the regex-comment corollary; deck v5 republished to the same URL. The demo confirmation remains theirs, for the fifth and - if the parser is to be believed - first genuinely testable time. validate 408 clean; check-engine clean; 38 guards ALL PASS."; }
    part spCloseOutGateR1 : TestResult { :>> id = "0d80073c-0814-673c-9b3e-00000030073c"; :>> outcome = VerdictKind::pass; :>> judgedAgainst = "1b78b12"; :>> judgedAt = "2026-08-21"; :>> judgedBy = "claudeOpus5"; }

    verification spRetroGate : Test { :>> id = "0d80073d-0814-673d-9b3e-00000030073d"; :>> title = "Sprint 376 retro gate (autonomous, D0049)"; :>> createdAt = "2026-08-21"; :>> createdBy = "claudeOpus5"; :>> method = VerificationMethod::analyze; :>> procedureText = "Autonomous retro (D0049). AVOIDABLE-ISSUE SCAN under rcRecurrence: (1) string-grep verification of executable content is the same shape as verify-the-file-not-the-screen, occurrence THREE of the family - now closed structurally by rule 0, tracked under dcEmittedJsMustParse; (2) shell-mangling occurrence EIGHT (the extractor's own inline python), folded into dcAuthorViaWriteTool - and the honest observation is that the RULE keeps being right and I keep reaching for the shell anyway when the snippet feels tiny, so the rule now says: the size of the snippet is not a factor, backslashes and quotes are; (3) the anchor-edit fragment is occurrence FOUR of that class, already covered by the assert-and-diff rule - the fragment predates the rule, no new item. WELL: (1) the human's four-word report was treated as an instrument reading rather than a complaint, and the answer was mechanical within minutes; (2) three errors were fixed by running the parser three times, not by theorizing once; (3) the review gate downgrades my three earlier fixes to INFERENCES honestly, since a dead script falsifies nothing; (4) the join fix uses String.fromCharCode(10), which removes the escape from every layer permanently. Estimate 3 pts, delivered."; }
    part spRetroGateR1 : TestResult { :>> id = "0d80073e-0814-673e-9b3e-00000030073e"; :>> outcome = VerdictKind::pass; :>> judgedAgainst = "1b78b12"; :>> judgedAt = "2026-08-21"; :>> judgedBy = "claudeOpus5"; }
}
