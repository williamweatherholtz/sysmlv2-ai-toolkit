// ProjectDeliveryS505 — Sprint 505: one command that checks all bases, and three fixes from the human’s corrections. EXECUTE. 5 pts.
package ProjectDeliveryS505 {
    private import EngineElement::*;
    private import EngineWork::*;
    private import EngineVerification::*;
    private import EngineRelationships::*;

    #CharteredBy dependency from statusAllBasesStory to d0270;

    part statusAllBasesStory : Story {
        :>> id = "2487fbf1-9d5a-43d6-90d4-e73f6842c9aa";
        :>> title = "Sprint 505: keel status, the decision-surfacing process, and a summary standard that can be judged (5 pts)";
        :>> createdAt = "2026-09-01"; :>> createdBy = "claudeOpus5"; :>> kind = WorkKind::code; :>> priority = WorkPriority::p0; :>> owner = "claudeOpus5"; :>> estimatedPoints = 5;
    }

    action def DeliveryRunS505 {
        action storyStatusAllBases;
        verification storyStatusAllBasesDoD : Test { :>> id = "94510f5d-d052-4eeb-9141-cad5c11d1980"; :>> method = VerificationMethod::test; :>> procedureText = "THREE CORRECTIONS FROM THE HUMAN, all landed. (1) D0269 decisionSurfacing + skill: pending judgments render into the exec-summary artifact, publish to a durable URL, and LEAD the response - 'Don't bury it under past messages'. (2) The exec-summary SKILL gains a sufficiency rule and a driver test, because 'WHAT DECIDES IT: picking which ones are good' is circular and left them to go find the item; a tab must now quote the item, say what accepting binds, make the fork concrete clause-vs-clause, separate evidence from assumption, and say what I do with each answer. (3) The stop hook's oversight nag is REMOVED entirely along with its dead console probe - it prescribed how to look at a queue while guessing from an env var whether they were at a terminal or on a phone. DELIVERED (D0270): keel status - engine pin vs binary, library units behind AND never-imported, model honesty, work frontier, and the CI verdict for HEAD, which is where the asynchronous CI surfacing they chose lands. VERIFY: status_distinguishes_unknown 4/4 asserting the UNKNOWN path specifically; clippy clean; the live run surfaced two units this project had never imported.: DELIVERED BACKLOG ITEMS: <items>. <what done means, verified how>."; }
        // RAN: // RAN: keel status live on this repo (5 sections, surfaced 2 never-imported units); status_distinguishes_unknown 4/4 on the UNKNOWN paths; exec-summary browser suite 8/8; clippy -D warnings clean
        part storyStatusAllBasesDoDR1 : TestResult { :>> id = "7287f9c3-c315-4fe8-ae8f-baafec9dd7d7"; :>> outcome = VerdictKind::pass; :>> judgedAgainst = "a16624c"; :>> judgedAt = "2026-08-31"; :>> judgedBy = "claudeOpus5"; }
    }

    verification statusAllBasesRefineGate : Test { :>> id = "3914354c-f2d0-4d56-a80b-450d9fa9e44f"; :>> title = "Sprint 505 refine gate (DoR)"; :>> createdAt = "2026-09-01"; :>> createdBy = "claudeOpus5"; :>> method = VerificationMethod::inspect; :>> procedureText = "READY: all four decisions on the summary page were adjudicated (st062) and the acceptance for nAutonomyBoundedByProof is recorded as a method=confirmation result naming the fork they chose against. Scope came from their NOTE, which widened the task from a unit-drift report to a full state readout - recorded as a requirement rather than folded in silently, because it changes what the task must deliver."; }
    verification statusAllBasesStandupGate : Test { :>> id = "d87f65c8-bfa8-4ff5-a229-73452fbf5a1d"; :>> title = "Sprint 505 standup gate"; :>> createdAt = "2026-09-01"; :>> createdBy = "claudeOpus5"; :>> method = VerificationMethod::inspect; :>> procedureText = "No blocker. One scoping judgment recorded: the acceptance covers nAutonomyBoundedByProof ONLY. nUnattendedCurrency was never contested and is not accepted by proximity - it stays on the decision page and is carried until answered or withdrawn, which is D0269's own dsCarry step applied to itself on its first day."; }
    verification statusAllBasesImplementGate : Test { :>> id = "dfc30136-a426-47da-921e-9efb0802f80a"; :>> title = "Sprint 505 implement gate"; :>> createdAt = "2026-09-01"; :>> createdBy = "claudeOpus5"; :>> method = VerificationMethod::test; :>> procedureText = "RAN: keel status on this repository -> five sections, and it immediately reported something I did not know (the library holds seven units, two never imported here). status_distinguishes_unknown 4/4: an unreachable library reports UNKNOWN not zero drift; a tree with no repository reports UNKNOWN not passed; the closing line counts attention and unknown SEPARATELY; and the live corpus is really read rather than an empty one. cargo clippy -D warnings clean - two lints fixed at the root (a const fn, and rfind over filter().next_back()), none suppressed. The exec-summary browser suite 8/8 after the page was rebuilt to the new standard; its word budgets rejected two `why` lines and both were tightened rather than exempted."; }
    verification statusAllBasesReviewGate : Test { :>> id = "1ece818e-51f1-4a0d-986c-44ee0cc9a7bc"; :>> title = "Sprint 505 review gate — three passes per D0172"; :>> createdAt = "2026-09-01"; :>> createdBy = "claudeOpus5"; :>> method = VerificationMethod::inspect; :>> procedureText = "THREE PASSES. (1) DOES UNKNOWN SURVIVE: three of the four probes assert the UNKNOWN path rather than the happy path, because a status screen is the worst place for the pass-at-zero hazard this codebase has now caught four times - it exists to be believed at a glance. (2) DOES STATUS CHANGE WHAT IT REPORTS: no section syncs, migrates or writes; a status command that mutates cannot be run to find out where you stand. (3) IS THE SUMMARY STANDARD REAL OR A PROMISE: it is in the SKILL, not only in this page - the fix was applied where the next summary will read it, and the page was rebuilt to demonstrate it rather than the reverse."; }
    verification statusAllBasesCloseOutGate : Test { :>> id = "89be9426-1733-4a11-af6f-df45036c15f4"; :>> title = "Sprint 505 closeOut gate (autonomous, D0049)"; :>> createdAt = "2026-09-01"; :>> createdBy = "claudeOpus5"; :>> method = VerificationMethod::inspect; :>> procedureText = "CLOSED. dcLibraryStatusShowsDrift is delivered wider than its DoD asked. The stop hook now speaks only when the model is dishonest. One decision remains genuinely open and is carried, not quietly dropped: nUnattendedCurrency's acceptance."; }
    verification statusAllBasesRetroGate : Test { :>> id = "a6a7467a-b7e4-4942-8e22-6bfe8871f2f1"; :>> title = "Sprint 505 retro gate (autonomous, D0049)"; :>> createdAt = "2026-09-01"; :>> createdBy = "claudeOpus5"; :>> method = VerificationMethod::analyze; :>> procedureText = "FINDING: three corrections in one turn, and all three were the same failure wearing different clothes - I produced output that was accurate and unusable. The decisions were reported honestly at the BOTTOM of long turns; the summary tabs were well-formed but could not be judged without opening the repository; the stop hook stated a true count and then prescribed a remedy for a location it was guessing at. None of it was dishonest and all of it wasted their attention. WHAT I TOOK FROM IT: accuracy is table stakes and it is not the deliverable. The test for a report is not 'is this true' but 'can they act on it without doing work I should have done'. That is now written into the exec-summary skill as the driver test, which is the only one of the three that will bind a future turn without me remembering this one."; }
}
