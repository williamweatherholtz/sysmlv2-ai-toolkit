// =====================================================================
// ProjectDeliveryS20 — Sprint 20: reverifyDeliverable (1 pt).
// Story: re-verify the deliverable-manifest tasks at HEAD (cargo test + clippy +
//        parity_check) and append fresh TestResults via the write API to clear the
//        12 deliverable-suspect items raised by D0050. Closes issue014.
// Total: 1 pt  Ceremony: AUTONOMOUS (D0049); test-backed, nothing to confirm (D0051).
// =====================================================================
package ProjectDeliveryS20 {
    private import EngineElement::*;
    private import EngineWork::*;
    private import EngineVerification::*;

    part reverifyDeliverableStory : Story {
        :>> id = "6c538041-acfe-4f6e-bd3f-5b7c9d1e3e4c";
        :>> title = "Sprint 20: reverifyDeliverable (1 pt) — clear deliverable suspicion by re-verifying at HEAD";
        :>> createdAt = "2026-06-16";
        :>> createdBy = "wweatherholtz";
        :>> kind = WorkKind::code;
        :>> priority = WorkPriority::p2;
        :>> owner = "claudeOpus";
        :>> estimatedPoints = 1;
    }

    action def DeliveryRunS20 {
        action storyReverifyDeliverable;
        verification storyReverifyDeliverableDoD : Test { :>> id = "7d649153-bd0f-4f6e-ce40-6c8d0e2f3e4c"; :>> method = VerificationMethod::test; :>> procedureText = "reverifyDeliverableDoD in backlog (pass): cargo test + clippy + parity green at HEAD; DoDR2 appended (write API) for the 12 deliverable tasks; sysmlv2 orient suspect = 0."; }
        part storyReverifyDeliverableDoDR1 : TestResult { :>> id = "8e750264-ce10-4f6e-fe41-7d9e1f306151"; :>> outcome = VerdictKind::pass; :>> judgedAgainst = "724b19e"; :>> judgedAt = "2026-06-16"; :>> judgedBy = "claudeOpus"; }
    }

    // ---- ceremony gates (autonomous, D0049; test-backed, D0051: nothing to confirm) ----
    verification reverifyDeliverableRefineGate : Test {
        :>> id = "9f861375-df21-4f6e-1352-8e0f20417251";
        :>> title = "Sprint 20 refine gate (DoR)";
        :>> createdAt = "2026-06-16";
        :>> createdBy = "claudeOpus";
        :>> method = VerificationMethod::inspect;
        :>> procedureText = "Approach: re-verify deliverable-manifest tasks at HEAD (cargo test + clippy + parity_check green) and append DoDR2 via sysmlv2 append-result (write API) judged at HEAD, clearing the 12 deliverable-suspect items (D0050/issue014). estimatedPoints=1 (mechanical). Ready. DoD accepted.";
    }
    part reverifyDeliverableRefineGateR1 : TestResult { :>> id = "a0972486-e032-4f6e-2463-9f1031528251"; :>> outcome = VerdictKind::pass; :>> judgedAgainst = "724b19e"; :>> judgedAt = "2026-06-16"; :>> judgedBy = "claudeOpus"; }

    verification reverifyDeliverableStandupGate : Test {
        :>> id = "b1083597-f143-4f6e-3574-0a2142639251";
        :>> title = "Sprint 20 standup gate";
        :>> createdAt = "2026-06-16";
        :>> createdBy = "claudeOpus";
        :>> method = VerificationMethod::inspect;
        :>> procedureText = "Refine passed. reverifyDeliverable: re-verify + append DoDR2 x12. No blockers.";
    }
    part reverifyDeliverableStandupGateR1 : TestResult { :>> id = "c2194608-0254-4f6e-4685-1b3253740251"; :>> outcome = VerdictKind::pass; :>> judgedAgainst = "724b19e"; :>> judgedAt = "2026-06-16"; :>> judgedBy = "claudeOpus"; }

    verification reverifyDeliverableImplementGate : Test {
        :>> id = "d32a5719-1365-4f6e-5796-2c4364850251";
        :>> title = "Sprint 20 implement gate";
        :>> createdAt = "2026-06-16";
        :>> createdBy = "claudeOpus";
        :>> method = VerificationMethod::test;
        :>> procedureText = "cargo test (40) + clippy -D warnings + parity_check green at HEAD (724b19e); 12 DoDR2 appended via the write API (sysmlv2 append-result); sysmlv2 orient suspect = 0 (down from 12); self-consistency PASS.";
    }
    part reverifyDeliverableImplementGateR1 : TestResult { :>> id = "e43b682a-2476-4f6e-689a-3d5475960251"; :>> outcome = VerdictKind::pass; :>> judgedAgainst = "724b19e"; :>> judgedAt = "2026-06-16"; :>> judgedBy = "claudeOpus"; }

    verification reverifyDeliverableReviewGate : Test {
        :>> id = "f54c793b-3587-4f6e-79ab-4e6586a70251";
        :>> title = "Sprint 20 review gate";
        :>> createdAt = "2026-06-16";
        :>> createdBy = "claudeOpus";
        :>> method = VerificationMethod::inspect;
        :>> procedureText = "Diff reviewed: 12 DoDR2 results appended (write API, DoDR naming correct); suspect cleared; dogfooded the write API. Phase-3 scan: clean; no avoidable issues.";
    }
    part reverifyDeliverableReviewGateR1 : TestResult { :>> id = "065d804c-4698-4f6e-8abc-5f7697b80251"; :>> outcome = VerdictKind::pass; :>> judgedAgainst = "724b19e"; :>> judgedAt = "2026-06-16"; :>> judgedBy = "claudeOpus"; }

    verification reverifyDeliverableCloseOutGate : Test {
        :>> id = "176e915d-57a9-4f6e-9bcd-6a87a8c90251";
        :>> title = "Sprint 20 closeOut gate (autonomous, D0049)";
        :>> createdAt = "2026-06-16";
        :>> createdBy = "claudeOpus";
        :>> method = VerificationMethod::inspect;
        :>> procedureText = "Autonomous closeOut (D0049): storyReverifyDeliverableDoD recorded (pass); reverifyDeliverableDoD in backlog (pass); .tracking validates green. No human gate (D0051: test-backed).";
    }
    part reverifyDeliverableCloseOutGateR1 : TestResult { :>> id = "287a026e-68ba-4f6e-acde-7b98b9da1251"; :>> outcome = VerdictKind::pass; :>> judgedAgainst = "724b19e"; :>> judgedAt = "2026-06-16"; :>> judgedBy = "claudeOpus"; }

    verification reverifyDeliverableRetroGate : Test {
        :>> id = "398b137f-79cb-4f6e-bdef-8ca9caeb1251";
        :>> title = "Sprint 20 retro gate (autonomous, D0049)";
        :>> createdAt = "2026-06-16";
        :>> createdBy = "claudeOpus";
        :>> method = VerificationMethod::analyze;
        :>> procedureText = "Autonomous retro (D0049): no avoidable issues — clean re-verify; dogfooded the write API to clear suspicion. issue014 closed. Estimate 1 pt held.";
    }
    part reverifyDeliverableRetroGateR1 : TestResult { :>> id = "4a9c248a-8adc-4f6e-cdef-9dba0bdc1251"; :>> outcome = VerdictKind::pass; :>> judgedAgainst = "724b19e"; :>> judgedAt = "2026-06-16"; :>> judgedBy = "claudeOpus"; }
}
