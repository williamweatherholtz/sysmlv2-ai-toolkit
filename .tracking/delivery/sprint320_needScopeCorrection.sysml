// ProjectDeliveryS320 — Sprint 320: N-8 superseded by N-19, the hosted direction recorded where it
// costs nothing, and two findings the question exposed. CHANGE (§3a). 3 pts.
package ProjectDeliveryS320 {
    private import EngineElement::*;
    private import EngineWork::*;
    private import EngineVerification::*;
    private import EngineRelationships::*;

    #CharteredBy dependency from needScopeStory to d0156;

    part needScopeStory : Story {
        :>> id = "0d8003b0-0814-63b0-9b3e-0000003003b0";
        :>> title = "Sprint 320: supersede N-8 with N-19; record the hosted direction; two findings (3 pts)";
        :>> createdAt = "2026-08-17"; :>> createdBy = "claudeOpus5"; :>> kind = WorkKind::decision; :>> priority = WorkPriority::p0; :>> owner = "claudeOpus5"; :>> estimatedPoints = 3;
    }

    action def DeliveryRunS320 {
        action storyNeedScope;
        verification storyNeedScopeDoD : Test { :>> id = "0d8003b1-0814-63b1-9b3e-0000003003b1"; :>> method = VerificationMethod::inspect; :>> procedureText = "Resolves issue132 and records what answering it exposed. DELIVERED: (1) D0156 accepted — N-8 SUPERSEDED (the mechanism D0115 itself used on four Needs, so the human's 2026-07-14 accepted-as-is attestation keeps naming the words it accepted) and N-19 nViewerViewStateTravels authored in its place: a saved viewpoint selection, filters and layout persist as a repository artifact and TRAVEL to another machine and another person's clone with no account and no server. srViewerPersistedViewState's satisfy edge repointed; the requirement itself needed NO change, because it already said sharing is by the artifact travelling in git. (2) D0157 records the hosted multi-user + marketplace direction with NO Need, NO requirement and NO backlog item — §1.4's decision-that-causes-no-action. (3) issue137: D0115's 'single-user' contradicts shipped distributed collaboration. (4) issue138: a viewpoint is the same portable UNIT as a process but only processes export. Both issues carry resolving actions. READ BACK from the computed views: validate 348 clean, check-engine clean, 34 guards ALL PASS, and `open-issues` shows issue132 resolved with issue137/issue138 triaged to real resolvers."; }
        part storyNeedScopeDoDR1 : TestResult { :>> id = "0d8003b2-0814-63b2-9b3e-0000003003b2"; :>> outcome = VerdictKind::pass; :>> judgedAgainst = "7493b12"; :>> judgedAt = "2026-08-17"; :>> judgedBy = "claudeOpus5"; }
    }

    verification nsRefineGate : Test { :>> id = "0d8003b3-0814-63b3-9b3e-0000003003b3"; :>> title = "Sprint 320 refine gate (DoR)"; :>> createdAt = "2026-08-17"; :>> createdBy = "claudeOpus5"; :>> method = VerificationMethod::inspect; :>> procedureText = "DoR. dcNeed8ScopeNarrowing was BLOCKED on d0156 by a #DependsOn to a proposed Decision, and it unblocked the moment the human accepted — which is the mechanism working exactly as intended: the work was visible without being schedulable by an actor forbidden to do it. THE DoD WAS PARTLY OVERTAKEN, stated rather than quietly reinterpreted: it said 'srViewerPersistedViewState still satisfies IT', meaning N-8, and the requirement now satisfies N-19 instead. The intent — that the requirement keeps satisfying the LIVE Need — holds, and the deviation is recorded here rather than by editing the DoD to match what happened. estimatedPoints=3."; }
    part nsRefineGateR1 : TestResult { :>> id = "0d8003b4-0814-63b4-9b3e-0000003003b4"; :>> outcome = VerdictKind::pass; :>> judgedAgainst = "7493b12"; :>> judgedAt = "2026-08-17"; :>> judgedBy = "claudeOpus5"; }

    verification nsStandupGate : Test { :>> id = "0d8003b5-0814-63b5-9b3e-0000003003b5"; :>> title = "Sprint 320 standup gate"; :>> createdAt = "2026-08-17"; :>> createdBy = "claudeOpus5"; :>> method = VerificationMethod::inspect; :>> procedureText = "Approach: revise D0156 IN PLACE rather than open a new Decision beside a stale proposal — it was created as the home for this exact question, and one governance home per question (D0105) applies to a question whose answer changed as much as to one whose answer held. Record in it that all four originally-proposed options were rejected, because the reason they were rejected is the finding. Answer the viewpoint-sharing question BEFORE authoring the Need, since the answer decides what the Need should say. No blockers."; }
    part nsStandupGateR1 : TestResult { :>> id = "0d8003b6-0814-63b6-9b3e-0000003003b6"; :>> outcome = VerdictKind::pass; :>> judgedAgainst = "7493b12"; :>> judgedAt = "2026-08-17"; :>> judgedBy = "claudeOpus5"; }

    verification nsImplementGate : Test { :>> id = "0d8003b7-0814-63b7-9b3e-0000003003b7"; :>> title = "Sprint 320 implement gate"; :>> createdAt = "2026-08-17"; :>> createdBy = "claudeOpus5"; :>> method = VerificationMethod::inspect; :>> procedureText = "MY FOUR PROPOSED OPTIONS WERE ALL WRONG AND THE RECORD SAYS SO. Every one assumed N-8's 'shareable' meant the VIEWER's sharing. The human's answer named a different object — 'the real need is to be able to transfer processes to them easily' — which the model already holds as nProcessPortability / srPortCatalogExchange, verified in sprint 297. Four internally-coherent answers to a question nobody had asked, which is a sharper failure than a wrong answer: an option set can be complete and still be about the wrong thing. THE VIEWPOINT-SHARING QUESTION HAS A CLEAN ANSWER and it collapses the confusion: measured, `keel process export` writes .engine-relative files plus a unit.toml naming what the receiving project must have; a viewpoint is the same shape (7 of 32 have a .view.toml, 21 of 32 name a keel subcommand as renderer, all 32 declared in one shared registry file), and BOTH apparent obstacles already have answers inside the process mechanism — a shared-file declaration carried by NAME (already done for rules) and a binary-capability dependency carried by name with the import reporting it (already done for guards). So unit.toml is UNIT-shaped and merely NAMED after processes, which is issue138. Three things had been hiding under one word: definition portability, result snapshot, and view state."; }
    part nsImplementGateR1 : TestResult { :>> id = "0d8003b8-0814-63b8-9b3e-0000003003b8"; :>> outcome = VerdictKind::pass; :>> judgedAgainst = "7493b12"; :>> judgedAt = "2026-08-17"; :>> judgedBy = "claudeOpus5"; }

    verification nsReviewGate : Test { :>> id = "0d8003b9-0814-63b9-9b3e-0000003003b9"; :>> title = "Sprint 320 review gate"; :>> createdAt = "2026-08-17"; :>> createdBy = "claudeOpus5"; :>> method = VerificationMethod::inspect; :>> procedureText = "Reviewed, and the load-bearing judgment is WHERE a weak-but-real intent lives. Needs drive decomposition, so a broad Need whose demand the human himself called 'weak atm' either sits undecomposed — dropping need_decomposed_pct off 100% and keeping it there — or gets decomposed into auth requirements for a local-only app, which IS issue132 repeated one level up. N-8's defect was never that it was wrong; it was written WIDER THAN THE DEMAND, and a reader three months later decomposed the wide half. A Decision carries the same intent at zero computational cost. D0157's WEAKEST PART IS NAMED IN ITS OWN RATIONALE rather than smoothed: no trigger date was given, and a direction with no trigger is indistinguishable from one nobody will act on. TWO PROVENANCE POINTS: N-19 was authored by claudeOpus5, not attributed to the human, even though its substance is theirs — attributing my words to them would be fabricated provenance; and the Decision records their authorization to author it, which is what D0108 requires for a Need I do not own."; }
    part nsReviewGateR1 : TestResult { :>> id = "0d8003ba-0814-63ba-9b3e-0000003003ba"; :>> outcome = VerdictKind::pass; :>> judgedAgainst = "7493b12"; :>> judgedAt = "2026-08-17"; :>> judgedBy = "claudeOpus5"; }

    verification nsCloseOutGate : Test { :>> id = "0d8003bb-0814-63bb-9b3e-0000003003bb"; :>> title = "Sprint 320 closeOut gate (autonomous, D0049)"; :>> createdAt = "2026-08-17"; :>> createdBy = "claudeOpus5"; :>> method = VerificationMethod::inspect; :>> procedureText = "Autonomous closeOut (D0049). issue132 resolved; issue137 and issue138 open and triaged, each to a declared action that ranks ready. ONE NEW WARNING IS A KNOWN FALSE POSITIVE and is left alone rather than silenced with a fake edge: the issue082 heuristic warns that sprint 319's DoD 'names srViewerPersistedViewState but no #Verify edge reaches it' — the DoD mentions that requirement in PROSE while describing this scope work and does not verify it, so authoring the suggested edge would assert verification that did not happen. validate 348 clean; check-engine clean; 34 guards ALL PASS (warnings only). No code changed this sprint, so no rebuild and no test-count movement."; }
    part nsCloseOutGateR1 : TestResult { :>> id = "0d8003bc-0814-63bc-9b3e-0000003003bc"; :>> outcome = VerdictKind::pass; :>> judgedAgainst = "7493b12"; :>> judgedAt = "2026-08-17"; :>> judgedBy = "claudeOpus5"; }

    verification nsRetroGate : Test { :>> id = "0d8003bd-0814-63bd-9b3e-0000003003bd"; :>> title = "Sprint 320 retro gate (autonomous, D0049)"; :>> createdAt = "2026-08-17"; :>> createdBy = "claudeOpus5"; :>> method = VerificationMethod::analyze; :>> procedureText = "Autonomous retro (D0049) under D0131's retroTrack. WELL: (1) the blocked-on-acceptance mechanism did its whole job — the work sat visible and unschedulable until its owner answered, then unblocked with no edit; (2) answering the mechanism question BEFORE authoring the Need changed the Need, which is the case for that ordering rather than an argument about it; (3) the four rejected options are recorded in D0156 with why, so the next reader inherits the correction and not just the conclusion. AVOIDABLE-ISSUE: I wrote two corrupted UUIDs — 'c47e style9b2d15' and 'a1f6c community2b3' — English words spliced into id strings in generated text. Both were caught, one by reading the file and one by grep, and neither reached a commit. THE CONTROL ALREADY EXISTS AND IT IS THE RIGHT ONE: `keel validate` checks id syntax and `duplicate-identity` checks uniqueness, so the fast gate catches this class before it lands; what I should stop doing is hand-minting UUIDs in prose at all, since `keel record`/`add-task` generate them from a CSPRNG (issue074). NO NEW ITEM — the guard exists, the defect is loud, and the remedy is to use the write API where one exists, which is already CLAUDE.md §4. Estimate 3 pts, delivered."; }
    part nsRetroGateR1 : TestResult { :>> id = "0d8003be-0814-63be-9b3e-0000003003be"; :>> outcome = VerdictKind::pass; :>> judgedAgainst = "7493b12"; :>> judgedAt = "2026-08-17"; :>> judgedBy = "claudeOpus5"; }
}
