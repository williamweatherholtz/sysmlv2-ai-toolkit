// ProjectDeliveryS488 — Sprint 488: four more controls proven; the probes found two defects. EXECUTE. 5 pts.
package ProjectDeliveryS488 {
    private import EngineElement::*;
    private import EngineWork::*;
    private import EngineVerification::*;
    private import EngineRelationships::*;

    #CharteredBy dependency from fourMoreControlsProvenStory to d0253;

    part fourMoreControlsProvenStory : Story {
        :>> id = "ed227cd9-06ec-42ff-a519-d78d7706e2a9";
        :>> title = "Sprint 488: four more controls proven to fire, and the probes found a field defect and a misaimed control (5 pts)";
        :>> createdAt = "2026-08-29"; :>> createdBy = "claudeOpus5"; :>> kind = WorkKind::code; :>> priority = WorkPriority::p0; :>> owner = "claudeOpus5"; :>> estimatedPoints = 5;
    }

    action def DeliveryRunS488 {
        action storyFourMoreControlsProven;
        verification storyFourMoreControlsProvenDoD : Test { :>> id = "9569340f-a993-4ca4-9dcb-5e802f57656b"; :>> method = VerificationMethod::test; :>> procedureText = "RESOLVES issue306. Probes for ctlPreWriteTiers, ctlFireLedger, ctlPrePushBehind and ctlReverify, each exercising the REAL mechanism - the real binary via its hook entry point with cwd inside a fixture, a real git push through the real .githooks/pre-push, the real reverify command against a manufactured drift-suspect task. Each control shown to ALLOW on the clean case before REFUSING on the dirty one. FIXES SHIPPED: the pre-push bootstrap refusal (issue306; remote_sha zeros now skips, as local_sha zeros always did), rides D0256 per the keystone lock. VERIFY: 4 probes pass; clippy; full suite; 54 guards; the four control-arming entries carry provenBy.: DELIVERED BACKLOG ITEMS: <items>. <what done means, verified how>."; }
        // RAN: / RAN: cargo test --release -p keel-cli --test hook_and_push_controls_actually_fire -> 4 passed (first run failed 3 of 4: wrong assumption, vacuous fixture, and issue306 - a real field defect); cargo clippy -D warnings clean; cargo test --workspace --release -> 17 suites ok, 0 FAILED; keel guard -> 54 guards 0 FAIL; gate --fast 549 clean
        part storyFourMoreControlsProvenDoDR1 : TestResult { :>> id = "820f884d-04a5-4454-a48a-8911ccf8787c"; :>> outcome = VerdictKind::pass; :>> judgedAgainst = "0d657ce"; :>> judgedAt = "2026-08-29"; :>> judgedBy = "claudeOpus5"; }
    }

    verification fourMoreControlsProvenRefineGate : Test { :>> id = "75dbd6e6-0934-4607-b421-e754184ed794"; :>> title = "Sprint 488 refine gate (DoR)"; :>> createdAt = "2026-08-29"; :>> createdBy = "claudeOpus5"; :>> method = VerificationMethod::inspect; :>> procedureText = "READY: chartered by D0253 (arming may be proven by test), scoped to the four controls a local test can reach. The three infra-resident ones (ctlAuditHistory, ctlBranchProtection, ctlReleaseGateJob) stay with dcProveTheRemainingControls, which may legitimately end in a stated reason no local test can reach them."; }
    verification fourMoreControlsProvenStandupGate : Test { :>> id = "f115651e-d9f0-435f-bff3-cbf307a1f0c2"; :>> title = "Sprint 488 standup gate"; :>> createdAt = "2026-08-29"; :>> createdBy = "claudeOpus5"; :>> method = VerificationMethod::inspect; :>> procedureText = "One transient blocker: cargo could not replace keel.exe (Access is denied) with only keel-serve.exe running - the console COPY, which is the documented workaround holding, not failing. Cleared on retry. The console being up is the correct state (issue150)."; }
    verification fourMoreControlsProvenImplementGate : Test { :>> id = "f9308000-9864-4b49-87b7-4425665746d3"; :>> title = "Sprint 488 implement gate"; :>> createdAt = "2026-08-29"; :>> createdBy = "claudeOpus5"; :>> method = VerificationMethod::test; :>> procedureText = "RAN: cargo test --release -p keel-cli --test hook_and_push_controls_actually_fire -> 4 passed. THE FIRST RUN FAILED 3 OF 4, and each failure taught something: (1) pre-write - MY assumption was wrong, an ordinary .tracking write under strict is ASK tier 2, not silent; the control is stricter than its prober believed, and the corrected assertion is kept with that history in its comment. (2) reverify - my fixture had no drift-suspect task, so the no-stamp assertion passed VACUOUSLY; rebuilt with manufactured drift (task verified at c1, deliverable moves at c2), and the green half - exactly one fresh stamp - is what keeps the red half honest. (3) pre-push - a REAL FIELD DEFECT (issue306): the hook refused every fresh project's bootstrap push, and separately, a plain behind push never reaches the hook at all because git's client-side check refuses first, so the probe now pushes --force, testing the D0129 history-rewrite class the control actually exists for."; }
    verification fourMoreControlsProvenReviewGate : Test { :>> id = "2d74c6ab-a2cc-4459-bb58-5341a6e87480"; :>> title = "Sprint 488 review gate — three passes per D0172"; :>> createdAt = "2026-08-29"; :>> createdBy = "claudeOpus5"; :>> method = VerificationMethod::inspect; :>> procedureText = "THREE PASSES. (1) REAL MECHANISM, NOT A COPY: the hook probe invokes the shipped binary's hook entry with cwd in the fixture; the push probe wires core.hooksPath at the REAL .githooks; reverify runs the real command. A probe of a reimplementation proves the reimplementation. (2) THE HOOK FIX IS MINIMAL AND SYMMETRIC: remote_sha zeros skips, exactly as local_sha zeros always did - the comment had claimed both halves while the code implemented one. (3) HONESTY OF THE CONTRACT EDITS: all four control-arming reasons KEEP their old text's valid half and name what was wrong with the rest - two of the four old reasons were the ctlWriteLock error again (existence rules out absence, not misbehaviour), and that pattern is now written where the next classifier will read it."; }
    verification fourMoreControlsProvenCloseOutGate : Test { :>> id = "e4b9e9f7-84a0-4419-b3e2-0a1a99140828"; :>> title = "Sprint 488 closeOut gate (autonomous, D0049)"; :>> createdAt = "2026-08-29"; :>> createdBy = "claudeOpus5"; :>> method = VerificationMethod::inspect; :>> procedureText = "CLOSED. Controls with evidence: 3 of 15 -> 7 of 15 (1 view-probe, 6 proven by test). Remaining without evidence: ctlAuditHistory, ctlBranchProtection, ctlReleaseGateJob (infra-resident, with dcProveTheRemainingControls), plus the commit gate's view-probe which predates this work. issue303 stays OPEN with those three. issue306 resolves here - found by a probe on its first run, fixed the same day, which is the entire argument for proving controls rather than classifying them."; }
    verification fourMoreControlsProvenRetroGate : Test { :>> id = "e3a44e1e-4ba2-4dc7-9567-f9a93fdcc873"; :>> title = "Sprint 488 retro gate (autonomous, D0049)"; :>> createdAt = "2026-08-29"; :>> createdBy = "claudeOpus5"; :>> method = VerificationMethod::analyze; :>> procedureText = "FINDING 1: the arming probes are the highest-yield tests in the codebase right now - four probes, first run, three failures, of which one was a FIELD DEFECT refusing every downstream project's first push (issue306), one was a control STRICTER than its prober believed, and one was a vacuous fixture that would have certified reverify forever without testing it. A control classified by reasoning had survived four of these findings; controls probed by test did not survive one run. FINDING 2: the pre-push probe's second lesson generalises - a control can be REAL and ARMED and still misaimed, because something upstream (git's own client check) already catches the case it was written for; its true value is the case only it catches (--force). 'What does this control catch that nothing else does' is a question the map cannot answer and probes can. FINDING 3, on my own conduct: the first draft of this very probe file contained the vacuous-fixture error I had criticised in the arming contract one sprint earlier. Writing the criticism does not confer immunity; only the discipline of making each probe FAIL first does."; }
}
