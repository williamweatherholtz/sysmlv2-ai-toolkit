// ProjectDeliveryS436 — Sprint 436: autoAccept (D0207): decisions auto-accept on being raised, forks earn the ask, and decision-channel ships as a portable process unit. EXECUTE. 2 pts.
package ProjectDeliveryS436 {
    private import EngineElement::*;
    private import EngineWork::*;
    private import EngineVerification::*;
    private import EngineRelationships::*;

    #CharteredBy dependency from autoAcceptStory to d0207;

    part autoAcceptStory : Story {
        :>> id = "87f2effc-3b8a-4792-86f2-0f4b30066d1b";
        :>> title = "Sprint 436: consent becomes standing, asks become earned (2 pts)";
        :>> createdAt = "2026-08-23"; :>> createdBy = "claudeFable5"; :>> kind = WorkKind::code; :>> priority = WorkPriority::p0; :>> owner = "claudeFable5"; :>> estimatedPoints = 2;
    }

    action def DeliveryRunS436 {
        action storyAutoAccept;
        verification storyAutoAcceptDoD : Test { :>> id = "4efcba96-0c2d-4f6e-b002-62e70ec26b8f"; :>> method = VerificationMethod::test; :>> procedureText = "DELIVERED: D0207 autoAccept, accepted on their verbatim direction ('issues raised are automatically accepted. they can be customizedly changed post-fact... formalize this as a process, and make it so other projects can inherit and use this ability right away'). ALL FOUR CLAUSES: (1) AUTO-ACCEPT - decision-issue.yml opens the issue then immediately records the acceptance for NON-FORK decisions (record_decision.sh AUTO mode: judgedBy the human, note carrying the AUTO-ACCEPTED machine token + the standing words + the issue link, in-workflow gate of record, merge-only push, receipt comment stating plainly not-individually-reviewed, auto-close), including a SWEEP of already-open non-fork issues - retireInbox (D0206) is the first live case, auto-accepting on this very push. (2) OVERRIDE ANYTIME - decision-record.yml now accepts comments on CLOSED decision issues; reject reopens, acknowledges in-thread, labels needs-reversal for the superseding record; accepted history is never rewritten. (3) FORKS EARN THE ASK - guard 48 judgment-request-quality: a PROPOSED fork must carry a short-name-led title, rationale >= 200 chars, a RESEARCH statement, and a COST per OPTION; negative-probed with a deliberately bad fork that drew all four violations and cleaned on removal; unit-owned by the new process so it travels with adoption. (4) PORTABLE - decision-channel is a full process unit (5 steps, owned guard, registered deploying skill with the downstream install recipe: copy 4 files, edit one allowlist, map logins, record YOUR standing consent - auto-accept is opt-in by recorded consent, never a keel default). attestation-policy [decisionAcceptance] declares standingConsent=d0207 beside the other delegations. ALSO CAUGHT PRE-LANDING: the recorder's git add -A would have committed the workflow's own scratch files - scoped to .engine .tracking with the reason inline. VERIFIED: python/bash/YAML lints; guard-48 four-violation probe; validate + check-engine + all 48 guards green; unit reads back in activation."; }
        part storyAutoAcceptDoDR1 : TestResult { :>> id = "a45a156d-9abf-4e13-bb0d-cd3c83fa380e"; :>> outcome = VerdictKind::pass; :>> judgedAgainst = "da538c22c5b4419a6c05059c9b5f63d69f2dfc74"; :>> judgedAt = "2026-08-23"; :>> judgedBy = "claudeFable5"; }
    }

    verification autoAcceptRefineGate : Test { :>> id = "61debb3b-2de8-4473-902d-e963829d3408"; :>> title = "Sprint 436 refine gate (DoR)"; :>> createdAt = "2026-08-23"; :>> createdBy = "claudeFable5"; :>> method = VerificationMethod::inspect; :>> procedureText = "DoR. Their message is charter and acceptance. Scope: the four D0207 clauses, the portable unit, doc-sync. Out of scope (stated): live-comment verification of GitHub payloads (chartered hardening from the dossier) and the reversal write plumbing (v1 acknowledges in-thread; the session records supersessions). 2 points."; }
    part autoAcceptRefineGateR1 : TestResult { :>> id = "55f4dfb1-3c96-4d03-8a12-e7f89e04337e"; :>> outcome = VerdictKind::pass; :>> judgedAgainst = "da538c22c5b4419a6c05059c9b5f63d69f2dfc74"; :>> judgedAt = "2026-08-23"; :>> judgedBy = "claudeFable5"; }
    verification autoAcceptStandupGate : Test { :>> id = "dda4d865-caaf-4c06-b889-4062ed329f2d"; :>> title = "Sprint 436 standup gate"; :>> createdAt = "2026-08-23"; :>> createdBy = "claudeFable5"; :>> method = VerificationMethod::inspect; :>> procedureText = "Approach: standing consent mirrors the D0165/D0192/D0198 declared-delegation shape - one policy contract holds every delegation with its withdraw line; the AUTO-ACCEPTED note token extends the never-one-number discipline to acceptances; the quality bar guards the PROPOSED state so a bad ask cannot even be committed, which is where their sufficiently-clear complaint actually bites."; }
    part autoAcceptStandupGateR1 : TestResult { :>> id = "9c2bd33f-b321-4b98-ad71-20ac5fe41fef"; :>> outcome = VerdictKind::pass; :>> judgedAgainst = "da538c22c5b4419a6c05059c9b5f63d69f2dfc74"; :>> judgedAt = "2026-08-23"; :>> judgedBy = "claudeFable5"; }
    verification autoAcceptImplementGate : Test { :>> id = "b0d68562-b900-4239-8129-faffebd0756b"; :>> title = "Sprint 436 implement gate"; :>> createdAt = "2026-08-23"; :>> createdBy = "claudeFable5"; :>> method = VerificationMethod::test; :>> procedureText = "Verified: guard 48 negative probe (bad fork: 4 violations - weak shortname, thin rationale, no RESEARCH, missing COSTs - clean on removal); open_decision_issues.py ast-parses with the auto-queue path; record_decision.sh bash -n with AUTO mode and closed-issue override; both workflows YAML-lint; the git-add scoping fix read back; sync-claude 37/37 skills; validate + check-engine + all 48 guards green; the live sweep of D0206 is verified post-push in this session's read-backs."; }
    part autoAcceptImplementGateR1 : TestResult { :>> id = "cbc491d4-5073-416b-a084-49c599bb3c95"; :>> outcome = VerdictKind::pass; :>> judgedAgainst = "da538c22c5b4419a6c05059c9b5f63d69f2dfc74"; :>> judgedAt = "2026-08-23"; :>> judgedBy = "claudeFable5"; }
    verification autoAcceptReviewGate : Test { :>> id = "876c334f-d555-44cb-aab4-8eec191d1f6f"; :>> title = "Sprint 436 review gate — three passes per D0172"; :>> createdAt = "2026-08-23"; :>> createdBy = "claudeFable5"; :>> method = VerificationMethod::inspect; :>> procedureText = "PASS 1, CLAIMS: every probe quoted from this session. PASS 2, BOUNDARY: auto-acceptance records the human as judge under a standing order they gave ONCE - the note states not-individually-reviewed and the override thread never closes, which is what keeps the record honest rather than flattering; a reader who wants per-item judgment can withdraw one policy line. PASS 3, OWN DIFF: two scripted-edit escape-mangling rounds on the python (the recurring class) ended with a clean Write-tool rewrite - the rule is now absolute: syntax-bearing files get written whole, never patched by string surgery; and the git add -A scratch-file leak was caught by reading the recorder as a reviewer before it ever ran. WHAT A REVIEWER SHOULD ATTACK: the 200-char rationale floor and 28-char shortname cap are judgment constants; the RESEARCH token is presence-checked, not quality-checked - a hollow RESEARCH line passes the guard and only the human's rejection teaches it."; }
    part autoAcceptReviewGateR1 : TestResult { :>> id = "3b5bcebf-8e69-479d-b214-75123286f502"; :>> outcome = VerdictKind::pass; :>> judgedAgainst = "da538c22c5b4419a6c05059c9b5f63d69f2dfc74"; :>> judgedAt = "2026-08-23"; :>> judgedBy = "claudeFable5"; }
    verification autoAcceptCloseOutGate : Test { :>> id = "5aefb81e-b289-4284-ab44-b0d5ca0de5bd"; :>> title = "Sprint 436 closeOut gate (autonomous, D0049)"; :>> createdAt = "2026-08-23"; :>> createdBy = "claudeFable5"; :>> method = VerificationMethod::inspect; :>> procedureText = "Autonomous closeOut (D0049). The unit is active; D0206 auto-accepts on this push (the standing-consent dry run); the frontier's remaining items still await their inputs; validate + all 48 guards green."; }
    part autoAcceptCloseOutGateR1 : TestResult { :>> id = "bcdc35a0-be01-404f-b0d3-990eeb4483a8"; :>> outcome = VerdictKind::pass; :>> judgedAgainst = "da538c22c5b4419a6c05059c9b5f63d69f2dfc74"; :>> judgedAt = "2026-08-23"; :>> judgedBy = "claudeFable5"; }
    verification autoAcceptRetroGate : Test { :>> id = "a7b3c9ae-5334-4687-92c5-50e3103e3703"; :>> title = "Sprint 436 retro gate (autonomous, D0049)"; :>> createdAt = "2026-08-23"; :>> createdBy = "claudeFable5"; :>> method = VerificationMethod::analyze; :>> procedureText = "Autonomous retro (D0049). AVOIDABLE-ISSUE SCAN under rcRecurrence: the escape-mangling class recurred TWICE in one sprint before the whole-file-Write rule was applied absolutely - the practice is now recorded in the review gate and this retro; recurrence would be a process defect. WELL: the channel shipped Thursday-shaped and was inverted Friday-shaped in one sprint because the ask/record separation held - the record layer needed zero changes to flip the consent model. Estimate 2 pts, delivered 2."; }
    part autoAcceptRetroGateR1 : TestResult { :>> id = "81d279cc-c08a-4b7a-b081-36ba8bc5f484"; :>> outcome = VerdictKind::pass; :>> judgedAgainst = "da538c22c5b4419a6c05059c9b5f63d69f2dfc74"; :>> judgedAt = "2026-08-23"; :>> judgedBy = "claudeFable5"; }
}
