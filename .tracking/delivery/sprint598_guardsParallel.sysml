// ProjectDeliveryS598 — Sprint 598: Rank 1 of D0367: the enforced guards run across a thread pool in declared order, and every guard and every git run is timed in-process (dcGuardsRunInParallelAndTimed, D0368). EXECUTE. 3 pts.
package ProjectDeliveryS598 {
    private import EngineElement::*;
    private import EngineWork::*;
    private import EngineVerification::*;
    private import EngineRelationships::*;

    #CharteredBy dependency from guardsParallelStory to d0368;

    part guardsParallelStory : Story {
        :>> id = "33a3a2a0-3a48-47df-897a-e42bbfac84a1";
        :>> title = "Sprint 598: Rank 1 of D0367: the enforced guards run across a thread pool in declared order, and every guard and every git run is timed in-process (dcGuardsRunInParallelAndTimed, D0368) (3 pts)";
        :>> createdAt = "2026-09-07"; :>> createdBy = "claudeOpus5"; :>> kind = WorkKind::code; :>> priority = WorkPriority::p0; :>> owner = "claudeOpus5"; :>> estimatedPoints = 3;
    }

    action def DeliveryRunS598 {
        action storyGuardsParallel;
        verification storyGuardsParallelDoD : Test { :>> id = "b3fb13f6-a9e8-4889-83bd-011cd6905973"; :>> method = VerificationMethod::test; :>> procedureText = "DELIVERED: guards::run_all splits the activation filter (serial, first) from execution (run_in_parallel: std::thread::scope, one worker per available core, a shared atomic work index, reports written back by slot so the order is GUARD_NAMES order); each guard runs under perf::phase('guard:<name>'); gitx::git() returns gitx::Git, whose output/status/spawn clock into GIT_NANOS on every run and tally the argv shape at KEEL_PERF=2, with the two rich helpers (govern::git_lines, reports::git_out) stripped of their own timing so nothing double-counts and orient's two cat-file batch waits timed at the wait; fingerprint::of serialises its compute so a parallel cold burst does one walk. VERIFIED: tests run_all_reports_are_in_guard_names_order and run_all_is_deterministic_across_two_runs (guards.rs parallel_tests) and a_git_run_through_the_constructor_advances_git_nanos (gitx.rs) pass in cargo test --release; no_git_spawn_bypasses_the_counted_constructor still holds; clippy pedantic clean. MEASURED on this tree from a shell timer, same binary shape, three runs each: `keel guard` BEFORE 30174 / 27156 / 26623 ms, AFTER 14086 / 11187 / 11657 ms; stdout byte-identical apart from the elapsed figure (diff). KEEL_PERF=2 now reads `git x56 in 11196ms` where it read `in 118ms`, and the top phase is guard:priority-inversion 12789 ms - the bound rank 2 removes. Resolves issue410 outright and the serial term of issue409."; }
        // RAN: cargo test --release -p keel-cli --lib -- gitx parallel_tests: 6 passed; keel guard before 30174/27156/26623 ms after 14086/11187/11657 ms (shell timer); diff of guard stdout identical
        part storyGuardsParallelDoDR1 : TestResult { :>> id = "52a2f553-8ea0-4619-8418-44fd07ae18e3"; :>> outcome = VerdictKind::pass; :>> judgedAgainst = "45c0b91347c7931b933170df9fdf35e05d7a0517"; :>> judgedAt = "2026-09-07"; :>> judgedBy = "claudeOpus5"; }
    }

    verification guardsParallelRefineGate : Test { :>> id = "c3098cbe-00c7-451d-9a0e-836d599573ca"; :>> title = "Sprint 598 refine gate (DoR)"; :>> createdAt = "2026-09-07"; :>> createdBy = "claudeOpus5"; :>> method = VerificationMethod::inspect; :>> procedureText = "READY, 3 pts: one function rewritten, one wrapper type, three tests, a measurement - the DoD names the check for each. Chartered by D0368, which carries #ProspectiveChange because guards.rs is under the keystone lock and so waits for the human under D0337; the code lands behind it in the same commit as the lock requires."; }
    // RAN: sprint598 Refine: see the gate's procedureText; keel guard timed 3x before/after from a shell timer, cargo test --release -p keel-cli --lib -- gitx parallel_tests 6 passed
    part guardsParallelRefineGateR1 : TestResult { :>> id = "5515c773-9028-42ce-a787-b11bdd3c6e0e"; :>> outcome = VerdictKind::pass; :>> judgedAgainst = "45c0b91347c7931b933170df9fdf35e05d7a0517"; :>> judgedAt = "2026-09-07"; :>> judgedBy = "claudeOpus5"; }
    verification guardsParallelStandupGate : Test { :>> id = "2637b3a9-7af6-4f22-8e18-cb035707ea78"; :>> title = "Sprint 598 standup gate"; :>> createdAt = "2026-09-07"; :>> createdBy = "claudeOpus5"; :>> method = VerificationMethod::inspect; :>> procedureText = "ONE CHOICE: the wrapper exposes the builder methods the sites use (arg, args, current_dir, env, stdin, stdout, stderr) and nothing else, so a site cannot reach the inner Command and run untimed; a new need adds a method to the wrapper. A second choice forced by the first measurement: the pool made a serial fingerprint memo miss into twelve concurrent computes (36 walks, 6.3 s thread time), fixed by serialising the compute in fingerprint::of - kept in this sprint because the pool caused it."; }
    // RAN: sprint598 Standup: see the gate's procedureText; keel guard timed 3x before/after from a shell timer, cargo test --release -p keel-cli --lib -- gitx parallel_tests 6 passed
    part guardsParallelStandupGateR1 : TestResult { :>> id = "28e8b93d-805e-420f-a4e0-1dba59a6f2d5"; :>> outcome = VerdictKind::pass; :>> judgedAgainst = "45c0b91347c7931b933170df9fdf35e05d7a0517"; :>> judgedAt = "2026-09-07"; :>> judgedBy = "claudeOpus5"; }
    verification guardsParallelImplementGate : Test { :>> id = "8720af4a-2ecc-4327-bb11-135e11867c9b"; :>> title = "Sprint 598 implement gate"; :>> createdAt = "2026-09-07"; :>> createdBy = "claudeOpus5"; :>> method = VerificationMethod::test; :>> procedureText = "RAN: python patch_gitx.py and patch_run_all.py (each replacement refusing unless its anchor occurs once), cargo clippy --release -p keel-cli --all-targets (four doc-markdown and one single-match-else fixed, then clean), cargo build --release, cargo test --release -p keel-cli --lib -- gitx parallel_tests (6 passed), three timed runs of keel guard before and three after from a copy of the binary (keel-serve.exe), diff of stdout, cp to .keel/bin/keel.exe so the hooks run the same engine."; }
    // RAN: sprint598 Implement: see the gate's procedureText; keel guard timed 3x before/after from a shell timer, cargo test --release -p keel-cli --lib -- gitx parallel_tests 6 passed
    part guardsParallelImplementGateR1 : TestResult { :>> id = "d9af0af9-aaec-4992-8a36-33673a3da740"; :>> outcome = VerdictKind::pass; :>> judgedAgainst = "45c0b91347c7931b933170df9fdf35e05d7a0517"; :>> judgedAt = "2026-09-07"; :>> judgedBy = "claudeOpus5"; }
    verification guardsParallelReviewGate : Test { :>> id = "ad494a80-b507-4778-90c8-1d4ed1cf2a6a"; :>> title = "Sprint 598 review gate — three passes per D0172"; :>> createdAt = "2026-09-07"; :>> createdBy = "claudeOpus5"; :>> method = VerificationMethod::inspect; :>> procedureText = "THREE QUESTIONS (D0172). Does the pool change any answer? No guard writes a file or sets process state (grep set_var, set_current_dir, static mut, fs::write in guards.rs: the one fs::write is a test); the model cache and fingerprint memo are behind locks; the determinism test judges the tree twice and compares per-guard counts. Is the time attribution now honest? GIT_NANOS is added at the one constructor's wrapper and at the two batch waits, and the double-timing in the two rich helpers was removed - 56 spawns in 11.2 s under contention is the number the line now shows. What is NOT claimed: that the wall time transfers to another host, or that the pool shortens priority-inversion - it lengthens it (12.8 s in the pool against 6.8 s alone), which is why rank 2 follows."; }
    // RAN: sprint598 Review: see the gate's procedureText; keel guard timed 3x before/after from a shell timer, cargo test --release -p keel-cli --lib -- gitx parallel_tests 6 passed
    part guardsParallelReviewGateR1 : TestResult { :>> id = "826f24e7-6ab7-4f5d-af14-e5dae2d871eb"; :>> outcome = VerdictKind::pass; :>> judgedAgainst = "45c0b91347c7931b933170df9fdf35e05d7a0517"; :>> judgedAt = "2026-09-07"; :>> judgedBy = "claudeOpus5"; }
    verification guardsParallelCloseOutGate : Test { :>> id = "b2f134cb-3361-4801-9328-c429dfa2cfba"; :>> title = "Sprint 598 closeOut gate (autonomous, D0049)"; :>> createdAt = "2026-09-07"; :>> createdBy = "claudeOpus5"; :>> method = VerificationMethod::inspect; :>> procedureText = "CLOSED. keel guard 26.6-30.2 s to 11.2-14.1 s on this tree; the instrumentation the spike needed a patch for is permanent. D0368 awaits the human's word; the frontier's next item is dcGitFactsAreContentAddressed."; }
    // RAN: sprint598 CloseOut: see the gate's procedureText; keel guard timed 3x before/after from a shell timer, cargo test --release -p keel-cli --lib -- gitx parallel_tests 6 passed
    part guardsParallelCloseOutGateR1 : TestResult { :>> id = "2997831e-8fb4-4e48-af9c-d23926bc1efd"; :>> outcome = VerdictKind::pass; :>> judgedAgainst = "45c0b91347c7931b933170df9fdf35e05d7a0517"; :>> judgedAt = "2026-09-07"; :>> judgedBy = "claudeOpus5"; }
    verification guardsParallelRetroGate : Test { :>> id = "ff3da013-c19a-4b26-8c14-a736a5955afd"; :>> title = "Sprint 598 retro gate (autonomous, D0049)"; :>> createdAt = "2026-09-07"; :>> createdBy = "claudeOpus5"; :>> method = VerificationMethod::analyze; :>> procedureText = "AVOIDABLE-ISSUE SCAN HELD. One process finding: the pre-bash hook refused two heredocs carrying a backslash inside Python source - D0309 doing what it says (issue372 tracks the class), and each cost one retry to the Write tool; no new item. One measurement finding kept in the sprint rather than deferred: parallelism exposed a memo that was correct only because callers were serial (fingerprint::of), the class 'a cache validated by the caller's discipline' - carried into dcOneCorpusPerProcess, whose corpus cache must be validated by the file's own (len, mtime), never by the caller's order; no new item."; }
    // RAN: sprint598 Retro: see the gate's procedureText; keel guard timed 3x before/after from a shell timer, cargo test --release -p keel-cli --lib -- gitx parallel_tests 6 passed
    part guardsParallelRetroGateR1 : TestResult { :>> id = "7494c5f8-6b7a-4685-9c00-62f895ddc783"; :>> outcome = VerdictKind::pass; :>> judgedAgainst = "45c0b91347c7931b933170df9fdf35e05d7a0517"; :>> judgedAt = "2026-09-07"; :>> judgedBy = "claudeOpus5"; }
}
