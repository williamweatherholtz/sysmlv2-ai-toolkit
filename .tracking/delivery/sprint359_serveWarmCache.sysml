// ProjectDeliveryS359 — Sprint 359: the interactive surface, measured for the first time. A cache HIT was
// 180ms and all of it was the cache KEY. Warm arrival burst 1.14s -> 0.02s. EXECUTE. 8 pts.
package ProjectDeliveryS359 {
    private import EngineElement::*;
    private import EngineWork::*;
    private import EngineVerification::*;
    private import EngineRelationships::*;

    #CharteredBy dependency from serveWarmStory to d0167;

    part serveWarmStory : Story {
        :>> id = "0d800620-0814-6620-9b3e-000000300620";
        :>> title = "Sprint 359: keel serve made fast where the human touches it — the epoch advances on change, not on read (8 pts)";
        :>> createdAt = "2026-08-20"; :>> createdBy = "claudeOpus5"; :>> kind = WorkKind::code; :>> priority = WorkPriority::p0; :>> owner = "claudeOpus5"; :>> estimatedPoints = 8;
    }

    action def DeliveryRunS359 {
        action storyServeWarm;
        verification storyServeWarmDoD : Test { :>> id = "0d800621-0814-6621-9b3e-000000300621"; :>> method = VerificationMethod::test; :>> procedureText = "Delivered by dcServeWarmCache under D0167. THE HEADLINE NUMBER, HTTP boundary, six-request console arrival burst, warm, same tree, five samples each: 1.05-1.17s BEFORE, 0.02s AFTER - about 3ms per request. Cold burst 3.91s to 3.11s, and 22.9s on the first-ever touch of a cold disk, which is antivirus rather than compute and is reported as such rather than claimed as a 7x win. THE FINDING: a cache HIT cost 137-208ms and the FINGERPRINT WAS ALL OF IT - `fp 180ms/604 stat, parse 0ms, build x0, git x0` on a 181ms request. The epoch advanced on every request, so each of the six requests in one page load re-statted 604 files to ask a question none of them had changed the answer to. THREE FIXES, of which only the third needed a Decision: (1) the shared view store, so /api/obligations stops computing four views into a private local that the console then recomputes - `orient` was computed TWICE per arrival; (2) the store keyed by the VIEW rather than the ROUTE, since /api/dispositions and /api/computed/dispositions cached identical JSON twice; (3) the epoch advanced by an OBSERVED CHANGE or a WRITE, never a read, with ONE watcher task per server instead of one 604-stat poll per open tab. VERIFIED END TO END, not argued: a real file edit gave `computed` at t+1s, `stale` at t+2-3s once observed, fresh `computed` from t+4s once the warmer landed, and the file restored with `git diff` empty. validate 391 clean; check-engine clean; 37 guards ALL PASS; 232 tests; clippy clean."; }
        part storyServeWarmDoDR1 : TestResult { :>> id = "0d800622-0814-6622-9b3e-000000300622"; :>> outcome = VerdictKind::pass; :>> judgedAgainst = "e5c376b"; :>> judgedAt = "2026-08-20"; :>> judgedBy = "claudeOpus5"; }
    }

    verification swRefineGate : Test { :>> id = "0d800623-0814-6623-9b3e-000000300623"; :>> title = "Sprint 359 refine gate (DoR)"; :>> createdAt = "2026-08-20"; :>> createdBy = "claudeOpus5"; :>> method = VerificationMethod::inspect; :>> procedureText = "DoR. Their statement is recorded verbatim as st005 and split into TWO user stories, because it carries two implications and the triage verdict is singular: us006 is a scopeConstraint - performance work is measured on the interactive surface - and us007 is an implementationChange, since `regardless, deploy performance improvements` is an instruction to ship even if my scoping differs from theirs. THE SCOPE CONSTRAINT IS THE CORRECTION OF A REAL MISDIRECTION and that is why it is not merely a priority: five prior performance sprints measured CLI commands, and `perf::report` only prints at process exit, so a server could never be measured at all. estimatedPoints=8."; }
    part swRefineGateR1 : TestResult { :>> id = "0d800624-0814-6624-9b3e-000000300624"; :>> outcome = VerdictKind::pass; :>> judgedAgainst = "e5c376b"; :>> judgedAt = "2026-08-20"; :>> judgedBy = "claudeOpus5"; }

    verification swStandupGate : Test { :>> id = "0d800625-0814-6625-9b3e-000000300625"; :>> title = "Sprint 359 standup gate"; :>> createdAt = "2026-08-20"; :>> createdBy = "claudeOpus5"; :>> method = VerificationMethod::inspect; :>> procedureText = "Approach: BUILD THE INSTRUMENT FIRST, because the surface they named was the one the existing instrument structurally could not see. `perf::interval()` reads and ZEROES the counters and is emitted per request in the serve log, which turned an unattributable 180ms into `fp 180ms/604 stat, parse 0ms, build x0`. That single line settled in one request what timing the whole burst could never have settled - the same count-don't-time rule sprint 358 wrote down, applied one layer out. No blockers. ONE THING WAS RULED OUT BEFORE STARTING: a TTL on the fingerprint memo, which is the obvious fix and directly contradicts the condition the human attached to authorising the memo, quoted in the module's own doc."; }
    part swStandupGateR1 : TestResult { :>> id = "0d800626-0814-6626-9b3e-000000300626"; :>> outcome = VerdictKind::pass; :>> judgedAgainst = "e5c376b"; :>> judgedAt = "2026-08-20"; :>> judgedBy = "claudeOpus5"; }

    verification swImplementGate : Test { :>> id = "0d800627-0814-6627-9b3e-000000300627"; :>> title = "Sprint 359 implement gate"; :>> createdAt = "2026-08-20"; :>> createdBy = "claudeOpus5"; :>> method = VerificationMethod::test; :>> procedureText = "THE MEASUREMENT THAT ALMOST SHIPPED A REGRESSION AS A WIN. The first pass - shared store, view-keyed cache, stale-while-revalidate, warming on change - took the COLD burst from 22.94s to 3.91s, and I could have stopped there and reported a 6x improvement. The WARM burst had gone the WRONG WAY, 0.38s to 1.14s, and the honest reading of that took two steps: five samples showed 1.05-1.17s, consistently, so it was not noise; and comparing a tiny view against a huge one showed both at ~180ms, so it was a FIXED cost, not payload. Only then did the per-request instrument name it. THE 0.38s READING WAS THE OUTLIER, not the 1.14s - it was taken immediately after a 22.9s cold pass had warmed the OS file cache, so my own rule about discarding the first timing after a build was pointing the wrong way round. A WRITE BUMPS THE EPOCH TWICE and this is the correctness detail I would defend hardest: bumping only BEFORE the handler leaves it memoizing the pre-write fingerprint under the new epoch, so the next read answers from the cache of a tree that no longer exists. That is `I click accept and nothing changes` - the exact report that started this whole line of work - and I would have reintroduced it as a performance improvement. Tested by editing out of band, then issuing a non-GET (rejected 422, which is fine because the bump is in middleware and does not depend on the handler succeeding), then reading: `stale` immediately, where a read alone inside the window correctly said `computed`."; }
    part swImplementGateR1 : TestResult { :>> id = "0d800628-0814-6628-9b3e-000000300628"; :>> outcome = VerdictKind::pass; :>> judgedAgainst = "e5c376b"; :>> judgedAt = "2026-08-20"; :>> judgedBy = "claudeOpus5"; }

    verification swReviewGate : Test { :>> id = "0d800629-0814-6629-9b3e-000000300629"; :>> title = "Sprint 359 review gate"; :>> createdAt = "2026-08-20"; :>> createdBy = "claudeOpus5"; :>> method = VerificationMethod::inspect; :>> procedureText = "Reviewed. WHAT I REFUSED TO DO: add a TTL to the fingerprint memo. It is the obvious fix, it is two lines, and `fingerprint.rs` records in its own module doc the condition the human attached to authorising the memo at all - keyed by an explicit epoch, never by elapsed time, nothing expires on a timer. A TTL contradicts that outright, and the fact that it would have worked is not the test. The shape that respects it is also the better one: an OBSERVATION is a fact about the tree established by reading it, and doing that once for all readers instead of once per reader is what makes the constant-cost watcher correct rather than merely cheap. WHY THIS IS STILL A DECISION AND NOT JUST A COMMIT: it changes WHO advances the epoch, and it opens a bounded window - an edit made outside the server is seen up to 1.5s late, and a read inside that window is answered `computed` from the pre-edit value. I argue that window is relocated rather than created, because the change-detection interval already governed when a page could learn of an out-of-band edit. That argument is theirs to accept or reject, so D0167 is proposed with the cost stated in its consequences rather than buried. MY FIRST WATCHER SHAPE WAS WRONG in a way worth recording: I put the detector inside the SSE connection, where the poll already lived. With no browser attached nothing would advance the epoch and the next arrival would be served a pre-edit answer indefinitely - a correctness bug dressed as an optimisation, caught by asking who runs this when nobody is looking."; }
    part swReviewGateR1 : TestResult { :>> id = "0d80062a-0814-662a-9b3e-00000030062a"; :>> outcome = VerdictKind::pass; :>> judgedAgainst = "e5c376b"; :>> judgedAt = "2026-08-20"; :>> judgedBy = "claudeOpus5"; }

    verification swCloseOutGate : Test { :>> id = "0d80062b-0814-662b-9b3e-00000030062b"; :>> title = "Sprint 359 closeOut gate (autonomous, D0049)"; :>> createdAt = "2026-08-20"; :>> createdBy = "claudeOpus5"; :>> method = VerificationMethod::inspect; :>> procedureText = "Autonomous closeOut (D0049). D0167 is PROPOSED and unsigned - the code is deployed because they said `regardless, deploy performance improvements`, and the Decision records the one part that narrows a condition they set, for their signature. issue168 records the instrumentation gap that made every prior performance number a CLI number; issue169 records the route-keyed cache and the bypassed store. Their statement is recorded as st005 with us006 (scopeConstraint) and us007 (implementationChange). Doc-sync rode along: the `fingerprint.rs` module doc described `serve bumps the epoch at the START of every HTTP request`, which is now false, and a doc that describes a mechanism the code no longer has is the dual truth section 1 forbids. A NEW TEST, verified BOTH WAYS: `the_epoch_is_advanced_by_writes_and_observations_not_by_reads` passes on the shipped code and FAILS on an unconditional bump, which I produced deliberately to watch it fail. validate 391 clean; check-engine clean; 37 guards ALL PASS; 232 tests; clippy clean."; }
    part swCloseOutGateR1 : TestResult { :>> id = "0d80062c-0814-662c-9b3e-00000030062c"; :>> outcome = VerdictKind::pass; :>> judgedAgainst = "e5c376b"; :>> judgedAt = "2026-08-20"; :>> judgedBy = "claudeOpus5"; }

    verification swRetroGate : Test { :>> id = "0d80062d-0814-662d-9b3e-00000030062d"; :>> title = "Sprint 359 retro gate (autonomous, D0049)"; :>> createdAt = "2026-08-20"; :>> createdBy = "claudeOpus5"; :>> method = VerificationMethod::analyze; :>> procedureText = "Autonomous retro (D0049) under D0131's retroTrack. WELL: (1) the instrument was built before the fix, and it is the reason this sprint found a real cause instead of a fourth wrong premise - `fp 180ms/604 stat, parse 0ms, build x0` is not arguable; (2) the warm-path REGRESSION was chased rather than shipped, when the cold-path number alone was a publishable 6x win and nobody would have looked; (3) the TTL was refused on a condition recorded in a module doc months of sprints ago - the doc did its job, which is the argument for writing conditions down where the code lives; (4) the write-path double bump was found by asking what happens to the console's own act, and it would have reintroduced the exact bug this whole line of work started from; (5) the watcher was moved out of the SSE connection by asking who runs it when no browser is attached; (6) the new test was verified by producing the regression, not by passing. AVOIDABLE-ISSUE, and it is the same class as sprint 358's: I named a HOT_VIEWS set from what looked important, then read the console's own source and found two of the six were guesses - `sitting-coverage` and `open-issues` are not on the arrival path. Guessing a warm set is not harmless: it spends the human's CPU on views nobody opened. THE RULE: a warm set is READ OFF the consumer, never inferred from what the server thinks matters. SECOND AVOIDABLE-ISSUE: my first reading of the warm regression treated 0.38s as the baseline, when it was an outlier taken on an OS cache warmed by the preceding 22.9s cold pass. Discard-the-first-timing is not a rule about position in a sequence; it is a rule about what state the machine was in. Estimate 8 pts, delivered."; }
    part swRetroGateR1 : TestResult { :>> id = "0d80062e-0814-662e-9b3e-00000030062e"; :>> outcome = VerdictKind::pass; :>> judgedAgainst = "e5c376b"; :>> judgedAt = "2026-08-20"; :>> judgedBy = "claudeOpus5"; }
}
