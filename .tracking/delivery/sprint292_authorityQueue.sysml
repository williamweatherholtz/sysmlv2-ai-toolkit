// ProjectDeliveryS292 — Sprint 292: `keel authority-queue` — what genuinely needs a human, with age
// and origin, and nothing a test already settles (dcAuthorityQueue, D0129). EXECUTE. 5 pts.
package ProjectDeliveryS292 {
    private import EngineElement::*;
    private import EngineWork::*;
    private import EngineVerification::*;
    private import EngineRelationships::*;

    #CharteredBy dependency from authorityQueueStory to d0144;

    part authorityQueueStory : Story {
        :>> id = "0d8001ed-0814-61ed-9b3e-0000003001ed";
        :>> title = "Sprint 292: the human-authority queue — age, origin, escalation, grandfathering (5 pts)";
        :>> createdAt = "2026-08-15"; :>> createdBy = "claudeOpus5"; :>> kind = WorkKind::code; :>> priority = WorkPriority::p0; :>> owner = "claudeOpus5"; :>> estimatedPoints = 5;
    }

    action def DeliveryRunS292 {
        action storyAuthorityQueue;
        verification storyAuthorityQueueDoD : Test { :>> id = "0d8001ee-0814-61ee-9b3e-0000003001ee"; :>> method = VerificationMethod::demo; :>> procedureText = "Delivers dcAuthorityQueue (srDcHumanAuthorityQueue, D0129). Human judgment is the only resource in a mostly-AI team that cannot be scaled by adding contributors, so it must never sit on the critical path of each unit of work — and asking for judgment an automated check could make degrades review into rubber-stamping, which launders unreviewed work as reviewed (D0051). DELIVERED `keel authority-queue`: four obligation classes, each row carrying WAITING AGE and ORIGINATING CONTRIBUTOR, with escalation past 14 days that MARKS rather than blocks. MEASURED against this repo: 57 items, 15 escalated, as of the HEAD commit date — 2 Decisions awaiting acceptance (d0146, d0147), 54 undispositioned findings at or above Medium, and ONE batched per-sitting-review row covering 247 sprints. `asOf` is git-derived (D0013 HEAD commit date), not the wall clock, so two contributors computing this against the same commit agree. EXCLUDED, deliberately and by construction: anything a passing automated check already settles — only obligations REQUIRING a human verdict appear, so no `method=test` gate can ever be listed. GRANDFATHERING IS THE LOAD-BEARING PART (issue068): each obligation carries the date it came into force and the Decision that created it — perSittingReview from 2026-06-18 (D0073), findingDisposition from 2026-06-22 (D0092) — and work predating it is excluded. MEASURED: 287 sprints are uncovered, 247 are actually owed, so 40 predating D0073 are correctly not resurrected. Without that filter this command would hand a human ~340 items nobody ever owed, which is not thoroughness but the rubber-stamping the item exists to prevent. clippy clean; 136 lib tests; validate 314 clean; 29 guards green."; }
        part storyAuthorityQueueDoDR1 : TestResult { :>> id = "0d8001ef-0814-61ef-9b3e-0000003001ef"; :>> outcome = VerdictKind::pass; :>> judgedAgainst = "07f000f"; :>> judgedAt = "2026-08-15"; :>> judgedBy = "claudeOpus5"; }
    }

    verification aqRefineGate : Test { :>> id = "0d8001f0-0814-61f0-9b3e-0000003001f0"; :>> title = "Sprint 292 refine gate (DoR)"; :>> createdAt = "2026-08-15"; :>> createdBy = "claudeOpus5"; :>> method = VerificationMethod::inspect; :>> procedureText = "DoR. CONSUMER CHECK (dorConsumer, D0144): the consumer is a HUMAN with finite attention, which is the whole premise of the item — so the first thing measured was VOLUME, before any code. 287 uncovered sprints and 54 undispositioned findings would have made a ~340-row queue. That number is what forced the grandfathering filter and the batched review row; had the consumer check been skipped, the command would have been built correctly and been unusable. estimatedPoints=5. DoR met."; }
    part aqRefineGateR1 : TestResult { :>> id = "0d8001f1-0814-61f1-9b3e-0000003001f1"; :>> outcome = VerdictKind::pass; :>> judgedAgainst = "07f000f"; :>> judgedAt = "2026-08-15"; :>> judgedBy = "claudeOpus5"; }

    verification aqStandupGate : Test { :>> id = "0d8001f2-0814-61f2-9b3e-0000003001f2"; :>> title = "Sprint 292 standup gate"; :>> createdAt = "2026-08-15"; :>> createdBy = "claudeOpus5"; :>> method = VerificationMethod::inspect; :>> procedureText = "Approach: read the in-force date of each obligation from the DECISION that created it, and record both in the code, so the filter can be audited rather than trusted. A hard-coded cutoff with no provenance would be indistinguishable from an arbitrary one, and this filter is what decides whether ~340 items are shown or hidden — the highest-leverage constant in the command. No blockers."; }
    part aqStandupGateR1 : TestResult { :>> id = "0d8001f3-0814-61f3-9b3e-0000003001f3"; :>> outcome = VerdictKind::pass; :>> judgedAgainst = "07f000f"; :>> judgedAt = "2026-08-15"; :>> judgedBy = "claudeOpus5"; }

    verification aqImplementGate : Test { :>> id = "0d8001f4-0814-61f4-9b3e-0000003001f4"; :>> title = "Sprint 292 implement gate"; :>> createdAt = "2026-08-15"; :>> createdBy = "claudeOpus5"; :>> method = VerificationMethod::test; :>> procedureText = "Three decisions carry the design. (1) The per-sitting review is ONE batched row naming 247 sprints, not 247 rows: D0049 makes the review per SITTING rather than per sprint, so a row each would misstate the ask by two orders of magnitude and invite precisely the rubber-stamping being avoided. (2) `asOf` comes from the HEAD commit date rather than the clock (D0013), so ages are deterministic across contributors — a wall clock would make two people disagree about whether the same item is escalated. (3) Escalation MARKS and never blocks: a contributor stalling on the queue would make the bottleneck worse rather than visible, which is the failure the item's own text warns about. The day arithmetic is exact civil-date maths with a leap-year test, because the SIGN of the comparison is what implements grandfathering — invert it and every historical item is resurrected."; }
    part aqImplementGateR1 : TestResult { :>> id = "0d8001f5-0814-61f5-9b3e-0000003001f5"; :>> outcome = VerdictKind::pass; :>> judgedAgainst = "07f000f"; :>> judgedAt = "2026-08-15"; :>> judgedBy = "claudeOpus5"; }

    verification aqReviewGate : Test { :>> id = "0d8001f6-0814-61f6-9b3e-0000003001f6"; :>> title = "Sprint 292 review gate"; :>> createdAt = "2026-08-15"; :>> createdBy = "claudeOpus5"; :>> method = VerificationMethod::inspect; :>> procedureText = "Reviewed, and the number is uncomfortable in a way worth stating plainly: 247 sprints have never had a sitting review, and 54 findings at or above Medium sit undispositioned, 15 of them past the escalation threshold. That is the true state, it has been true for a while, and the queue's value is precisely that it says so instead of averaging it away. The unknown-obligation fallback is `0000-00-00`, which grandfathers NOTHING — a typo in an obligation name cannot silently empty the queue, which is the failure mode that would make this command quietly worthless."; }
    part aqReviewGateR1 : TestResult { :>> id = "0d8001f7-0814-61f7-9b3e-0000003001f7"; :>> outcome = VerdictKind::pass; :>> judgedAgainst = "07f000f"; :>> judgedAt = "2026-08-15"; :>> judgedBy = "claudeOpus5"; }

    verification aqCloseOutGate : Test { :>> id = "0d8001f8-0814-61f8-9b3e-0000003001f8"; :>> title = "Sprint 292 closeOut gate (autonomous, D0049)"; :>> createdAt = "2026-08-15"; :>> createdBy = "claudeOpus5"; :>> method = VerificationMethod::inspect; :>> procedureText = "Autonomous closeOut (D0049). dcAuthorityQueue carries a passing DoD TestResult. Queue measured against this repo with age, origin and escalation; grandfathering demonstrated numerically (287 uncovered, 247 owed, 40 correctly excluded); no self-evidencing test result can appear, by construction. clippy clean; 136 lib tests; validate 314 clean; check-engine clean; 29 guards green. No gate bypassed."; }
    part aqCloseOutGateR1 : TestResult { :>> id = "0d8001f9-0814-61f9-9b3e-0000003001f9"; :>> outcome = VerdictKind::pass; :>> judgedAgainst = "07f000f"; :>> judgedAt = "2026-08-15"; :>> judgedBy = "claudeOpus5"; }

    verification aqRetroGate : Test { :>> id = "0d8001fa-0814-61fa-9b3e-0000003001fa"; :>> title = "Sprint 292 retro gate (autonomous, D0049)"; :>> createdAt = "2026-08-15"; :>> createdBy = "claudeOpus5"; :>> method = VerificationMethod::analyze; :>> procedureText = "Autonomous retro (D0049) under D0131's retroTrack. WELL: (1) VOLUME was measured before any code was written, and the ~340-item answer is what forced the grandfathering filter and the batched review row — a correctly-implemented, unusable command was the real risk here and the consumer check caught it; (2) each obligation's cutoff cites the Decision that created it, so the filter deciding what a human never sees is auditable rather than arbitrary; (3) the uncomfortable numbers are reported rather than softened, which is the only reason the queue is worth reading. AVOIDABLE-ISSUE 1: the heredoc failed AGAIN on a Rust block containing quotes — fifth instance this pass — and I switched to writing the block as a file and splicing it, which worked first time. NO NEW ITEM: issue094 carries the class and sprint 285 built the advisory hook for the shell-adaptation half; this half is 'do not build source through a shell heredoc', and the remedy is mechanical rather than detectable. What is new and worth recording: writing the block to a FILE and splicing it is strictly better than either heredoc or many small edits for a 200-line insertion, and that is now the default I should reach for. Estimate 5 pts, delivered."; }
    part aqRetroGateR1 : TestResult { :>> id = "0d8001fb-0814-61fb-9b3e-0000003001fb"; :>> outcome = VerdictKind::pass; :>> judgedAgainst = "07f000f"; :>> judgedAt = "2026-08-15"; :>> judgedBy = "claudeOpus5"; }
}
