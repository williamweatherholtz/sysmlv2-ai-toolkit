// ProjectDeliveryS626 — Sprint 626: A Release carries the tag it names as its own field, and the release-recorded guard binds on that field, never on a title (dcReleaseRecordNamesItsTag, issue387, D0400). EXECUTE. 3 pts.
package ProjectDeliveryS626 {
    private import EngineElement::*;
    private import EngineWork::*;
    private import EngineVerification::*;
    private import EngineRelationships::*;

    #CharteredBy dependency from releaseRecordNamesItsTagStory to d0400;

    part releaseRecordNamesItsTagStory : Story {
        :>> id = "1a806bd3-fc33-40d6-9a79-bdb880f82c05";
        :>> title = "Sprint 626: A Release carries the tag it names as its own field, and the release-recorded guard binds on that field, never on a title (dcReleaseRecordNamesItsTag, issue387, D0400) (3 pts)";
        :>> createdAt = "2026-09-09"; :>> createdBy = "claudeOpus5"; :>> kind = WorkKind::code; :>> priority = WorkPriority::p0; :>> owner = "claudeOpus5"; :>> estimatedPoints = 3;
    }

    action def DeliveryRunS626 {
        action storyReleaseRecordNamesItsTag;
        verification storyReleaseRecordNamesItsTagDoD : Test { :>> id = "abce04c8-8551-4256-9d60-b9ea4d3e915e"; :>> method = VerificationMethod::test; :>> procedureText = "DELIVERED: `Release.tag : String [0..1]` in the frozen core schema (baseline.sysml, co-committed with proposed D0400 under the D0070 lock); guard release-recorded matches a tag to the record whose `tag` field EQUALS it through the pure `release_for_tag`, retired records skipped, and its warning names the field to fill; migration `.engine/tools/migrations/2026-09-09-release-tag-field.py` (D0067: dry run, four control totals, idempotent) tagged the ten records whose title opens with a version token and left the three milestones untagged. VERIFIED: unit test a_release_is_bound_to_its_tag_by_the_field_and_nothing_else - v0.4.1 binds to release041 not to release040 whose prose names it, v0.4.11 is not vouched for by v0.4.1, a missing tag is None, a retired record does not vouch; live probe: removing release041's tag line made the guard WARN naming v0.4.1 (and nothing else), the migration restored the file to md5 eb3fe497, and the guard reads 9 scanned 0 warnings on this tree for a pointable reason (ten `:>> tag` fields, nine distinct). validate_schema.py 20/20; release build, clippy -D warnings and keel-cli lib tests exit 0. Docs: guards.md row, release skill step 4."; }
        // RAN: unit test a_release_is_bound_to_its_tag_by_the_field_and_nothing_else 1 passed; live probe positive (v0.4.1 warned when its tag line was removed) and negative (0 warnings restored, md5 eb3fe497)
        part storyReleaseRecordNamesItsTagDoDR1 : TestResult { :>> id = "a90b880f-31c0-41b5-ae65-167c6d6622fc"; :>> outcome = VerdictKind::pass; :>> judgedAgainst = "3a3d821"; :>> judgedAt = "2026-09-09"; :>> judgedBy = "claudeOpus5"; }
    }

    verification releaseRecordNamesItsTagRefineGate : Test { :>> id = "e4aaff6f-f640-403e-a8ec-fd5d5360575a"; :>> title = "Sprint 626 refine gate (DoR)"; :>> createdAt = "2026-09-09"; :>> createdBy = "claudeOpus5"; :>> method = VerificationMethod::inspect; :>> procedureText = "READY. Head of keel whats-next after sprint 625. The DoD names the shape (an authored field, matched exactly, migrated in) and calls it a Change Request on the frozen schema, so the Decision is recorded FIRST with the process-change marker and stays proposed for the human (D0337); the change rides the lock co-committed, as D0363 did. 3 points: schema line, guard refactor with a pure matcher, a D0067 migration with totals, doc-sync."; }
    // RAN: keel whats-next . at 3a3d821: dcReleaseRecordNamesItsTag at the head; D0400 recorded proposed with the process-change marker; 3 points
    part releaseRecordNamesItsTagRefineGateR1 : TestResult { :>> id = "7586427d-09b9-42bf-9ae3-1a2db69e320b"; :>> outcome = VerdictKind::pass; :>> judgedAgainst = "3a3d821"; :>> judgedAt = "2026-09-09"; :>> judgedBy = "claudeOpus5"; }
    verification releaseRecordNamesItsTagStandupGate : Test { :>> id = "92131002-66f2-47d7-a82e-5d89d7b713bc"; :>> title = "Sprint 626 standup gate"; :>> createdAt = "2026-09-09"; :>> createdBy = "claudeOpus5"; :>> method = VerificationMethod::inspect; :>> procedureText = "Blockers: none within the sprint. D0400 waits on the human and reaches them through the brief; nothing here depends on that word except the Decision's own standing."; }
    // RAN: blockers none; D0400 waits on the human via the brief
    part releaseRecordNamesItsTagStandupGateR1 : TestResult { :>> id = "36f3505d-85d0-4fba-ae32-2f287e1828d5"; :>> outcome = VerdictKind::pass; :>> judgedAgainst = "3a3d821"; :>> judgedAt = "2026-09-09"; :>> judgedBy = "claudeOpus5"; }
    verification releaseRecordNamesItsTagImplementGate : Test { :>> id = "558d5637-3adf-4363-8b97-25084ea8303d"; :>> title = "Sprint 626 implement gate"; :>> createdAt = "2026-09-09"; :>> createdBy = "claudeOpus5"; :>> method = VerificationMethod::test; :>> procedureText = "baseline.sysml gains `tag`; guards.rs gains ReleaseRow, release_for_tag (empty tag never binds, retired skipped, equality not containment) and release_tag_tests; the block reader takes `:>> tag` instead of `:>> title`. Migration dry run: conservation 10 == 10, coverage 9 of 9 tags, no-leak 10 + 3 + 0 == 13 blocks, content hash equal; applied, re-run 0 to change. Clippy caught a too-long first doc paragraph and an implicit hasher; both fixed."; }
    // RAN: validate_schema.py 20/20; cargo build --release exit 0; cargo clippy --release -p keel-cli -- -D warnings exit 0; cargo test --release -p keel-cli --lib release_tag_tests 1 passed; migration dry run 10==10, 9 of 9, 10+3+0==13, hash equal; --apply wrote 10, re-run 0 to change
    part releaseRecordNamesItsTagImplementGateR1 : TestResult { :>> id = "57305686-559e-494d-8834-30919b34f052"; :>> outcome = VerdictKind::pass; :>> judgedAgainst = "3a3d821"; :>> judgedAt = "2026-09-09"; :>> judgedBy = "claudeOpus5"; }
    verification releaseRecordNamesItsTagReviewGate : Test { :>> id = "72ccb95e-255a-4d0c-b0d9-368b88a482b7"; :>> title = "Sprint 626 review gate — three passes per D0172"; :>> createdAt = "2026-09-09"; :>> createdBy = "claudeOpus5"; :>> method = VerificationMethod::inspect; :>> procedureText = "Pass 1 (intent): the DoD's four VERIFY clauses are each a named assertion in the unit test or a step of the live probe. Pass 2 (defects): the probe was run positive-then-negative on the real tree before the guard's answer was stated (D0388) - one tag line removed, the warning read back naming that tag, the file restored to the same md5. The retired release020 also carries `tag = v0.2.0`; it is truthful (it IS the record of that tag as intended) and the guard skips it, so v0.2.0 binds to release020Shipped. Pass 3 (docs): the D0400 consequences said nine tagged records; the census found ten (the retired one) and the text was corrected before any acceptance, by its owner."; }
    // RAN: live probe: tag line for v0.4.1 removed -> keel guard release-recorded WARN naming v0.4.1 only; migration --apply restored the file to md5 eb3fe497 (equal before); guard 9 scanned 0 warnings
    part releaseRecordNamesItsTagReviewGateR1 : TestResult { :>> id = "0451b4f3-8d29-46f2-802e-9904c7ac1ec1"; :>> outcome = VerdictKind::pass; :>> judgedAgainst = "3a3d821"; :>> judgedAt = "2026-09-09"; :>> judgedBy = "claudeOpus5"; }
    verification releaseRecordNamesItsTagCloseOutGate : Test { :>> id = "7c6553a7-0c57-4a6c-83ea-c4e039309864"; :>> title = "Sprint 626 closeOut gate (autonomous, D0049)"; :>> createdAt = "2026-09-09"; :>> createdBy = "claudeOpus5"; :>> method = VerificationMethod::inspect; :>> procedureText = "A tag now names its record by a typed fact. A title can say anything true, including another version's name, and the guard no longer cares."; }
    // RAN: keel-serve.exe guard . --no-receipt exit 0; validate . 711 clean; check-engine . clean; sync-claude applied
    part releaseRecordNamesItsTagCloseOutGateR1 : TestResult { :>> id = "87a05cd0-2eb5-448c-a1f8-d9d97aadcac1"; :>> outcome = VerdictKind::pass; :>> judgedAgainst = "3a3d821"; :>> judgedAt = "2026-09-09"; :>> judgedBy = "claudeOpus5"; }
    verification releaseRecordNamesItsTagRetroGate : Test { :>> id = "78811d04-ff57-4b77-875e-f59beace10af"; :>> title = "Sprint 626 retro gate (autonomous, D0049)"; :>> createdAt = "2026-09-09"; :>> createdBy = "claudeOpus5"; :>> method = VerificationMethod::analyze; :>> procedureText = "Retro held; avoidable-issue scan: the Decision's consequences were drafted from the DoD's count (nine) before the census ran (ten) - text stated before the check, the D0388 class in miniature, caught in review because the migration's totals disagreed with the prose. Already tracked: the D0388 rule itself and dcSynopsisCitesLiveDecisions (issue423) are the standing controls for prose that cites a fact it did not read; no new item."; }
    // RAN: retro held; avoidable-issue scan: Decision count drafted before the census (nine vs ten), caught by the migration totals; already tracked by D0388 and issue423/dcSynopsisCitesLiveDecisions; no new item
    part releaseRecordNamesItsTagRetroGateR1 : TestResult { :>> id = "86fba366-ad5d-4611-95af-9194484b94f2"; :>> outcome = VerdictKind::pass; :>> judgedAgainst = "3a3d821"; :>> judgedAt = "2026-09-09"; :>> judgedBy = "claudeOpus5"; }
}
