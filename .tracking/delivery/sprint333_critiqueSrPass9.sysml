// ProjectDeliveryS333 — Sprint 333: critique pass 9 — the LAST critiquable SystemRequirements. Every SR
// not authored by claudeOpus5 is now critique-covered. EXECUTE. 3 pts.
package ProjectDeliveryS333 {
    private import EngineElement::*;
    private import EngineWork::*;
    private import EngineVerification::*;
    private import EngineRelationships::*;

    #CharteredBy dependency from critPass9Story to d0080;

    part critPass9Story : Story {
        :>> id = "0d800480-0814-6480-9b3e-000000300480";
        :>> title = "Sprint 333: critique pass 9 — the last 5 critiquable SRs, 10 fail / 5 pass (3 pts)";
        :>> createdAt = "2026-08-17"; :>> createdBy = "claudeOpus5"; :>> kind = WorkKind::modeling; :>> priority = WorkPriority::p0; :>> owner = "claudeOpus5"; :>> estimatedPoints = 3;
    }

    action def DeliveryRunS333 {
        action storyCritPass9;
        verification storyCritPass9DoD : Test { :>> id = "0d800481-0814-6481-9b3e-000000300481"; :>> method = VerificationMethod::analyze; :>> procedureText = "Pass 9: srViewerSchemaApi, srViewerScopedAuthoring, srViewerSearchDiscovery, srViewerSystemBoundViews, srViewerVisualViewpoint. 10 fail, 5 pass. MILESTONE: SystemRequirement coverage 20 -> 30 of 72 across passes 8 and 9, and the target picker now reports 0 critiquable with 42 blocked — every SR not authored by claudeOpus5 is covered, and 72 minus 30 is exactly the blocked set. THREE FINDINGS. (1) AN ELEMENT WITH A TITLE IS NOT FINDABLE BY ITS NAME: srViewerSearchDiscovery scopes search to displayLabel plus id, and view::display_label returns the TITLE when present, falling back to the name only when it is blank — so the name is searchable only for untitled elements, while `orient`, `whats-next`, `open-issues` and every guard message identify elements BY NAME. A user who reads dcViewpointEnumeration in a computed view and types it into the search finds nothing; the id half is a UUID nobody types. One word fixes it. (2) SIBLING HAS NO BASIS IN THE TYPED GRAPH: srViewerSystemBoundViews defines sibling as 'same type + shared parent' and then requires 'pure computed views over the typed graph', while nothing in schema/core declares containment — shared parent can only mean same FILE, which is a storage location rather than a modelled fact and changes when a file is split. (3) srViewerSchemaApi commits to a line-oriented TEXT SCAN of the schema, which is the exact mechanism that shipped broken in the attribute-vocabulary guard (8088 of 41036 assignments scanned, reported PASS) — so a valid but unanticipated layout is silently absent and a generative UI silently omits those fields."; }
        part storyCritPass9DoDR1 : TestResult { :>> id = "0d800482-0814-6482-9b3e-000000300482"; :>> outcome = VerdictKind::pass; :>> judgedAgainst = "cd1637e"; :>> judgedAt = "2026-08-17"; :>> judgedBy = "claudeOpus5"; }
    }

    verification c9RefineGate : Test { :>> id = "0d800483-0814-6483-9b3e-000000300483"; :>> title = "Sprint 333 refine gate (DoR)"; :>> createdAt = "2026-08-17"; :>> createdBy = "claudeOpus5"; :>> method = VerificationMethod::inspect; :>> procedureText = "DoR. The last five critiquable SRs. Three mechanisms checked before judgment, and one of my planned findings did not survive: I expected search-over-displayLabel to exclude titles, and display_label RETURNS the title — so the defect is the mirror image of what I assumed, and sharper. Also checked: scan_schema_defs' path scope (the whole .engine/schema, broader than the requirement's 'schema/core'), and whether any parent or containment relation exists in schema/core (none does). estimatedPoints=3."; }
    part c9RefineGateR1 : TestResult { :>> id = "0d800484-0814-6484-9b3e-000000300484"; :>> outcome = VerdictKind::pass; :>> judgedAgainst = "cd1637e"; :>> judgedAt = "2026-08-17"; :>> judgedBy = "claudeOpus5"; }

    verification c9StandupGate : Test { :>> id = "0d800485-0814-6485-9b3e-000000300485"; :>> title = "Sprint 333 standup gate"; :>> createdAt = "2026-08-17"; :>> createdBy = "claudeOpus5"; :>> method = VerificationMethod::inspect; :>> procedureText = "Approach: apply sprint 332's search discipline — when a finding turns on ABSENCE, search the CAPABILITY rather than the one expected location, and state what was searched. Used here for the containment question: I grepped schema/core for a parent relation rather than assuming its absence from the edge algebra I remembered. No blockers."; }
    part c9StandupGateR1 : TestResult { :>> id = "0d800486-0814-6486-9b3e-000000300486"; :>> outcome = VerdictKind::pass; :>> judgedAgainst = "cd1637e"; :>> judgedAt = "2026-08-17"; :>> judgedBy = "claudeOpus5"; }

    verification c9ImplementGate : Test { :>> id = "0d800487-0814-6487-9b3e-000000300487"; :>> title = "Sprint 333 implement gate"; :>> createdAt = "2026-08-17"; :>> createdBy = "claudeOpus5"; :>> method = VerificationMethod::analyze; :>> procedureText = "THE SECOND REQUIREMENT DEFERRING ITS OWN SUBSTANCE TO AN UNWRITTEN DECISION appears here: srViewerVisualViewpoint leaves its authoring surface as 'open question Q4', exactly as srViewerDatePredicates leaves its predicate bound as Q3, and neither Decision exists. That makes the structural gap named in sprint 331 a pattern rather than an instance: the engine can express blocked WORK (a #DependsOn to a proposed Decision drops an action off the ready frontier and shows in pendingAcceptances) and cannot express a blocked REQUIREMENT, so both of these read as ordinary coverage gaps rather than as decisions nobody has taken. I have still NOT proposed a mechanism, because it would be a schema-shaped change nobody has asked for — but two instances is worth recording as a count rather than as an anecdote. THE SEARCH FINDING IS THE MOST ACTIONABLE THING IN THIS PASS: a one-word fix (search displayLabel, NAME and id) makes the discovery surface reachable from the engine's own output, and without it every element identifier keel prints is unsearchable in the tool built to explore keel."; }
    part c9ImplementGateR1 : TestResult { :>> id = "0d800488-0814-6488-9b3e-000000300488"; :>> outcome = VerdictKind::pass; :>> judgedAgainst = "cd1637e"; :>> judgedAt = "2026-08-17"; :>> judgedBy = "claudeOpus5"; }

    verification c9ReviewGate : Test { :>> id = "0d800489-0814-6489-9b3e-000000300489"; :>> title = "Sprint 333 review gate"; :>> createdAt = "2026-08-17"; :>> createdBy = "claudeOpus5"; :>> method = VerificationMethod::inspect; :>> procedureText = "Reviewed across the five SR passes: 25 SystemRequirements, 75 lenses, 49 fail and 26 pass. THE PASS RATE ROSE FROM THE NEEDS PASSES (15 of 60) TO THE SR PASSES (26 of 75) and the reason is checkable rather than a drift in my standards: a requirement is written after its Need has been used, against a running prototype, and eight of the 26 passes are specifically for REPAIRING a defect I had faulted the parent Need for — srViewerInProgramEdit reframing an edit as a supersession, srViewerIterativeCritique naming the independent-critic discipline, srViewerExportShare adding the source commit, srViewerGraphExpand defining stable layout operationally, srViewerNavHistory keeping model writes out of client history. WHAT I AM NOT CLAIMING: that 30 of 72 SRs being covered means the architecture is sound. It means a judgment has been formed and recorded against each, with its reasoning and its evidence — the EXAMINED dimension of `keel verification`, which says nothing about whether the owner agrees."; }
    part c9ReviewGateR1 : TestResult { :>> id = "0d80048a-0814-648a-9b3e-00000030048a"; :>> outcome = VerdictKind::pass; :>> judgedAgainst = "cd1637e"; :>> judgedAt = "2026-08-17"; :>> judgedBy = "claudeOpus5"; }

    verification c9CloseOutGate : Test { :>> id = "0d80048b-0814-648b-9b3e-00000030048b"; :>> title = "Sprint 333 closeOut gate (autonomous, D0049)"; :>> createdAt = "2026-08-17"; :>> createdBy = "claudeOpus5"; :>> method = VerificationMethod::inspect; :>> procedureText = "Autonomous closeOut (D0049). SYSTEMREQUIREMENTS ARE EXHAUSTED for this critic: 0 critiquable, 42 blocked, coverage 30 of 72. Needs were exhausted at sprint 327. Remaining critiquable: 22 Decisions. Zero open issues; ready frontier empty; D0159 queued. validate clean; check-engine clean; 35 guards ALL PASS; no code changed in any of the five SR passes."; }
    part c9CloseOutGateR1 : TestResult { :>> id = "0d80048c-0814-648c-9b3e-00000030048c"; :>> outcome = VerdictKind::pass; :>> judgedAgainst = "cd1637e"; :>> judgedAt = "2026-08-17"; :>> judgedBy = "claudeOpus5"; }

    verification c9RetroGate : Test { :>> id = "0d80048d-0814-648d-9b3e-00000030048d"; :>> title = "Sprint 333 retro gate (autonomous, D0049)"; :>> createdAt = "2026-08-17"; :>> createdBy = "claudeOpus5"; :>> method = VerificationMethod::analyze; :>> procedureText = "Autonomous retro (D0049) under D0131's retroTrack, covering the five-pass SystemRequirement backfill. WELL: (1) sprint 332's search discipline was applied the very next pass and worked — I grepped the CAPABILITY (containment, parent) rather than trusting my memory of the edge algebra, and it confirmed the absence I then asserted; (2) a planned finding died again on contact with display_label, and the mirror-image defect it revealed is more useful than the one I expected — the pattern across nine passes is that checking a claim tends to SHARPEN the finding rather than remove it; (3) the pass-rate rise was explained with named evidence rather than asserted, so a reader can test whether I softened. AVOIDABLE-ISSUE: none this sprint. CARRIED FORWARD: two requirements now defer their substance to Decisions nobody wrote (Q3, Q4), which makes the blocked-requirement gap a counted pattern; and the same nothing-hardcoded fixture is now named by SIX elements and still does not exist. Estimate 3 pts, delivered — 15 pts across the five SR passes against 15 estimated."; }
    part c9RetroGateR1 : TestResult { :>> id = "0d80048e-0814-648e-9b3e-00000030048e"; :>> outcome = VerdictKind::pass; :>> judgedAgainst = "cd1637e"; :>> judgedAt = "2026-08-17"; :>> judgedBy = "claudeOpus5"; }
}
