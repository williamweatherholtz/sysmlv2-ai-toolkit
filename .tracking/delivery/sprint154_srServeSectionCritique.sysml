// ProjectDeliveryS154 — Sprint 154: sr18Deliver (verifies sr18ServeSectionCritique) — section-local
// render + section-scoped critique. NEW view::section_json + GET /api/section (a declared view's
// element set, OR an element + its 1-hop typed-edge neighbourhood); section-scoped critique (the AI
// judges a target within its bounded local context) via an optional AgentReq.section seed; a console
// Section tab. EXECUTE. 3 pts. AUTONOMOUS (D0049). Reuses the view Model/traverse/emit + sr16 critique substrate.
package ProjectDeliveryS154 {
    private import EngineElement::*;
    private import EngineWork::*;
    private import EngineVerification::*;
    private import EngineRelationships::*;

    #CharteredBy dependency from srServeSectionCritiqueStory to sr18ServeSectionCritique;

    part srServeSectionCritiqueStory : Story {
        :>> id = "63940516-2c7d-4e8f-c154-51627384c001";
        :>> title = "Sprint 154: sr18Deliver (3 pts) — section-local render + section-scoped critique (verifies sr18)";
        :>> createdAt = "2026-06-24"; :>> createdBy = "wweatherholtz"; :>> kind = WorkKind::code; :>> priority = WorkPriority::p2; :>> owner = "claudeOpus"; :>> estimatedPoints = 3;
    }

    action def DeliveryRunS154 {
        action storySrServeSectionCritique;
        verification storySrServeSectionCritiqueDoD : Test { :>> id = "63940516-2c7d-4e8f-c154-51627384c002"; :>> method = VerificationMethod::test; :>> procedureText = "Satisfies sr18ServeSectionCritique (Need n17ServeGranularWhitebox): whole-model views are too coarse for local 'does X make sense here' critique. DELIVERED: (1) view::section_json + GET /api/section?view=NAME|element=NAME -> {seed,kind,count,items[],edges[]} — a declared view's element set OR an element + its 1-hop typed-edge neighbourhood (induced subgraph). (2) section-scoped critique: AgentReq gains an optional `section` seed (view:/element:); section_member_names resolves the bound; build_agent_prompt names the local neighbourhood so the AI judges the target IN CONTEXT, still recording findings against the section's elements via the sr16 critique path. (3) a console Section tab: pick a view or element -> render the bounded section -> 'Critique in section'. VERIFIED LIVE: curl ?element=sr18ServeSectionCritique -> 2 items (sr18 + satisfy-neighbour n17) + the induced satisfy edge; ?view=issues -> 48 items; no-seed/unknown-element -> 400 + clear error. Unit-tested: element_neighbourhood, section_subgraph_json (induced edges only), parse_section_seed, build_agent_prompt (scoped only with members). clippy -D warnings + cargo test (60 lib) + keel validate (167) + guard all (12) green; sr18Verify (#Verify -> sr18) records it."; }
        part storySrServeSectionCritiqueDoDR1 : TestResult { :>> id = "63940516-2c7d-4e8f-c154-51627384c003"; :>> outcome = VerdictKind::pass; :>> judgedAgainst = "665aa4d"; :>> judgedAt = "2026-06-24"; :>> judgedBy = "claudeOpus"; }
    }

    verification srServeSectionCritiqueRefineGate : Test { :>> id = "63940516-2c7d-4e8f-c154-51627384c004"; :>> title = "Sprint 154 refine gate (DoR)"; :>> createdAt = "2026-06-24"; :>> createdBy = "claudeOpus"; :>> method = VerificationMethod::inspect; :>> procedureText = "DoR: sr18ServeSectionCritique is an unverified tier-satisfaction gap (D0098) authored by serveRequirementsTrace (sprint149); first of the two remaining serve SRs under n17ServeGranularWhitebox. Scope: render a bounded section (declared view OR element + 1-hop neighbourhood) + record section-scoped critique against its elements. Reuses the existing serve console (sr15/16/17) + view Model/traverse/emit substrate, so estimatedPoints=3 (matching sibling serve sprints). #CharteredBy sr18ServeSectionCritique. Backlog action sr18Deliver authored (human-approved: 'author backlog actions for both, then sprint sr18 first'). DoR met."; }
    part srServeSectionCritiqueRefineGateR1 : TestResult { :>> id = "63940516-2c7d-4e8f-c154-51627384c005"; :>> outcome = VerdictKind::pass; :>> judgedAgainst = "665aa4d"; :>> judgedAt = "2026-06-24"; :>> judgedBy = "claudeOpus"; }
    verification srServeSectionCritiqueStandupGate : Test { :>> id = "63940516-2c7d-4e8f-c154-51627384c006"; :>> title = "Sprint 154 standup gate"; :>> createdAt = "2026-06-24"; :>> createdBy = "claudeOpus"; :>> method = VerificationMethod::inspect; :>> procedureText = "Approach (TDD): (a) view.rs — element_neighbourhood (element + 1-hop, both directions) + section_subgraph_json (induced-edge emit via the Json helper) + section_json/section_member_names over a shared resolve_section (view => run_resolved; element => Model::build + neighbourhood). (b) serve.rs — GET /api/section (SectionReq) + section-scoped critique (AgentReq.section + parse_section_seed + build_agent_prompt enrichment). (c) console.html — a Section tab (view|element seed -> render -> per-element 'Critique in section'). Tests-first for every pure fn. The live AI critique itself drives `claude -p` (billing, D0094) so the wiring is unit-tested rather than spawned. No blockers."; }
    part srServeSectionCritiqueStandupGateR1 : TestResult { :>> id = "63940516-2c7d-4e8f-c154-51627384c007"; :>> outcome = VerdictKind::pass; :>> judgedAgainst = "665aa4d"; :>> judgedAt = "2026-06-24"; :>> judgedBy = "claudeOpus"; }
    verification srServeSectionCritiqueImplementGate : Test { :>> id = "63940516-2c7d-4e8f-c154-51627384c008"; :>> title = "Sprint 154 implement gate"; :>> createdAt = "2026-06-24"; :>> createdBy = "claudeOpus"; :>> method = VerificationMethod::test; :>> procedureText = "TDD red->green: 3 element_neighbourhood tests (element+1-hop, incoming neighbours, stops-at-1-hop) + 2 section_subgraph_json tests (induced edges, excludes leaving edges) + parse_section_seed + build_agent_prompt (section-scoped only with members) — all written failing first, then implemented. /api/section + console Section tab added. clippy -D warnings clean (fixed 6 first-pass lints: map_or_else, write!-not-push_str(format!), 2 too-long-first-doc-paragraph, doc-backticks, single-item iter). cargo test 60 lib + workspace green; keel validate 167 + guard all (12) green. Live: /api/section element + view seeds + error cases verified."; }
    part srServeSectionCritiqueImplementGateR1 : TestResult { :>> id = "63940516-2c7d-4e8f-c154-51627384c009"; :>> outcome = VerdictKind::pass; :>> judgedAgainst = "665aa4d"; :>> judgedAt = "2026-06-24"; :>> judgedBy = "claudeOpus"; }
    verification srServeSectionCritiqueReviewGate : Test { :>> id = "63940516-2c7d-4e8f-c154-51627384c00a"; :>> title = "Sprint 154 review gate"; :>> createdAt = "2026-06-24"; :>> createdBy = "claudeOpus"; :>> method = VerificationMethod::inspect; :>> procedureText = "Diff reviewed. section_json is a THIN layer over the existing view substrate (resolve_section reuses run_resolved + Model::build + traverse-style neighbourhood; emit reuses the Json helper) — no duplicated model logic. The genuine value of sr18 is that the section gives the critique LOCAL CONTEXT (build_agent_prompt names the neighbourhood) rather than an isolated-element critique. Honest scope: the render half is live-verified end to end; the AI critique half is unit-tested wiring (section seed -> member resolution -> prompt) rather than a spawned `claude -p` run, to avoid headless billing (D0094) — the same section_member_names path is exercised live by /api/section. Clean."; }
    part srServeSectionCritiqueReviewGateR1 : TestResult { :>> id = "63940516-2c7d-4e8f-c154-51627384c00b"; :>> outcome = VerdictKind::pass; :>> judgedAgainst = "665aa4d"; :>> judgedAt = "2026-06-24"; :>> judgedBy = "claudeOpus"; }
    verification srServeSectionCritiqueCloseOutGate : Test { :>> id = "63940516-2c7d-4e8f-c154-51627384c00c"; :>> title = "Sprint 154 closeOut gate (autonomous, D0049)"; :>> createdAt = "2026-06-24"; :>> createdBy = "claudeOpus"; :>> method = VerificationMethod::inspect; :>> procedureText = "Autonomous closeOut (D0049): DoD pass; section-local render + section-scoped critique delivered. clippy + cargo test (60 lib) + keel validate (167) + guard all (12) green. Self-evidencing (D0051). sr18ServeSectionCritique verified -> tier-satisfaction SR-verified now 18/19 (sr19ServeWhiteboxBoundary the sole remaining gap). Of the serve SRs sr15-sr19, 4 of 5 are done; sr19 (AI white-box boundary, the chained tier-satisfaction sweep) remains — its backlog action sr19Deliver is authored + ready."; }
    part srServeSectionCritiqueCloseOutGateR1 : TestResult { :>> id = "63940516-2c7d-4e8f-c154-51627384c00d"; :>> outcome = VerdictKind::pass; :>> judgedAgainst = "665aa4d"; :>> judgedAt = "2026-06-24"; :>> judgedBy = "claudeOpus"; }
    verification srServeSectionCritiqueRetroGate : Test { :>> id = "63940516-2c7d-4e8f-c154-51627384c00e"; :>> title = "Sprint 154 retro gate (autonomous, D0049)"; :>> createdAt = "2026-06-24"; :>> createdBy = "claudeOpus"; :>> method = VerificationMethod::analyze; :>> procedureText = "Autonomous retro (D0049). WELL: section_json fell out of the existing view substrate almost for free (resolve_section over run_resolved + a tiny element_neighbourhood) — the D0075 select/traverse/emit separation paid off; the section's real worth is feeding the critique its LOCAL CONTEXT, which the prompt enrichment captures without a new write-trust surface. TDD held: every pure fn was red-first. AVOIDABLE-ISSUE SCAN: clippy flagged 6 lints on the first run (too-long-first-doc-paragraph x2, push_str(&format!), map_or_else, doc-backticks, single-item iter) AFTER cargo test was green — LESSON: run `cargo clippy --all-targets -D warnings` BEFORE declaring implement done, not after, since the local 1.96 toolchain (localGateMatchesCi) catches exactly what CI would. NON-blocking: the AI-critique half is unit-tested, not spawn-verified (billing) — acceptable and consistent with sr16. Estimate 3 pts held. NEXT: sr19Deliver (white-box boundary + the tier-satisfaction sweep) is the last n17 item."; }
    part srServeSectionCritiqueRetroGateR1 : TestResult { :>> id = "63940516-2c7d-4e8f-c154-51627384c00f"; :>> outcome = VerdictKind::pass; :>> judgedAgainst = "665aa4d"; :>> judgedAt = "2026-06-24"; :>> judgedBy = "claudeOpus"; }

    // Per-sitting human review (D0049/issue040) — the SINGLE human gate. The human explicitly accepted
    // Sprint 154's content on 2026-06-24 ("sprint 154 accepted"); recorded as a method=confirmation review
    // whose #Covers edge attests the sprint Story. FIRST per-sitting review recorded in the repo.
    verification sittingRevS154 : Test { :>> id = "63940516-2c7d-4e8f-c154-51627384c010"; :>> title = "Per-sitting review — Sprint 154 accepted by the human"; :>> createdAt = "2026-06-24"; :>> createdBy = "wweatherholtz"; :>> method = VerificationMethod::confirmation; :>> procedureText = "Per-sitting review (D0049, the single human touchpoint): the human reviewed Sprint 154 (sr18Deliver — section-local render + section-scoped critique) and EXPLICITLY accepted its content. The test-backed work is self-evidencing (D0051) — clippy -D warnings, 60 lib tests, keel validate 168, guard all 12, and GitHub CI all green; this confirmation attests the sitting's direction/acceptance (the irreducible human judgment, D0016). First per-sitting review in the repo (sitting-coverage was 0-covered)."; }
    part sittingRevS154R1 : TestResult { :>> id = "63940516-2c7d-4e8f-c154-51627384c011"; :>> outcome = VerdictKind::pass; :>> judgedAgainst = "85706b3"; :>> judgedAt = "2026-06-24"; :>> judgedBy = "wweatherholtz"; }
    #Covers dependency from sittingRevS154 to srServeSectionCritiqueStory;
}
