// ProjectDeliveryS679 — Sprint 679: The orientation family joins keel show. Under D0450 (d0399 option A, the human's word 2026-09-11) the eleven read-only orientation verbs - orient, whats-next, status, view, item, arch, attestation, actor-trace, governing-version, reprocess-candidates, enforcement-report - leave the top-level dispatch and become lenses of `keel show`, each keeping its word and its arguments, in the sprint 512 shape (D0273): a committed transform rewrites every call site in the same commit, no alias window, and the pre-fold binary is held byte-equal to the post-fold binary on every moved verb. Delivers the second of the five folds dcRemainingCliFamilies names; the dispatch count hardening reads drops 69 to 58. CHANGE.. EXECUTE. 5 pts.
package ProjectDeliveryS679 {
    private import EngineElement::*;
    private import EngineWork::*;
    private import EngineVerification::*;
    private import EngineRelationships::*;

    #CharteredBy dependency from orientationFamilyFoldStory to d0450;

    part orientationFamilyFoldStory : Story {
        :>> id = "5257e189-86e8-481d-b571-bf3d06a8f1db";
        :>> title = "Sprint 679: The orientation family joins keel show. Under D0450 (d0399 option A, the human's word 2026-09-11) the eleven read-only orientation verbs - orient, whats-next, status, view, item, arch, attestation, actor-trace, governing-version, reprocess-candidates, enforcement-report - leave the top-level dispatch and become lenses of `keel show`, each keeping its word and its arguments, in the sprint 512 shape (D0273): a committed transform rewrites every call site in the same commit, no alias window, and the pre-fold binary is held byte-equal to the post-fold binary on every moved verb. Delivers the second of the five folds dcRemainingCliFamilies names; the dispatch count hardening reads drops 69 to 58. CHANGE. (5 pts)";
        :>> createdAt = "2026-09-11"; :>> createdBy = "claudeOpus5"; :>> kind = WorkKind::code; :>> priority = WorkPriority::p0; :>> owner = "claudeOpus5"; :>> estimatedPoints = 5;
    }

    action def DeliveryRunS679 {
        action storyOrientationFamilyFold;
        verification storyOrientationFamilyFoldDoD : Test { :>> id = "9edc81b9-05be-4fcf-b152-dbd32b2b0243"; :>> method = VerificationMethod::test; :>> procedureText = "DELIVERED: `keel show <verb> ...` answers for all eleven verbs with the arguments unchanged; the eleven top-level arms are gone from main.rs, COMMAND_NAMES (68 to 57) and LENS_NAMES gains them (40 to 51); the eleven CliCommand facts carry family lens and a `show <verb> ...` invocation in both .engine/cli/commands.sysml and cli_facts.rs (108 facts, unchanged count); every call site under .engine, CLAUDE.md, README.md, docs, scripts and keel-cli/assets is rewritten by .engine/tools/migrations/2026-09-11-orientation-family-fold.py (dry-run default, per-file conservation, re-plan 0), the Rust usage strings and the test argv sites by hand, .claude/output-styles/keel.md by hand; .claude regenerated by keel sync-claude; the pre-fold binary (build e1de7c7) and the post-fold binary agree byte for byte on 18 of 20 cases, the two diffs being the status header that names the command and the old binary's own cli-surface-declared self-check against the post-fold surface; hardening reads dispatched 58/58; validate, check-engine, guard, clippy, the touched suite and the surface tests pass. Decisions and .tracking are not rewritten; the stpa fixture is not rewritten; facts.py line 480 keeps `keel orient` because it is a regex over D0367's attested text."; }
        // RAN: keel show orient . / whats-next / status / view decisions / item d0450 / arch elements / attestation / actor-trace claudeOpus5 / governing-version storyRenderFamilyFold / reprocess-candidates / enforcement-report on keel-serve.exe: all eleven answer; keel orient .: usage, exit 2 (no alias); compare679b.txt: 18 of 20 EQUAL against keel-prefold679.exe (build e1de7c7), DIFF only the status header naming the command and the old binary self-checking cli-surface-declared against the post-fold surface; keel show hardening .: dispatched 58 namedInHelp 58 coveragePct 100; COMMAND_NAMES 57, LENS_NAMES 51, 108 facts; transform 2026-09-11-orientation-family-fold.py --apply: 81 sites / 33 files, re-plan 0; keel validate 777 clean; check-engine clean; guard --no-receipt 0 violations; sync-claude --check matches; cargo clippy --release --all-targets -D warnings 0; cargo test --lib cli_surface 10 passed, --lib hardening 10 passed, --test capability_refusal_bites 5 passed; keel suite --touched: pass 776 passed 0 failed in 578s, receipt touched-receipt.toml at=1789169152 head=e1de7c7 (VERIFIER-RECEIPT.txt)
        part storyOrientationFamilyFoldDoDR1 : TestResult { :>> id = "471ee001-03e0-466a-99de-f7fb037fd608"; :>> outcome = VerdictKind::pass; :>> judgedAgainst = "e1de7c7c8e9e06e733df0948d037e43f3bde9650"; :>> judgedAt = "2026-09-11"; :>> judgedBy = "claudeOpus5"; }
    }

    verification orientationFamilyFoldRefineGate : Test { :>> id = "d2367330-7ffe-4af7-a357-58913932fdad"; :>> title = "Sprint 679 refine gate (DoR)"; :>> createdAt = "2026-09-11"; :>> createdBy = "claudeOpus5"; :>> method = VerificationMethod::inspect; :>> procedureText = "Chartered by D0450, plan-covered under D0396 by d0399 option A, accepted by the human 2026-09-11 on the brief copy-out. Five points: eleven dispatch arms move under one router with their bodies verbatim, two constant arrays, eleven facts in two homes, one Python transform over 33 prose files, 68 Rust prose sites and 22 argv test sites by hand, and a twenty-case byte comparison. Same shape as sprints 512 and 678. NOT A PROCESS CHANGE beyond what D0450 states - the fold is the Decision's own text. NOT A FORK - the fork was d0399 and is decided."; }
    // RAN: keel show authority-queue . before the sprint: d0399 option A accepted 2026-09-11 (brief copy-out); keel show item dcRemainingCliFamilies .: open, rendering fold delivered by sprint678; D0450 authored with --derived-from d0399; estimatedPoints 5; CharteredBy d0450 in the sprint file
    part orientationFamilyFoldRefineGateR1 : TestResult { :>> id = "f10b54ab-31b4-4653-8a1a-803cea8cc259"; :>> outcome = VerdictKind::proposed; :>> judgedAgainst = "e1de7c7c8e9e06e733df0948d037e43f3bde9650"; :>> judgedAt = "2026-09-11"; :>> judgedBy = "claudeOpus5"; }
    verification orientationFamilyFoldStandupGate : Test { :>> id = "b291048a-ae08-4eea-ac31-8d49ef91a69b"; :>> title = "Sprint 679 standup gate"; :>> createdAt = "2026-09-11"; :>> createdBy = "claudeOpus5"; :>> method = VerificationMethod::inspect; :>> procedureText = "Order, taken from the sprint 678 retro: preserve the pre-fold binary FIRST as keel-prefold679.exe from the landed build; move the eleven arms into cmd_show by script with each old line asserted unique; rebuild the router's two lens lists from its own arms (the hand-written list had already drifted by three lenses); shrink COMMAND_NAMES and grow LENS_NAMES and turn the eleven facts to family lens in both homes in one script so cli-surface-declared stays equal; rewrite Rust prose with the transform's own rule and the argv sites by a hand list each asserted to hit once; run the transform; sync-claude; rebuild; compare old against new back to back on this tree; read hardening; record. Blocker met: the transform would have rewritten a regex in scripts/exec_brief/facts.py that matches D0367's attested context string - excluded with its reason in the transform's docstring and the file's eight prose sites rewritten by hand."; }
    // RAN: cp target/release/keel.exe target/release/keel-prefold679.exe from the landed e1de7c7 build BEFORE any source edit; fold679_main.py: 11 arm moves each asserted unique; fold679_surface.py: two arrays + eleven facts in two homes in one script; transform --dry-run: 81 sites / 33 files with the facts.py regex site named as the blocker and excluded with its reason in the docstring
    part orientationFamilyFoldStandupGateR1 : TestResult { :>> id = "a1d26066-a4a2-44b0-8b99-70fcff032ce0"; :>> outcome = VerdictKind::proposed; :>> judgedAgainst = "e1de7c7c8e9e06e733df0948d037e43f3bde9650"; :>> judgedAt = "2026-09-11"; :>> judgedBy = "claudeOpus5"; }
    verification orientationFamilyFoldImplementGate : Test { :>> id = "d4af048c-8dca-4415-9471-efb9393aadf1"; :>> title = "Sprint 679 implement gate"; :>> createdAt = "2026-09-11"; :>> createdBy = "claudeOpus5"; :>> method = VerificationMethod::test; :>> procedureText = "keel-cli/src/main.rs: eleven arms removed from main() and inserted into cmd_show in sorted position with their bodies verbatim (arch keeps its repo_arg comment); the unknown-lens and usage lists rebuilt from the arms, 51 names. cli_surface.rs: COMMAND_NAMES 57, LENS_NAMES 51. cli_facts.rs and .engine/cli/commands.sysml: the eleven facts family lens, invocation `show <verb> <args>`, 108 facts. Rust prose and usage: 68 sites across 29 files by the transform's rule; argv call sites: 22 across 14 test files by hand (no_green_over_nothing's MODEL_READERS table, status_distinguishes_unknown, init_smoke, pin_actually_bites, judge_set_records_each_item, reverify_demos_replays_each_receipt and eight more). .claude/output-styles/keel.md line 30 by hand (a source, embedded by claude_surface.rs). Transform applied: 81 call sites across 33 files, re-plan 0 (viewpoint-registry 12, commands.sysml 11 titles, usage.md 11, CLAUDE.md 6, claude-md-template 4). status.rs header prints `keel show status`. keel sync-claude: 46/46 skills, --check matches."; }
    // RAN: cargo build --release -p keel-cli: Finished in 2m16s; transform --apply 81/33 then re-plan 0; fold679_rust.py: 68 prose sites across 29 files, 22 argv sites across 14 test files each asserted to hit once; fold679_lenslist.py: both Lenses eprintln sites now print LENS_NAMES.join; keel sync-claude: 46/46 skills, --check matches; keel show nonsense .: unknown lens, 51 names printed from LENS_NAMES
    part orientationFamilyFoldImplementGateR1 : TestResult { :>> id = "8d01440a-333b-4091-abc6-afcdd8e22e62"; :>> outcome = VerdictKind::pass; :>> judgedAgainst = "e1de7c7c8e9e06e733df0948d037e43f3bde9650"; :>> judgedAt = "2026-09-11"; :>> judgedBy = "claudeOpus5"; }
    verification orientationFamilyFoldReviewGate : Test { :>> id = "19d89b5f-3aa6-4e71-a982-e7eb63d2ef8e"; :>> title = "Sprint 679 review gate — three passes per D0172"; :>> createdAt = "2026-09-11"; :>> createdBy = "claudeOpus5"; :>> method = VerificationMethod::inspect; :>> procedureText = "Delivered and measured 2026-09-11: compare679.txt - 18 of 20 cases EQUAL between keel-prefold679.exe (build e1de7c7) and keel-serve.exe on the same tree back to back, stdout and exit code, nothing normalised: orient, whats-next, view x2, item x2, arch x6, attestation x2, actor-trace, governing-version, reprocess-candidates, enforcement-report. DIFF 1: `status` line 1 reads `keel show status` for `keel status` (the header names the command that produced it), and its model section reads OK on the new binary where the old reads 46 VIOLATIONs - the old binary's cli-surface-declared guard failing against the post-fold commands.sysml. DIFF 2: `orient --html` line 71 differs by that same count, 46 to 0 invariant blockers. Both are the retired surface checking itself, not a change in a moved arm. hardening dispatched 58 of 58, coveragePct 100. `keel orient .` on the new binary prints the usage - no alias."; }
    // RAN: python compare679.py > compare679b.txt: 18 of 20 EQUAL, DIFF status line 1 (keel show status header) and orient --html line 71 (46 vs 0 invariant blockers = old binary cli-surface-declared self-check); keel show hardening .: dispatched 58 namedInHelp 58 coveragePct 100; cargo clippy --release --all-targets -- -D warnings: exit 0; cargo test --lib cli_surface 10 passed; --lib hardening 10 passed; --test capability_refusal_bites 5 passed
    part orientationFamilyFoldReviewGateR1 : TestResult { :>> id = "52ece6a9-3511-4ffd-bdea-3abd1994abba"; :>> outcome = VerdictKind::proposed; :>> judgedAgainst = "e1de7c7c8e9e06e733df0948d037e43f3bde9650"; :>> judgedAt = "2026-09-11"; :>> judgedBy = "claudeOpus5"; }
    verification orientationFamilyFoldCloseOutGate : Test { :>> id = "02650337-7dbd-4c64-9b4b-d47b072118f4"; :>> title = "Sprint 679 closeOut gate (autonomous, D0049)"; :>> createdAt = "2026-09-11"; :>> createdBy = "claudeOpus5"; :>> method = VerificationMethod::inspect; :>> procedureText = "Sprint 679 closes on the byte comparison, the hardening read-back, validate, check-engine, guard, sync-claude --check, clippy, the surface tests and the touched suite. D0450 is staged with this sprint (keystone lock, D0209 cl.2). dcRemainingCliFamilies stays open: three folds remain, D0451 next, D0452 and D0453 on the human's word."; }
    // RAN: VERIFIER-RECEIPT.txt (haiku, skill test-verify, D0438): keel suite --touched pass 776 passed 0 failed 578s, stems changed MATCH, at 1789169152 > launch 1789168574, head e1de7c7; validate 777 clean; check-engine clean; guard --no-receipt 0 violations; sync-claude --check matches; D0388 pair: keel show orient . exit 0 JSON, keel orient . exit 2 usage; VERDICT green; git log -1 after the subagent: e1de7c7 unchanged
    part orientationFamilyFoldCloseOutGateR1 : TestResult { :>> id = "c0161201-d306-4459-82f1-fdf909a8b3af"; :>> outcome = VerdictKind::proposed; :>> judgedAgainst = "e1de7c7c8e9e06e733df0948d037e43f3bde9650"; :>> judgedAt = "2026-09-11"; :>> judgedBy = "claudeOpus5"; }
    verification orientationFamilyFoldRetroGate : Test { :>> id = "05d1e5ed-f60f-428a-ba93-2da41e837586"; :>> title = "Sprint 679 retro gate (autonomous, D0049)"; :>> createdAt = "2026-09-11"; :>> createdBy = "claudeOpus5"; :>> method = VerificationMethod::analyze; :>> procedureText = "AVOIDABLE-ISSUE SCAN: none new. FINDING: cmd_show's hand-written lens list had drifted from its arms by three names (control-census, control-structure, priority) before this sprint touched it - a list restated beside the arms it describes is a second home for the same fact; fixed at the root in this sprint: cmd_show now prints LENS_NAMES itself (main.rs, both the unknown-lens and usage paths), so the list has one home and cli-surface-declared already holds LENS_NAMES equal to the facts and the arms. No new item (D0131): the second home no longer exists, and the fold is d0450's own text. FINDING: the transform's file-level exclusion had to grow a single-file entry for a regex over attested text; the D0452/D0453 transforms should scan for `re.compile` and `re.search` sites over their verbs before the dry run. No new item (D0131): the scratch harness ends with the five folds, as the 678 retro said; dcRemainingCliFamilies carries the three that remain and this scan rides their standups."; }
    // RAN: fold679_main.py assert block.count(OLD_LIST) == 2 with the arms regex: the hand-written Lenses list lacked control-census, control-structure, priority; fixed at the root by fold679_lenslist.py (LENS_NAMES.join at both sites); keel guard retro-backlog --no-receipt .: PASS 0 violations after each finding named its item (d0450, dcRemainingCliFamilies); no new tracked item raised
    part orientationFamilyFoldRetroGateR1 : TestResult { :>> id = "7fe93bba-99cd-46f4-a7fe-49c8960f08bc"; :>> outcome = VerdictKind::proposed; :>> judgedAgainst = "e1de7c7c8e9e06e733df0948d037e43f3bde9650"; :>> judgedAt = "2026-09-11"; :>> judgedBy = "claudeOpus5"; }
}
