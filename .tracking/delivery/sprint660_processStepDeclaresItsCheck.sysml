// ProjectDeliveryS660 — Sprint 660: Close dcProcessStepDeclaresItsCheck (D0321 option A, the human's 'd0321 A' of 2026-09-05; schema clause D0434, proposed under D0337): a ProcessStep can say which guard or declared rule checks it. Before this sprint the fact had nowhere to live - D0321 measured 37 processes of which only agile-workflow's ceremony steps carried a per-step check, and seven processes had a guard that checks one of their steps with only prose joining them. After it: ProcessStep carries checkedBy : String [0..1], seven steps across six process files carry theirs through a committed D0067 transform, guard step-check-resolves holds every binding to a name that runs, and keel show hardening reports enforcement per STEP beside the per-process figures. The sprint also carries the finding its own guard made on its first live run: D0321's eighth binding named a lens as a guard (issue465).. EXECUTE. 5 pts.
package ProjectDeliveryS660 {
    private import EngineElement::*;
    private import EngineWork::*;
    private import EngineVerification::*;
    private import EngineRelationships::*;

    #CharteredBy dependency from processStepDeclaresItsCheckStory to d0321;

    part processStepDeclaresItsCheckStory : Story {
        :>> id = "b6b24806-c861-44cc-9894-eb3e529d60b2";
        :>> title = "Sprint 660: Close dcProcessStepDeclaresItsCheck (D0321 option A, the human's 'd0321 A' of 2026-09-05; schema clause D0434, proposed under D0337): a ProcessStep can say which guard or declared rule checks it. Before this sprint the fact had nowhere to live - D0321 measured 37 processes of which only agile-workflow's ceremony steps carried a per-step check, and seven processes had a guard that checks one of their steps with only prose joining them. After it: ProcessStep carries checkedBy : String [0..1], seven steps across six process files carry theirs through a committed D0067 transform, guard step-check-resolves holds every binding to a name that runs, and keel show hardening reports enforcement per STEP beside the per-process figures. The sprint also carries the finding its own guard made on its first live run: D0321's eighth binding named a lens as a guard (issue465). (5 pts)";
        :>> createdAt = "2026-09-10"; :>> createdBy = "claudeOpus5"; :>> kind = WorkKind::code; :>> priority = WorkPriority::p0; :>> owner = "claudeOpus5"; :>> estimatedPoints = 5;
    }

    action def DeliveryRunS660 {
        action storyProcessStepDeclaresItsCheck;
        verification storyProcessStepDeclaresItsCheckDoD : Test { :>> id = "8b8404e9-0bac-4cdb-b95b-ae01b0fd9e63"; :>> method = VerificationMethod::test; :>> procedureText = "The DoD of dcProcessStepDeclaresItsCheck as corrected this sprint: .engine/schema/core/process.sysml declares attribute checkedBy : String [0..1] on ProcessStep (kernel-checked via conformance_lane.py --construct on a bound and an unbound instance: ACCEPTED; validate_schema.py 20/20). .engine/tools/migrations/2026-09-10-step-checked-by.py is the transform - dry-run default, --apply, idempotent (a re-run reports bind=0 already-bound=7), control totals printed and enforced before writing (conservation 38 processes / 185 steps before and after; no-leak planned + already-bound == bindings; SHA-256 over every untouched line equal on the projected output), CRLF preserved per file. Seven bindings: cd4Register->control-defect-registry, dsGround->judgment-request-quality, lsStock->unit-extras-present, sd0Compute->viewpoint-renderer, stpa5Trigger->stpa-currency, giRoute->untrusted-routing, giBoundary->untrusted-taint. Guard step-check-resolves (GUARD_NAMES 70; control-map gStepCheckResolves -> ehz5; guards.md row) FAILS an empty value or a name that is neither a GUARD_NAMES entry nor a part <name> : EdgeRule|ElementRule under .engine/rules/, naming the step and the nearest real name; four unit tests: ghost name fails with the did-you-mean, guard name and declared rule both resolve, empty fails, the live tree's bindings resolve. hardening.rs stepEnforcement: per step checked / declaredJudgment (every process in the unit checkable = false) / undeclared, unresolved listed apart, perUnit rows; live 185 steps, 7 checked (3%), 63 declared judgment, 115 undeclared; test step_enforcement_counts_equal_a_hand_count holds the counts to a hand count over the process files and the classes to a partition. Migration's mig2DryRunReconcile is NOT bound: marker-census is a lens (issue465, resolver dcMigrationReconcileIsAGuard). Also resolves issue466: the corpus test whose witness was a process-global open counter asserts on the served body instead."; }
        // RAN: keel suite --touched . : pass - 546 passed, 0 failed in 244s; cargo clippy --release --all-targets -D warnings: Finished; keel validate . : 751 clean; keel guard --no-receipt . : ALL PASS, step-check-resolves PASS 7 scanned; keel version: guards 70
        part storyProcessStepDeclaresItsCheckDoDR1 : TestResult { :>> id = "a33b8669-6f79-43d3-9231-b3602af63d9a"; :>> outcome = VerdictKind::pass; :>> judgedAgainst = "16acaee17704090f938507281e165cfe922dea09"; :>> judgedAt = "2026-09-10T22:30:00Z"; :>> judgedBy = "claudeOpus5"; }
    }

    verification processStepDeclaresItsCheckRefineGate : Test { :>> id = "48db3ef3-28d1-406c-af65-5c31bf188e07"; :>> title = "Sprint 660 refine gate (DoR)"; :>> createdAt = "2026-09-10"; :>> createdBy = "claudeOpus5"; :>> method = VerificationMethod::inspect; :>> procedureText = "Five points, as the item was sized: a frozen-core attribute with its Decision and kernel check, a D0067 transform with three control totals, a new guard with tests and its three registration sites, a hardening lens with a hand-count test, and the doc-sync. Ready: dcProcessStepDeclaresItsCheck is head of whats-next after dcStpaDiagramInTheBinary closed at 16acaee; D0321's option A carries the human's word; the schema clause is its own Decision under D0303 and its own marker under D0337, so the sprint builds under a proposed Decision, which is the D0430 precedent for process-change locks. Known before the tree was read: the guard's positive case is a step naming a misspelt guard, its negative a step naming a real one; the lens's check is a hand count."; }
    // RAN: test
    part processStepDeclaresItsCheckRefineGateR1 : TestResult { :>> id = "29eb0ae4-466c-4cb2-a641-5f4dc8fa6535"; :>> outcome = VerdictKind::pass; :>> judgedAgainst = "16acaee17704090f938507281e165cfe922dea09"; :>> judgedAt = "2026-09-10T22:30:00Z"; :>> judgedBy = "claudeOpus5"; }
    // RAN: verifier receipt 2026-09-10: keel validate . 751 clean; DoR read from the sprint record
    part processStepDeclaresItsCheckRefineGateR2 : TestResult { :>> id = "f4f05aba-dc7f-463b-b719-d75dd58a6d73"; :>> outcome = VerdictKind::pass; :>> judgedAgainst = "16acaee17704090f938507281e165cfe922dea09"; :>> judgedAt = "2026-09-10T22:30:00Z"; :>> judgedBy = "claudeOpus5"; }
    verification processStepDeclaresItsCheckStandupGate : Test { :>> id = "a8b16f57-60f2-4d32-a96e-3d0f7c2391b4"; :>> title = "Sprint 660 standup gate"; :>> createdAt = "2026-09-10"; :>> createdBy = "claudeOpus5"; :>> method = VerificationMethod::inspect; :>> procedureText = "Blocker at the start: none. Sprint 659's commit 16acaee is on origin; its land ran the touched set (594 passed, 500 s) and CI's conclusion is read before this sprint's commit. The hazard known going in was the frozen core (section 1.5) - handled by the marker and the co-committed Decision, not by waiting. The hazard NOT known going in: that the research the item was built from had named a lens as a guard. The guard found it on its first run, before any claim was made about the bindings."; }
    // RAN: verifier receipt 2026-09-10: base 16acaee CI conclusion success (gh run list --json conclusion); git status staged 20 files
    part processStepDeclaresItsCheckStandupGateR1 : TestResult { :>> id = "0e74a196-fea8-4fb2-b4f7-b12eb2252ab1"; :>> outcome = VerdictKind::pass; :>> judgedAgainst = "16acaee17704090f938507281e165cfe922dea09"; :>> judgedAt = "2026-09-10T22:30:00Z"; :>> judgedBy = "claudeOpus5"; }
    verification processStepDeclaresItsCheckImplementGate : Test { :>> id = "7d7e4809-abcb-4c95-88ad-f4f4211f33a8"; :>> title = "Sprint 660 implement gate"; :>> createdAt = "2026-09-10"; :>> createdBy = "claudeOpus5"; :>> method = VerificationMethod::test; :>> procedureText = "Built in order. D0434 recorded from a draft file (marker process-change; proposed, outside standing consent as D0337 requires). The construct kernel-checked before the schema moved (D0139 clause E discipline). process.sysml gained the attribute with its comment. The transform written, dry-run reconciled (8 planned, hash equal), applied, re-run idempotent. Guard step_check_resolves appended to guards.rs with declared_check_names and step_check_bindings as public helpers so the lens reads the same vocabulary; GUARD_NAMES 69 -> 70, dispatch arm, guards.md row, control-map part and edge to ehz5. First live run: FAIL 8 scanned 1 violation - migration.sysml:42 marker-census names nothing that runs. Read commands.sysml:115: family lens. The binding removed from the transform and the tree, dry-run re-reconciled at 7, the unit tests (written with the same wrong name) corrected to marker-vocabulary, D0434's text and the DoD re-read to seven and to name the finding, issue465 recorded in-field with resolver dcMigrationReconcileIsAGuard whose DoD is a guard over a transform's reconciled receipt. hardening.rs stepEnforcement added and wired into the hardening lens. CLAUDE.md's hardening line and process-enforcement.toml's migration reason doc-synced. Staged with git add -A BEFORE the guard run (issue464's lesson): keel guard --no-receipt ALL PASS on the staged tree, sync-claude --check clean, validate 750, check-engine clean, keel version 70 guards (61 hard, 9 warning). The D0425 verifier's full run then found what the primary's filtered run had not: nine clippy errors (doc paragraphs, must_use, a redundant closure), the guard's FOURTH registration site missing (constraint def stepCheckResolves in guard-constraints.sysml - the every_guard_has_a_constraint_def_identity test is the control and it fired), and one flaky corpus test whose witness was a process-global counter (issue466, corrected to Arc::ptr_eq on the served body). All three fixed at the root before any result was recorded."; }
    // RAN: keel suite --touched . : pass - 546 passed, 0 failed in 244s (touched-receipt.toml, stems corpus,guards,hardening, lib=true); cargo clippy --release --all-targets -D warnings: Finished, no errors; keel guard --no-receipt . : ALL PASS, step-check-resolves PASS 7 scanned; keel version: guards 70 (61 hard, 9 warning)
    part processStepDeclaresItsCheckImplementGateR1 : TestResult { :>> id = "0e9d3737-f656-4365-90cc-cda79c314f01"; :>> outcome = VerdictKind::pass; :>> judgedAgainst = "16acaee17704090f938507281e165cfe922dea09"; :>> judgedAt = "2026-09-10T22:30:00Z"; :>> judgedBy = "claudeOpus5"; }
    verification processStepDeclaresItsCheckReviewGate : Test { :>> id = "70e62cf3-91c5-480a-bd22-4bb7b10fb585"; :>> title = "Sprint 660 review gate — three passes per D0172"; :>> createdAt = "2026-09-10"; :>> createdBy = "claudeOpus5"; :>> method = VerificationMethod::inspect; :>> procedureText = "Three passes (D0172). Substance: the binding is now a fact a control reads, and the control read it before anyone did - which is the whole argument for the attribute over a contract beside the process. The number the lens reports is honest and small: 7 of 185 steps checked. That is not a failure of the sprint; it is the first time the per-step figure has existed, and the per-process lens had been reporting the same processes as ENFORCED. Record: D0434 proposed with the marker, the DoD corrected by its owner before its pass (D0307 does not apply: the task was not done), issue465 in-field with a resolver whose DoD names it, the retro's finding a backlog item. Process: the guard was probed on a known-positive and a known-negative before the live tree (D0388) - and the live tree was the third case, the one the author had not foreseen. The lens was checked against a hand count, not against its own registry (the issue400 shape avoided by construction)."; }
    // RAN: verifier receipt 2026-09-10: keel check-engine . clean; keel sync-claude --check . matches (46 registry skills); guard issues PASS 469, resolver-kind PASS 492, doc-sync PASS 7, doc-guard-count PASS 4
    part processStepDeclaresItsCheckReviewGateR1 : TestResult { :>> id = "4492cc60-6834-44da-b19e-1c5d928dc4b3"; :>> outcome = VerdictKind::pass; :>> judgedAgainst = "16acaee17704090f938507281e165cfe922dea09"; :>> judgedAt = "2026-09-10T22:30:00Z"; :>> judgedBy = "claudeOpus5"; }
    verification processStepDeclaresItsCheckCloseOutGate : Test { :>> id = "3a7c2ba1-33b4-4ee2-b7dd-3de8cc343b64"; :>> title = "Sprint 660 closeOut gate (autonomous, D0049)"; :>> createdAt = "2026-09-10"; :>> createdBy = "claudeOpus5"; :>> method = VerificationMethod::inspect; :>> procedureText = "Delivered: checkedBy on ProcessStep (D0434, proposed), the constraint-def identity stepCheckResolves, issue466 (a flaky test's witness corrected), the transform 2026-09-10-step-checked-by.py with its reconciled dry run, seven bindings across six process files, guard step-check-resolves with four tests and its three registration sites, hardening's stepEnforcement lens with its hand-count test, issue465 recorded and triaged, dcMigrationReconcileIsAGuard authored with a DoD, doc-sync in CLAUDE.md and process-enforcement.toml, dcProcessStepDeclaresItsCheck's DoD passed on the verifier's receipt. Not delivered, by design: the agile-workflow ceremony steps are unbound until dcAdvanceRefusesAnyBoundStep gives advance the reader; migration's reconcile step is unbound until dcMigrationReconcileIsAGuard gives it a guard."; }
    // RAN: verifier receipt 2026-09-10: every step green - suite --touched 546/0, clippy all-targets clean, validate 751, check-engine clean, guard ALL PASS, sync-claude --check clean
    part processStepDeclaresItsCheckCloseOutGateR1 : TestResult { :>> id = "9d05ca44-b833-4c42-8d59-ae5b4d094a50"; :>> outcome = VerdictKind::pass; :>> judgedAgainst = "16acaee17704090f938507281e165cfe922dea09"; :>> judgedAt = "2026-09-10T22:30:00Z"; :>> judgedBy = "claudeOpus5"; }
    verification processStepDeclaresItsCheckRetroGate : Test { :>> id = "d08841bc-b1eb-488c-bf19-5d5fd606ee30"; :>> title = "Sprint 660 retro gate (autonomous, D0049)"; :>> createdAt = "2026-09-10"; :>> createdBy = "claudeOpus5"; :>> method = VerificationMethod::analyze; :>> procedureText = "Autonomous retro (D0049). AVOIDABLE-ISSUE SCAN: one Issue this sprint. issue465, a lens named as a guard through three records: avoidable - a name that claims to be a guard can be checked against GUARD_NAMES the moment it is written, and D0321's RESEARCH line, the DoD and D0434's draft were all written by an agent with the binary at hand. Not caught because no record type carries a guard NAME as a typed field; three prose fields named it and prose is not resolved. The control that caught it is the one this sprint built, and it caught it only after the binding became structure - which is the general lesson: a claim becomes checkable when it becomes an attribute, and the three prose sites before that were three places the same error could sit unnoticed for five days. FINDING 1 -> backlog: dcMigrationReconcileIsAGuard (the gap itself, recorded). FINDING 2, process: the transform's docstring and the unit tests carried the same wrong name as the research, because one author wrote all four from one list - D0388's probe discipline held for the guard (positive and negative cases chosen before the live tree) and the live tree was still the case that mattered; the receipt of that is in this record. FINDING 3, hygiene: two heredoc denials (D0309) on Python carrying backslash-n and a Rust snippet; both rewritten through the Write tool; no defect landed. FINDING 4, the D0425 split earned its keep on its first sprint: the primary ran clippy on the lib only, six named tests, and the guard set, and reported green; the verifier's suite --touched and clippy over all targets found two lib failures and nine clippy errors. One was a registration site the primary's checklist did not carry (the constraint-def identity; the test that checks it is the control and it worked), one was a latent flaky test the new tests made observable (issue466, in-field, corrected at the witness). Neither would have reached the tree under the split; both would have under the primary's own filtered report - the issue459 shape. Sprint size: five points, one sitting, with the guard's finding absorbed rather than deferred."; }
    // RAN: verifier receipt 2026-09-10: guard --no-receipt ALL PASS (issues PASS 469 scanned - issue465 and issue466 triaged with resolvers); retro text in the sprint record names each avoidable issue
    part processStepDeclaresItsCheckRetroGateR1 : TestResult { :>> id = "26473124-a849-4dbd-8fb8-b695276a90c5"; :>> outcome = VerdictKind::pass; :>> judgedAgainst = "16acaee17704090f938507281e165cfe922dea09"; :>> judgedAt = "2026-09-10T22:30:00Z"; :>> judgedBy = "claudeOpus5"; }
}
