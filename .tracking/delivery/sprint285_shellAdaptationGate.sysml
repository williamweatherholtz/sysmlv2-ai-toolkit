// ProjectDeliveryS285 — Sprint 285: the shell-adaptation advisory becomes an in-loop control
// (dcShellAdaptationGate, issue094). EXECUTE. 5 pts.
package ProjectDeliveryS285 {
    private import EngineElement::*;
    private import EngineWork::*;
    private import EngineVerification::*;
    private import EngineRelationships::*;

    #CharteredBy dependency from shellGateStory to d0144;

    part shellGateStory : Story {
        :>> id = "0d80017c-0814-617c-9b3e-00000030017c";
        :>> title = "Sprint 285: keel hook pre-bash — the #1 friction class becomes a control, not a reminder (5 pts)";
        :>> createdAt = "2026-08-15"; :>> createdBy = "claudeOpus5"; :>> kind = WorkKind::code; :>> priority = WorkPriority::p0; :>> owner = "claudeOpus5"; :>> estimatedPoints = 5;
    }

    action def DeliveryRunS285 {
        action storyShellGate;
        verification storyShellGateDoD : Test { :>> id = "0d80017d-0814-617d-9b3e-00000030017d"; :>> method = VerificationMethod::demo; :>> procedureText = "Delivers dcShellAdaptationGate; resolves issue094. CLAUDE.md §6 names host/shell adaptation the #1 avoidable-friction class and it kept recurring anyway — three times in the sitting that opened issue094, then twice more in sprints 281 and 283, each retro naming this item as the unbuilt resolver. Sprint 263's retro had concluded the class was NOT automatable because it 'lives in throwaway shell commands, not committed artifacts'; that reasoning assumed a control must inspect ARTIFACTS, while D0134's in-loop gates inspect TOOL CALLS — and a shell command is a tool call. The premise was wrong, not the conclusion unreachable. DELIVERED: `keel hook pre-bash`, wired as a `PreToolUse` hook on Bash, detecting (a) an MSYS-style `/c/...`, `/tmp/...` or `/mnt/...` path handed to a Windows-native program, and (b) PowerShell-only syntax in a bash command — the leading `&` call operator, `$env:`, a cmdlet. ADVISORY, never blocking, and that is a design commitment rather than caution: these checks cannot be exact, and a heuristic that blocks shell commands is the issue076/issue081 dynamic where an over-strict gate trains its actor to disable it, which this project already paid for with eight bypassed commits. VERIFIED END TO END against the live binary: all three real failing commands are detected and each names its concrete remedy (`cygpath -w`, or switch to the PowerShell tool); every one of nine ordinary commands is silent — including `git -C /c/Users/... status`, since git-for-Windows IS MSYS-aware and flagging it would be a false positive on the most common command in this repo, and `./server > log 2>&1 &`, where `&` is backgrounding rather than a call operator; a Windows path passed to a Windows program is not flagged; a malformed payload and an unknown command both exit 0. `hook-config-integrity` passes on the new config. clippy clean; 176 tests."; }
        part storyShellGateDoDR1 : TestResult { :>> id = "0d80017e-0814-617e-9b3e-00000030017e"; :>> outcome = VerdictKind::pass; :>> judgedAgainst = "9e14881"; :>> judgedAt = "2026-08-15"; :>> judgedBy = "claudeOpus5"; }
    }

    verification sgRefineGate : Test { :>> id = "0d80017f-0814-617f-9b3e-00000030017f"; :>> title = "Sprint 285 refine gate (DoR)"; :>> createdAt = "2026-08-15"; :>> createdBy = "claudeOpus5"; :>> method = VerificationMethod::inspect; :>> procedureText = "DoR. CONSUMER CHECK (dorConsumer, D0144): the consumer is the Claude Code `PreToolUse` hook contract, so the payload shape had to be confirmed before writing the detector — `/tool_input/command`, matching how `post-edit` already reads `/tool_input/file_path`. The second consumer is the `hook-config-integrity` guard, which reads `.claude/settings.json`, so the wiring had to satisfy it rather than merely work. estimatedPoints=5. DoR met."; }
    part sgRefineGateR1 : TestResult { :>> id = "0d800180-0814-6180-9b3e-000000300180"; :>> outcome = VerdictKind::pass; :>> judgedAgainst = "9e14881"; :>> judgedAt = "2026-08-15"; :>> judgedBy = "claudeOpus5"; }

    verification sgStandupGate : Test { :>> id = "0d800181-0814-6181-9b3e-000000300181"; :>> title = "Sprint 285 standup gate"; :>> createdAt = "2026-08-15"; :>> createdBy = "claudeOpus5"; :>> method = VerificationMethod::inspect; :>> procedureText = "Approach: write the false-positive test list FIRST, from real commands in this repo's own history, and treat silence on them as the harder requirement than detection. A detector that fires on `git -C /c/...` or on a trailing `&` would be run a dozen times an hour against correct commands, and the reader would stop reading it inside a day — at which point it looks like coverage while providing none. No blockers."; }
    part sgStandupGateR1 : TestResult { :>> id = "0d800182-0814-6182-9b3e-000000300182"; :>> outcome = VerdictKind::pass; :>> judgedAgainst = "9e14881"; :>> judgedAt = "2026-08-15"; :>> judgedBy = "claudeOpus5"; }

    verification sgImplementGate : Test { :>> id = "0d800183-0814-6183-9b3e-000000300183"; :>> title = "Sprint 285 implement gate"; :>> createdAt = "2026-08-15"; :>> createdBy = "claudeOpus5"; :>> method = VerificationMethod::test; :>> procedureText = "Two decisions carry the design. FIRST, `git` is deliberately ABSENT from the Windows-native program list: git-for-Windows accepts `/c/...` happily, so including it would false-positive on the single most common command here. The list is programs that genuinely cannot open an MSYS path, not programs that happen to be .exe files. SECOND, the `&` detection is narrow by construction — in bash `&` is backgrounding, `&&` is an operator and `2>&1` is a redirect, all correct and frequent — so it matches only `&` in COMMAND POSITION followed by a quote or a drive letter, which is the PowerShell call-operator shape and nothing else. Both are encoded as tests over real commands rather than asserted in comments."; }
    part sgImplementGateR1 : TestResult { :>> id = "0d800184-0814-6184-9b3e-000000300184"; :>> outcome = VerdictKind::pass; :>> judgedAgainst = "9e14881"; :>> judgedAt = "2026-08-15"; :>> judgedBy = "claudeOpus5"; }

    verification sgReviewGate : Test { :>> id = "0d800185-0814-6185-9b3e-000000300185"; :>> title = "Sprint 285 review gate"; :>> createdAt = "2026-08-15"; :>> createdBy = "claudeOpus5"; :>> method = VerificationMethod::inspect; :>> procedureText = "Reviewed. HONEST LIMITATION, stated because it bounds what this control can claim: it catches the two shapes that actually recurred here, and it is a string heuristic, not a shell parser. It will not catch a novel host-adaptation error, and the three occurrences in sprints 281/283 that it does NOT address were backslash escaping through a python heredoc — a different mechanism entirely, still untracked by any control, and the reason this sprint's own retro records a fourth instance of it. Detecting the recurring shapes is worth doing; claiming the class is now closed would not be true."; }
    part sgReviewGateR1 : TestResult { :>> id = "0d800186-0814-6186-9b3e-000000300186"; :>> outcome = VerdictKind::pass; :>> judgedAgainst = "9e14881"; :>> judgedAt = "2026-08-15"; :>> judgedBy = "claudeOpus5"; }

    verification sgCloseOutGate : Test { :>> id = "0d800187-0814-6187-9b3e-000000300187"; :>> title = "Sprint 285 closeOut gate (autonomous, D0049)"; :>> createdAt = "2026-08-15"; :>> createdBy = "claudeOpus5"; :>> method = VerificationMethod::inspect; :>> procedureText = "Autonomous closeOut (D0049). dcShellAdaptationGate carries a passing DoD TestResult; issue094 resolves for the two shapes it covers, with the residual stated in the review gate rather than glossed. Doc-sync rides this commit: CLAUDE.md §5 names the new hook and its advisory status. clippy clean; 176 tests; validate clean; check-engine clean; 29 guards green including hook-config-integrity on the new PreToolUse entry. No gate bypassed."; }
    part sgCloseOutGateR1 : TestResult { :>> id = "0d800188-0814-6188-9b3e-000000300188"; :>> outcome = VerdictKind::pass; :>> judgedAgainst = "9e14881"; :>> judgedAt = "2026-08-15"; :>> judgedBy = "claudeOpus5"; }

    verification sgRetroGate : Test { :>> id = "0d800189-0814-6189-9b3e-000000300189"; :>> title = "Sprint 285 retro gate (autonomous, D0049)"; :>> createdAt = "2026-08-15"; :>> createdBy = "claudeOpus5"; :>> method = VerificationMethod::analyze; :>> procedureText = "Autonomous retro (D0049) under D0131's retroTrack. WELL: (1) a prior retro's REASONING was overturned rather than its conclusion inherited — sprint 263 said the class was not automatable because controls inspect artifacts, and that premise was simply false once D0134 made tool calls inspectable, which is worth noting because a recorded 'not automatable' is otherwise permanent; (2) the false-positive list was written before the detector and treated as the harder requirement, so silence on nine real commands is tested rather than hoped for; (3) the limitation is stated — this catches two shapes, not the class, and saying so keeps the issue honest instead of closing it on a partial. AVOIDABLE-ISSUE 1: a python heredoc mangled backslash escapes in a Rust patch for the FOURTH time this pass, costing a round trip, and I had used the Edit tool correctly for exactly this reason twice already in the same sprint. NO NEW ITEM, reason stated: it is the same class issue094 tracks and the control just built does not address it — a heredoc escaping bug is not a shell-adaptation error, it is a tool-choice error, and the honest remedy is mechanical (use Edit for source patches, never a heredoc) rather than another detector. Recorded here and in this sprint's review gate so the residual is visible on the item that claims to resolve the class. Estimate 5 pts, delivered."; }
    part sgRetroGateR1 : TestResult { :>> id = "0d80018a-0814-618a-9b3e-00000030018a"; :>> outcome = VerdictKind::pass; :>> judgedAgainst = "9e14881"; :>> judgedAt = "2026-08-15"; :>> judgedBy = "claudeOpus5"; }
}
