// ProjectDeliveryS152 — Sprint 152: serveSettings (D0094, resolves issue049) — a PERSISTENT settings
// toggle to enable/disable the `claude -p` agent bridge (billing control). Addresses the human's
// concern that headless `claude -p` may bill as API (D0094 caveat): default ON ("fine for now"), but
// the user can turn it OFF -> the console spawns no `claude -p` (read/oversight only). EXECUTE. 3 pts. AUTONOMOUS (D0049).
package ProjectDeliveryS152 {
    private import EngineElement::*;
    private import EngineWork::*;
    private import EngineVerification::*;
    private import EngineRelationships::*;

    #CharteredBy dependency from serveSettingsStory to d0094;

    part serveSettingsStory : Story {
        :>> id = "63940516-2c7d-4e8f-c152-51627384c001";
        :>> title = "Sprint 152: serveSettings (3 pts) — persistent agent-bridge toggle (claude -p billing control) (D0094/issue049)";
        :>> createdAt = "2026-06-24"; :>> createdBy = "wweatherholtz"; :>> kind = WorkKind::code; :>> priority = WorkPriority::p2; :>> owner = "claudeOpus"; :>> estimatedPoints = 3;
    }

    action def DeliveryRunS152 {
        action storyServeSettings;
        verification storyServeSettingsDoD : Test { :>> id = "63940516-2c7d-4e8f-c152-51627384c002"; :>> method = VerificationMethod::test; :>> procedureText = "issue049: the agent bridge spawns `claude -p` (headless), whose billing is in flux (D0094 — may bill as API not subscription); the human wants to be able to avoid that. FIX (human directive: 'make a settings toggle ... make settings persist'): a PERSISTENT serve-settings file `.keel-serve.json` (gitignored, project-local, default agentBridge=ON 'fine for now'); GET/POST /api/settings to read/write it; /api/agent/stream now refuses when the bridge is OFF with a clear message (no `claude -p` spawned) BEFORE the action/cap/PATH checks; console Settings tab with a checkbox (+ the billing caveat), and the Critique button is hidden when OFF (fetched on load). VERIFIED (live): GET /api/settings -> {agentBridge:true}; POST {agentBridge:false} -> persisted {ok:true,agentBridge:false}; critique stream when OFF -> 'the AI agent bridge is OFF in settings ...' (NO claude spawned); Settings tab present; clippy -D warnings + cargo build + keel validate + guard all (12) green. (Also added the write::append_resolves_edge helper used next by sr16.) When OFF, AI critique runs in the user's own subscription-billed Claude Code session."; }
        part storyServeSettingsDoDR1 : TestResult { :>> id = "63940516-2c7d-4e8f-c152-51627384c003"; :>> outcome = VerdictKind::pass; :>> judgedAgainst = "7f9e635"; :>> judgedAt = "2026-06-24"; :>> judgedBy = "claudeOpus"; }
    }

    verification serveSettingsRefineGate : Test { :>> id = "63940516-2c7d-4e8f-c152-51627384c004"; :>> title = "Sprint 152 refine gate (DoR)"; :>> createdAt = "2026-06-24"; :>> createdBy = "claudeOpus"; :>> method = VerificationMethod::inspect; :>> procedureText = "DoR: human flagged claude -p billing (issue049) mid serve-redesign + directed 'make a settings toggle, persist'. Scope: a persistent agent-bridge on/off. estimatedPoints=3. #CharteredBy d0094. DoR met."; }
    part serveSettingsRefineGateR1 : TestResult { :>> id = "63940516-2c7d-4e8f-c152-51627384c005"; :>> outcome = VerdictKind::pass; :>> judgedAgainst = "7f9e635"; :>> judgedAt = "2026-06-24"; :>> judgedBy = "claudeOpus"; }
    verification serveSettingsStandupGate : Test { :>> id = "63940516-2c7d-4e8f-c152-51627384c006"; :>> title = "Sprint 152 standup gate"; :>> createdAt = "2026-06-24"; :>> createdBy = "claudeOpus"; :>> method = VerificationMethod::inspect; :>> procedureText = "Approach: .keel-serve.json (gitignored) + agent_bridge_enabled() default-true + GET/POST /api/settings + gate /api/agent/stream when OFF + console Settings tab + hide Critique when OFF + load-time fetch. No blockers."; }
    part serveSettingsStandupGateR1 : TestResult { :>> id = "63940516-2c7d-4e8f-c152-51627384c007"; :>> outcome = VerdictKind::pass; :>> judgedAgainst = "7f9e635"; :>> judgedAt = "2026-06-24"; :>> judgedBy = "claudeOpus"; }
    verification serveSettingsImplementGate : Test { :>> id = "63940516-2c7d-4e8f-c152-51627384c008"; :>> title = "Sprint 152 implement gate"; :>> createdAt = "2026-06-24"; :>> createdBy = "claudeOpus"; :>> method = VerificationMethod::test; :>> procedureText = "Added settings_path/agent_bridge_enabled + /api/settings GET/POST + the OFF gate + Settings tab + Critique-hidden-when-OFF + .gitignore entry. VERIFIED live (toggle persists; OFF blocks the bridge with no claude; Settings tab present); clippy + build + validate + guard 12 green."; }
    part serveSettingsImplementGateR1 : TestResult { :>> id = "63940516-2c7d-4e8f-c152-51627384c009"; :>> outcome = VerdictKind::pass; :>> judgedAgainst = "7f9e635"; :>> judgedAt = "2026-06-24"; :>> judgedBy = "claudeOpus"; }
    verification serveSettingsReviewGate : Test { :>> id = "63940516-2c7d-4e8f-c152-51627384c00a"; :>> title = "Sprint 152 review gate"; :>> createdAt = "2026-06-24"; :>> createdBy = "claudeOpus"; :>> method = VerificationMethod::inspect; :>> procedureText = "Diff reviewed. The toggle gives the user control over the one real billing-risk surface (claude -p) without losing the capability — default ON now, off later if Anthropic's billing settles unfavorably. Gitignored + project-local (per-clone preference, no git noise). The OFF path is checked first + spawns nothing; the console hides Critique + explains the caveat. Honest, proportionate, directly answers the human's concern. Clean."; }
    part serveSettingsReviewGateR1 : TestResult { :>> id = "63940516-2c7d-4e8f-c152-51627384c00b"; :>> outcome = VerdictKind::pass; :>> judgedAgainst = "7f9e635"; :>> judgedAt = "2026-06-24"; :>> judgedBy = "claudeOpus"; }
    verification serveSettingsCloseOutGate : Test { :>> id = "63940516-2c7d-4e8f-c152-51627384c00c"; :>> title = "Sprint 152 closeOut gate (autonomous, D0049)"; :>> createdAt = "2026-06-24"; :>> createdBy = "claudeOpus"; :>> method = VerificationMethod::inspect; :>> procedureText = "Autonomous closeOut (D0049): DoD pass; persistent agent-bridge toggle live; billing risk now user-controllable. clippy + build + keel validate + guard all (12) green. Self-evidencing (D0051). issue049 resolved. Resumes the serve redesign (sr16 next, on the now-toggle-able bridge)."; }
    part serveSettingsCloseOutGateR1 : TestResult { :>> id = "63940516-2c7d-4e8f-c152-51627384c00d"; :>> outcome = VerdictKind::pass; :>> judgedAgainst = "7f9e635"; :>> judgedAt = "2026-06-24"; :>> judgedBy = "claudeOpus"; }
    verification serveSettingsRetroGate : Test { :>> id = "63940516-2c7d-4e8f-c152-51627384c00e"; :>> title = "Sprint 152 retro gate (autonomous, D0049)"; :>> createdAt = "2026-06-24"; :>> createdBy = "claudeOpus"; :>> method = VerificationMethod::analyze; :>> procedureText = "Autonomous retro (D0049). WELL: a live user concern (claude -p billing) was converted into a tracked Issue + a clean persistent toggle, mid-redesign, without derailing. Default-ON keeps current value; OFF is a one-click escape that spawns zero `claude -p`. AVOIDABLE-ISSUE SCAN: the billing risk was a KNOWN D0094 caveat that hadn't been surfaced as a user control — now it is (issue049 + the toggle). LESSON: a known external-dependency caveat (billing) deserves a user-facing control, not just a doc note. NON-blocking: settings is now extensible (more keys later). Resume sr16 (critique loop) -> sr18 -> sr19 on the toggle-able bridge. Estimate 3 pts held."; }
    part serveSettingsRetroGateR1 : TestResult { :>> id = "63940516-2c7d-4e8f-c152-51627384c00f"; :>> outcome = VerdictKind::pass; :>> judgedAgainst = "7f9e635"; :>> judgedAt = "2026-06-24"; :>> judgedBy = "claudeOpus"; }
}
