// ProjectDeliveryS591 — Sprint 591: the measures become a declared, analysed set instead of a class of thing no analysis could see. EXECUTE. 1 pts.
package ProjectDeliveryS591 {
    private import EngineElement::*;
    private import EngineWork::*;
    private import EngineVerification::*;
    private import EngineRelationships::*;

    #CharteredBy dependency from instrumentsAreDeclaredAndAnalysedStory to d0361;

    part instrumentsAreDeclaredAndAnalysedStory : Story {
        :>> id = "7be5ddfc-f894-43c6-94d0-80c7a8d3de08";
        :>> title = "Sprint 591: the measures become a declared, analysed set instead of a class of thing no analysis could see (1 pts)";
        :>> createdAt = "2026-09-07"; :>> createdBy = "claudeOpus5"; :>> kind = WorkKind::code; :>> priority = WorkPriority::p0; :>> owner = "claudeOpus5"; :>> estimatedPoints = 1;
    }

    action def DeliveryRunS591 {
        action storyInstrumentsAreDeclaredAndAnalysed;
        verification storyInstrumentsAreDeclaredAndAnalysedDoD : Test { :>> id = "d233b9c5-653c-49ce-bddf-fd7f00548ad1"; :>> method = VerificationMethod::test; :>> procedureText = "DELIVERED: the instrument inventory (20 declared in .engine/contracts/instruments.toml, each with what it measures, whose belief it maintains, its output form, its determinism and its known failure modes), STPA step 4 over the feedback half of this project's own control structure (hazard EHZ10 plus nine loss scenarios as causal chains, eight evidenced by incidents and one named before it happens), and guard 65 instruments-declared holding the declaration against the tree in both directions. Chartered by D0361, with D0360 supplying the rule that a new control ships with its demonstrated catch. VERIFIED: keel suite 569 passed 0 failed (receipt bc74b6ded639); instruments_declared_catches_it 4/4 including the undeclared case, the stale-declaration case and the no-manifest case; keel validate 671 clean; keel guard ALL PASS at 65 guards; clippy -D warnings clean; the proof census moved 16 to 18 proven because guard 65 arrived with its test rather than after it."; }
        // RAN: keel suite . = 569 passed 0 failed (receipt bc74b6ded639); instruments_declared_catches_it 4/4; keel validate 671; keel guard ALL PASS (65); clippy clean
        part storyInstrumentsAreDeclaredAndAnalysedDoDR1 : TestResult { :>> id = "043e0750-0eac-4f2c-9892-340ef9b3ea1b"; :>> outcome = VerdictKind::pass; :>> judgedAgainst = "HEAD"; :>> judgedAt = "2026-09-06"; :>> judgedBy = "claudeOpus5"; }
    }

    verification instrumentsAreDeclaredAndAnalysedRefineGate : Test { :>> id = "ba843247-2244-4c40-bf5f-9a2c2882c6fc"; :>> title = "Sprint 591 refine gate (DoR)"; :>> createdAt = "2026-09-07"; :>> createdBy = "claudeOpus5"; :>> method = VerificationMethod::inspect; :>> procedureText = "READY: the owner asked for the list, an STPA over it, and the tightening. The STPA was RESUMED rather than started - four losses, nine hazards, seven controllers and eighteen UCAs already stood - and the finding that shaped the work was that the model held ZERO Feedback items, because feedback is computed from CliCommand facts and every instrument outside the CLI is therefore invisible to it."; }
    // RAN: keel suite 569/0 (bc74b6ded639)
    part instrumentsAreDeclaredAndAnalysedRefineGateR1 : TestResult { :>> id = "bf1bf4b0-5720-4c32-a339-220939aacb83"; :>> outcome = VerdictKind::pass; :>> judgedAgainst = "HEAD"; :>> judgedAt = "2026-09-06"; :>> judgedBy = "claudeOpus5"; }
    verification instrumentsAreDeclaredAndAnalysedStandupGate : Test { :>> id = "6c861b98-8d06-43e0-bcf3-98ed2a4db3ff"; :>> title = "Sprint 591 standup gate"; :>> createdAt = "2026-09-07"; :>> createdBy = "claudeOpus5"; :>> method = VerificationMethod::inspect; :>> procedureText = "MY OWN INVENTORY WAS SHORT BY A THIRD. I hand-wrote twelve instruments; guard 65's first run named eight more - the whole JVM kernel lane - and two of those BLOCK, so they are controls as well as instruments. The list I would have published as complete was not."; }
    // RAN: keel suite 569/0 (bc74b6ded639)
    part instrumentsAreDeclaredAndAnalysedStandupGateR1 : TestResult { :>> id = "174a4b11-20a3-40ab-b49e-af217007c080"; :>> outcome = VerdictKind::pass; :>> judgedAgainst = "HEAD"; :>> judgedAt = "2026-09-06"; :>> judgedBy = "claudeOpus5"; }
    verification instrumentsAreDeclaredAndAnalysedImplementGate : Test { :>> id = "c1cf3e0a-2494-4146-ac60-09ca25562ff1"; :>> title = "Sprint 591 implement gate"; :>> createdAt = "2026-09-07"; :>> createdBy = "claudeOpus5"; :>> method = VerificationMethod::test; :>> procedureText = "RAN: keel show control-structure tested for each out-of-band instrument, none present; the manifest authored and then corrected by the guard; guard 65 written with its proof test in the same commit; the test caught the guard accusing a fresh scaffold of the three tools the engine ships, fixed by reading the shipped set from its one home; keel suite twice - the first run went red 551/18 on tool-reference, because the migrated manifest gave every adopter seventeen dead references, fixed by making it engine-dev-only; the census before and after."; }
    // RAN: keel suite 569/0 (bc74b6ded639)
    part instrumentsAreDeclaredAndAnalysedImplementGateR1 : TestResult { :>> id = "4d537b29-fe04-4fcc-a3d1-224c796764a0"; :>> outcome = VerdictKind::pass; :>> judgedAgainst = "HEAD"; :>> judgedAt = "2026-09-06"; :>> judgedBy = "claudeOpus5"; }
    verification instrumentsAreDeclaredAndAnalysedReviewGate : Test { :>> id = "f88bcfad-e75b-4b18-9328-ddb7c36d5cbc"; :>> title = "Sprint 591 review gate — three passes per D0172"; :>> createdAt = "2026-09-07"; :>> createdBy = "claudeOpus5"; :>> method = VerificationMethod::inspect; :>> procedureText = "THREE PASSES. (1) DID THE ANALYSIS FIND SOMETHING THE INCIDENTS HAD NOT: yes - S-F9, the one scenario with no incident behind it, is that instruments read the working tree while reports cite a SHA, and the citation is authored by the same process that read the dirty tree, so the two can never contradict each other. (2) WERE MY OWN NUMBERS COMPUTED: the header of the manifest originally asserted a count that the guard then made wrong within the hour; it now states what was measured without a number that ages. (3) DID THE CONTROLS CATCH ME: three times - guard 65 on my incomplete inventory, its own test on the false accusation, tool-reference on the portability defect. None of those was found by reading."; }
    // RAN: keel suite 569/0 (bc74b6ded639)
    part instrumentsAreDeclaredAndAnalysedReviewGateR1 : TestResult { :>> id = "0041265a-dbf9-4f7b-93a9-24b67276822d"; :>> outcome = VerdictKind::pass; :>> judgedAgainst = "HEAD"; :>> judgedAt = "2026-09-06"; :>> judgedBy = "claudeOpus5"; }
    verification instrumentsAreDeclaredAndAnalysedCloseOutGate : Test { :>> id = "3a3f2143-583e-4be9-874f-07733b9c57fb"; :>> title = "Sprint 591 closeOut gate (autonomous, D0049)"; :>> createdAt = "2026-09-07"; :>> createdBy = "claudeOpus5"; :>> method = VerificationMethod::inspect; :>> procedureText = "CLOSED. The measures are a declared set, the feedback half of the control structure has an analysis, and the first control to arrive under D0360 came with the evidence that it works."; }
    // RAN: keel suite 569/0 (bc74b6ded639)
    part instrumentsAreDeclaredAndAnalysedCloseOutGateR1 : TestResult { :>> id = "6b5efa41-c73f-4a25-af65-879c6dac4f7a"; :>> outcome = VerdictKind::pass; :>> judgedAgainst = "HEAD"; :>> judgedAt = "2026-09-06"; :>> judgedBy = "claudeOpus5"; }
    verification instrumentsAreDeclaredAndAnalysedRetroGate : Test { :>> id = "562f87a0-04c5-4187-9e9a-e6ac67a69290"; :>> title = "Sprint 591 retro gate (autonomous, D0049)"; :>> createdAt = "2026-09-07"; :>> createdBy = "claudeOpus5"; :>> method = VerificationMethod::analyze; :>> procedureText = "AVOIDABLE-ISSUE SCAN HELD. Already tracked, no new item: issue393 was raised during this work (the stpa skill's own SOP is not deployed, so following its first instruction hits a missing path), and the instrument defects are issue384/386/389/390/391/392. The avoidable one here is mine and it is the same shape as the thing being fixed: I authored a twelve-item inventory as though a hand-written list of measures could be complete, and the mechanical check found a third more within minutes. The lesson is not 'check the list' - it is that an inventory of anything is a measure, and a measure written by hand and never held against the tree is the defect class this sprint exists to close."; }
    // RAN: keel suite 569/0 (bc74b6ded639)
    part instrumentsAreDeclaredAndAnalysedRetroGateR1 : TestResult { :>> id = "82b65cd8-c187-4f2f-a49e-d57f7812be9b"; :>> outcome = VerdictKind::pass; :>> judgedAgainst = "HEAD"; :>> judgedAt = "2026-09-06"; :>> judgedBy = "claudeOpus5"; }
}
