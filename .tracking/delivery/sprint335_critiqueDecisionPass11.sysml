// ProjectDeliveryS335 — Sprint 335: critique pass 11. Measured a corpus-wide pattern: no warning-level
// control has ever been promoted to hard. EXECUTE. 3 pts.
package ProjectDeliveryS335 {
    private import EngineElement::*;
    private import EngineWork::*;
    private import EngineVerification::*;
    private import EngineRelationships::*;

    #CharteredBy dependency from critPass11Story to d0080;

    part critPass11Story : Story {
        :>> id = "0d8004a0-0814-64a0-9b3e-0000003004a0";
        :>> title = "Sprint 335: critique pass 11 — 5 Decisions x Core-3, 7 fail / 8 pass (3 pts)";
        :>> createdAt = "2026-08-17"; :>> createdBy = "claudeOpus5"; :>> kind = WorkKind::modeling; :>> priority = WorkPriority::p0; :>> owner = "claudeOpus5"; :>> estimatedPoints = 3;
    }

    action def DeliveryRunS335 {
        action storyCritPass11;
        verification storyCritPass11DoD : Test { :>> id = "0d8004a1-0814-64a1-9b3e-0000003004a1"; :>> method = VerificationMethod::analyze; :>> procedureText = "Pass 11: d0110, d0111, d0112, d0113, d0116. 7 fail, 8 pass — the first pass where passes outnumber fails, and the reason is checkable: these five are small, mechanism-reusing Decisions that were carried out, rather than large direction Decisions with unbuilt clauses. THE CORPUS-WIDE FINDING: 'promote to a hard guard once proven low-noise' has no criterion, owner or trigger in ANY Decision that uses it — and MEASURED, no Decision in .engine/decisions records a warning-to-hard promotion ever happening, while 9 of 35 guards remain warning-only. At least three Decisions use the construction (the D0102 precedent, D0111, D0113), so warning-first is indistinguishable from warning-forever, and a control that will never gate is a reminder — which D0047 says is not a control. SECOND: d0112's decision text opens 'PROPOSED direction ... not yet accepted' while its status field reads accepted. That is the second stale-status contradiction in two passes (d0109's title) and the third instance of the class this session (issue140's six gate comments), and the guard written for issue140 cannot catch either, because it keys on comments adjacent to acceptance RESULTS rather than on an element's own text contradicting its own status field. READ BACK: Decision coverage 29 -> 34 of 75."; }
        part storyCritPass11DoDR1 : TestResult { :>> id = "0d8004a2-0814-64a2-9b3e-0000003004a2"; :>> outcome = VerdictKind::pass; :>> judgedAgainst = "db044d4"; :>> judgedAt = "2026-08-17"; :>> judgedBy = "claudeOpus5"; }
    }

    verification c11RefineGate : Test { :>> id = "0d8004a3-0814-64a3-9b3e-0000003004a3"; :>> title = "Sprint 335 refine gate (DoR)"; :>> createdAt = "2026-08-17"; :>> createdBy = "claudeOpus5"; :>> method = VerificationMethod::inspect; :>> procedureText = "DoR. Five Decisions. Four things measured against the tree before judgment: that decision-authoring's process file AND its registered skill both exist (so D0110's non-inert claim holds), that researchSpikeCharterRule is one of the eight declared rules, that d0112's status is accepted, and whether ANY Decision records a warning-to-hard promotion (none does). The last of those turned a suspicion I had carried since pass 10 into a measurement. estimatedPoints=3."; }
    part c11RefineGateR1 : TestResult { :>> id = "0d8004a4-0814-64a4-9b3e-0000003004a4"; :>> outcome = VerdictKind::pass; :>> judgedAgainst = "db044d4"; :>> judgedAt = "2026-08-17"; :>> judgedBy = "claudeOpus5"; }

    verification c11StandupGate : Test { :>> id = "0d8004a5-0814-64a5-9b3e-0000003004a5"; :>> title = "Sprint 335 standup gate"; :>> createdAt = "2026-08-17"; :>> createdBy = "claudeOpus5"; :>> method = VerificationMethod::inspect; :>> procedureText = "Approach: when a phrase recurs across Decisions (promote once proven, widen once proven), stop treating it as boilerplate and MEASURE whether it has ever fired. That is what produced this pass's only cross-corpus finding, and it is cheap — one grep over the decisions directory plus the guard split from `keel version`. No blockers."; }
    part c11StandupGateR1 : TestResult { :>> id = "0d8004a6-0814-64a6-9b3e-0000003004a6"; :>> outcome = VerdictKind::pass; :>> judgedAgainst = "db044d4"; :>> judgedAt = "2026-08-17"; :>> judgedBy = "claudeOpus5"; }

    verification c11ImplementGate : Test { :>> id = "0d8004a7-0814-64a7-9b3e-0000003004a7"; :>> title = "Sprint 335 implement gate"; :>> createdAt = "2026-08-17"; :>> createdBy = "claudeOpus5"; :>> method = VerificationMethod::analyze; :>> procedureText = "D0113 PREDICTED THE BLIND SPOT THIS SESSION FELL INTO, which is worth recording as a credit rather than a fault. Its correctness lens passes because the Decision states its own ceiling in advance: 'a mechanical check cannot know a doc CLAIM is stale, only that a definitional change shipped with no doc touch'. Sprint 328 then found six comments asserting gates were PENDING beside their own passing acceptance results — stale doc CLAIMS inside model files — and doc-sync could not have caught one of them, because each shipped in a commit touching no definitional artifact. A Decision that names the class of defect its control cannot see is more useful than one that overstates coverage, and this is the clearest example in the corpus. THE COUNTERWEIGHT is in the same Decision's completeness lens: excluding tool .rs code means the largest source of doc-invalidating change sits outside the check, and this session proves it — every guard I added required a hand doc-sync of guards.md and CLAUDE.md's count, in commits doc-sync was structurally unable to examine."; }
    part c11ImplementGateR1 : TestResult { :>> id = "0d8004a8-0814-64a8-9b3e-0000003004a8"; :>> outcome = VerdictKind::pass; :>> judgedAgainst = "db044d4"; :>> judgedAt = "2026-08-17"; :>> judgedBy = "claudeOpus5"; }

    verification c11ReviewGate : Test { :>> id = "0d8004a9-0814-64a9-9b3e-0000003004a9"; :>> title = "Sprint 335 review gate"; :>> createdAt = "2026-08-17"; :>> createdBy = "claudeOpus5"; :>> method = VerificationMethod::inspect; :>> procedureText = "Reviewed, and the pass-heavy result needs an explanation rather than an apology. EIGHT PASSES of fifteen, against 11 fails in pass 10, and the difference is the KIND of Decision: pass 10 held large direction Decisions (a controls architecture, a discipline doctrine, an agent-discipline direction) whose ambition outran what got built, while pass 11 holds small mechanism-reusing ones — adopt a process that exists, declare one rule, add one warning guard, retire a state nobody wanted. Every one of those was carried out, and three of the five (D0110, D0111, D0113) passed BOTH correctness and feasibility. THE GENERALISATION IS THE FINDING: across two Decision passes, the Decisions that needed NO new mechanism were all carried out and the ones proposing new machinery were partly not — D0108 and D0113 explicitly argued mechanism-reuse as their feasibility case and both shipped, while D0105's rule kinds and D0106's parallel execution did not. D0111's honesty about a mid-implementation widening ('corrected to match D0068, not a scope change') is the single best implementation record in the corpus."; }
    part c11ReviewGateR1 : TestResult { :>> id = "0d8004aa-0814-64aa-9b3e-0000003004aa"; :>> outcome = VerdictKind::pass; :>> judgedAgainst = "db044d4"; :>> judgedAt = "2026-08-17"; :>> judgedBy = "claudeOpus5"; }

    verification c11CloseOutGate : Test { :>> id = "0d8004ab-0814-64ab-9b3e-0000003004ab"; :>> title = "Sprint 335 closeOut gate (autonomous, D0049)"; :>> createdAt = "2026-08-17"; :>> createdBy = "claudeOpus5"; :>> method = VerificationMethod::inspect; :>> procedureText = "Autonomous closeOut (D0049). Decision coverage 29 -> 34 of 75; 12 critiquable Decisions remain. NO ISSUE RAISED for either cross-corpus finding, and the reasoning is the same in both cases: the promotion-criterion gap would be fixed by editing three human-authored Decisions, and the stale-status contradictions by editing two more — none of which I may do (D0108: only the owner edits an item's fields), and inventing backlog actions for them would schedule the owner's work. Both are recorded in the critiques with the measurement attached, which is where a reader of those Decisions will meet them. validate clean; check-engine clean; 35 guards ALL PASS; no code changed."; }
    part c11CloseOutGateR1 : TestResult { :>> id = "0d8004ac-0814-64ac-9b3e-0000003004ac"; :>> outcome = VerdictKind::pass; :>> judgedAgainst = "db044d4"; :>> judgedAt = "2026-08-17"; :>> judgedBy = "claudeOpus5"; }

    verification c11RetroGate : Test { :>> id = "0d8004ad-0814-64ad-9b3e-0000003004ad"; :>> title = "Sprint 335 retro gate (autonomous, D0049)"; :>> createdAt = "2026-08-17"; :>> createdBy = "claudeOpus5"; :>> method = VerificationMethod::analyze; :>> procedureText = "Autonomous retro (D0049) under D0131's retroTrack. WELL: (1) measuring a recurring PHRASE rather than reading past it produced the only corpus-level finding of the pass — 'promote once proven low-noise' appears in at least three Decisions and has never once fired; (2) the pass-heavy result was explained with a testable generalisation (mechanism-reusing Decisions got carried out; new-machinery Decisions partly did not) rather than left to look like leniency; (3) D0113 was CREDITED for predicting a blind spot this session then fell into, which is the kind of thing a critique corpus should preserve — its author knew the ceiling and said so. AVOIDABLE-ISSUE: none this sprint; the collision check added to the batch writer last pass held, and no name conflicts occurred. CARRIED: the stale-status class now has two Decision instances (d0109's title, d0112's decision text) on top of issue140's six comments, and the guard I wrote for issue140 covers none of them — a control narrower than the class it was written for, which is the same shape as the defects it was written to catch. Estimate 3 pts, delivered."; }
    part c11RetroGateR1 : TestResult { :>> id = "0d8004ae-0814-64ae-9b3e-0000003004ae"; :>> outcome = VerdictKind::pass; :>> judgedAgainst = "db044d4"; :>> judgedAt = "2026-08-17"; :>> judgedBy = "claudeOpus5"; }
}
