// ProjectDeliveryS262 — Sprint 262: a released artifact that can identify itself (issue091). Found by
// verifying the DOWNLOADED v0.2.2 asset rather than a local build. v0.2.3. EXECUTE. 2 pts.
package ProjectDeliveryS262 {
    private import EngineElement::*;
    private import EngineWork::*;
    private import EngineVerification::*;
    private import EngineRelationships::*;

    #CharteredBy dependency from versionIdentificationStory to d0135;

    part versionIdentificationStory : Story {
        :>> id = "0d7f0002-0814-5f02-9b3e-0000002f0002";
        :>> title = "Sprint 262: keel version — release version + build commit + guard inventory; v0.2.3 (2 pts)";
        :>> createdAt = "2026-08-14"; :>> createdBy = "claudeOpus5"; :>> kind = WorkKind::code; :>> priority = WorkPriority::p0; :>> owner = "claudeOpus5"; :>> estimatedPoints = 2;
    }

    action def DeliveryRunS262 {
        action storyVersionIdentification;
        verification storyVersionIdentificationDoD : Test { :>> id = "0d7f0003-0814-5f03-9b3e-0000002f0003"; :>> method = VerificationMethod::test; :>> procedureText = "Delivers dcVersionIdentification (issue091). Three versioned releases shipped with NO version identification in the artifact — `--version`, `-V` and `version` all printed usage. Since a guard's behaviour is a property of the BINARY (the mechanism behind issue089 and issue090), 'which binary are you running' is the FIRST diagnostic step for any blocked-downstream report, and it was answerable by neither the reporter nor the maintainer: a project still on the blocked version was INDISTINGUISHABLE from one that had upgraded, making 'upgrade to v0.2.2' unverifiable advice. FIX: `keel version` (also --version / -V / --json) reports the release version, the build commit baked by a new keel-cli/build.rs, and the guard inventory computed from GUARD_NAMES rather than restated. The COMMIT is load-bearing: the version string alone cannot separate the published artifact from a stale local build claiming the same number. It degrades honestly rather than guessing — `unknown` with no git, `+dirty` from a modified tree — and is checkable against the recorded Release facts in baselines.sysml. VERIFY, all measured: all four invocation forms print version + commit + guard split at exit 0; `--json` gives the machine-readable form; it answers from OUTSIDE a keel project, resolving before any root resolution, because a caller establishing which binary they hold may be standing anywhere; `+dirty` correctly flagged the modified working tree during development and the CI-built asset reports a CLEAN commit; a unit test asserts WARNING_ONLY_GUARDS is a strict subset of GUARD_NAMES, since a stray name would make the reported hard-blocking count overstate enforcement — the same defect class as the version gap itself. Published v0.2.3 asset asked to identify itself: reports `keel 0.2.3` / `build commit: b006f10`, matching the tag commit exactly, three platform binaries attached. clippy clean; 157 tests; validate + all 23 guards + check-engine green."; }
        part storyVersionIdentificationDoDR1 : TestResult { :>> id = "0d7f0004-0814-5f04-9b3e-0000002f0004"; :>> outcome = VerdictKind::pass; :>> judgedAgainst = "b006f10"; :>> judgedAt = "2026-08-14"; :>> judgedBy = "claudeOpus5"; }
    }

    verification viRefineGate : Test { :>> id = "0d7f0005-0814-5f05-9b3e-0000002f0005"; :>> title = "Sprint 262 refine gate (DoR)"; :>> createdAt = "2026-08-14"; :>> createdBy = "claudeOpus5"; :>> method = VerificationMethod::inspect; :>> procedureText = "DoR: the human asked only 'not working?' with no diagnostic detail. Rather than guess among the plausible subsystems or block on a question, the sprint took the one action useful under EVERY reading — verify the PUBLISHED artifact, since that is what downstream actually runs and I had only ever verified local builds. That gap was itself worth closing regardless of the answer. estimatedPoints=2. DoR met."; }
    part viRefineGateR1 : TestResult { :>> id = "0d7f0006-0814-5f06-9b3e-0000002f0006"; :>> outcome = VerdictKind::pass; :>> judgedAgainst = "b006f10"; :>> judgedAt = "2026-08-14"; :>> judgedBy = "claudeOpus5"; }

    verification viStandupGate : Test { :>> id = "0d7f0007-0814-5f07-9b3e-0000002f0007"; :>> title = "Sprint 262 standup gate"; :>> createdAt = "2026-08-14"; :>> createdBy = "claudeOpus5"; :>> method = VerificationMethod::inspect; :>> procedureText = "Approach: download the v0.2.2 asset from the GitHub Release and re-run the issue089 and issue090 reproductions against IT, not against a local build. Both passed — so the shipped fixes are real. The probe for how a downstream identifies its binary then failed outright, which became the sprint's actual content. No blockers."; }
    part viStandupGateR1 : TestResult { :>> id = "0d7f0008-0814-5f08-9b3e-0000002f0008"; :>> outcome = VerdictKind::pass; :>> judgedAgainst = "b006f10"; :>> judgedAt = "2026-08-14"; :>> judgedBy = "claudeOpus5"; }

    verification viImplementGate : Test { :>> id = "0d7f0009-0814-5f09-9b3e-0000002f0009"; :>> title = "Sprint 262 implement gate"; :>> createdAt = "2026-08-14"; :>> createdBy = "claudeOpus5"; :>> method = VerificationMethod::test; :>> procedureText = "Implemented at b006f10, released v0.2.3. The guard inventory is COMPUTED from GUARD_NAMES rather than written as a literal, because a hand-maintained count is exactly the kind of trusted-but-unchecked number this sprint exists to fix; a test enforces that the warning-only list stays a strict subset so the hard-blocking figure cannot overstate enforcement. build.rs emits rerun-if-changed only for paths that exist, since naming an absent path makes cargo rebuild on every invocation."; }
    part viImplementGateR1 : TestResult { :>> id = "0d7f000a-0814-5f0a-9b3e-0000002f000a"; :>> outcome = VerdictKind::pass; :>> judgedAgainst = "b006f10"; :>> judgedAt = "2026-08-14"; :>> judgedBy = "claudeOpus5"; }

    verification viReviewGate : Test { :>> id = "0d7f000b-0814-5f0b-9b3e-0000002f000b"; :>> title = "Sprint 262 review gate"; :>> createdAt = "2026-08-14"; :>> createdBy = "claudeOpus5"; :>> method = VerificationMethod::inspect; :>> procedureText = "Reviewed. The finding came from testing the thing downstream ACTUALLY RUNS instead of the thing on my disk — the two had never been distinguished, which is precisely the defect found. But the honest reading is that this is a PROCESS gap, not a missing flag: `relTagPublish` requires verifying the assets are ATTACHED, so three releases were verified by confirming files existed at a URL, and no published asset was ever executed. The process's own `relGate` argues a release is the one artifact that cannot be quietly re-verified later — that argument applies to the PUBLISHED binary, not only to the tree. Closing that requires editing a process definition, which is a CHANGE needing human acceptance, so it is PROPOSED rather than applied and recorded as its OWN Issue (issue092) with its own resolver — not as a second half of issue091, because resolution is COMPUTED from the resolver and one Issue would have computed as resolved the moment the code landed while the process gap remained. Prose cannot hold a state the model computes differently."; }
    part viReviewGateR1 : TestResult { :>> id = "0d7f000c-0814-5f0c-9b3e-0000002f000c"; :>> outcome = VerdictKind::pass; :>> judgedAgainst = "b006f10"; :>> judgedAt = "2026-08-14"; :>> judgedBy = "claudeOpus5"; }

    verification viCloseOutGate : Test { :>> id = "0d7f000d-0814-5f0d-9b3e-0000002f000d"; :>> title = "Sprint 262 closeOut gate (autonomous, D0049)"; :>> createdAt = "2026-08-14"; :>> createdBy = "claudeOpus5"; :>> method = VerificationMethod::inspect; :>> procedureText = "Autonomous closeOut (D0049). dcVersionIdentification carries a passing DoD TestResult at b006f10, so issue091 RESOLVES; the process root is issue092, whose resolver dcReleaseAssetVerification is declared and awaits human acceptance of a process-definition CHANGE. v0.2.3 published, and for the first time the published asset was obtained and asked what it is: `keel 0.2.3` / `build commit: b006f10`, matching the tag, three platform binaries attached. The v0.2.2 asset was confirmed to fix both downstream blockers in their reproduced states. validate + all 23 guards + check-engine green; clippy clean; 157 tests; CI green at b006f10 before tagging."; }
    part viCloseOutGateR1 : TestResult { :>> id = "0d7f000e-0814-5f0e-9b3e-0000002f000e"; :>> outcome = VerdictKind::pass; :>> judgedAgainst = "b006f10"; :>> judgedAt = "2026-08-14"; :>> judgedBy = "claudeOpus5"; }

    verification viRetroGate : Test { :>> id = "0d7f000f-0814-5f0f-9b3e-0000002f000f"; :>> title = "Sprint 262 retro gate (autonomous, D0049)"; :>> createdAt = "2026-08-14"; :>> createdBy = "claudeOpus5"; :>> method = VerificationMethod::analyze; :>> procedureText = "Autonomous retro (D0049) under D0131's retroTrack. WELL: (1) an ambiguous one-word prompt was answered by taking the action useful under every reading rather than guessing a subsystem or blocking on a question — and it found a real defect; (2) verifying the DOWNLOADED asset rather than a local build is what surfaced the gap, and it is now the difference between checking that a release exists and checking that it works; (3) the guard inventory is computed rather than restated, so the fix does not introduce a fresh unchecked number. AVOIDABLE-ISSUE 1: I reported a 'lead' — that `keel init` ships no schema/core/relationships.sysml — which was my own bug: an MSYS path (/c/Users/...) passed to Windows Python, which cannot resolve it. The file was present all along. NO NEW ITEM, and the reason is explicit: this is the OS/shell-adaptation class already recorded as issue065 and stated in CLAUDE.md §6, and it is not gate-able — the defect lived in a throwaway diagnostic command, not in a committed artifact, so no automated control could see it. What IS transferable is narrower and worth stating: an unexpected NEGATIVE result from a probe deserves the same read-back-the-computed-answer skepticism as a positive one, since I announced a finding on a FileNotFoundError before checking whether my own path form was valid. AVOIDABLE-ISSUE 2 (the substantive one): the deploy process verifies that release assets are ATTACHED but never that a published asset is the RIGHT BUILD, so three releases were verified by confirming files existed at a URL and none was ever executed. TRACKED as issue092 (severity High) with resolver dcReleaseAssetVerification declared and ranked above dcActivationManifest, the `relTagPublish` change PROPOSED for human acceptance rather than applied — a process edit is a CHANGE (§3a) and cannot be self-accepted. NOTE the correction this forced: I first wrote the process gap as a second 'half' of issue091 and stated in prose that it stayed open. `keel open-issues` computed issue091 as RESOLVED the moment its code resolver passed, so the prose asserted a state the model contradicted — the dual-truth failure the response contract exists to prevent, caught only by reading the computed view back instead of trusting what I had just written. One Issue per resolvable defect, each with its own resolver, is what makes resolution computable at all. Estimate 2 pts, delivered."; }
    part viRetroGateR1 : TestResult { :>> id = "0d7f0010-0814-5f10-9b3e-0000002f0010"; :>> outcome = VerdictKind::pass; :>> judgedAgainst = "b006f10"; :>> judgedAt = "2026-08-14"; :>> judgedBy = "claudeOpus5"; }
}
