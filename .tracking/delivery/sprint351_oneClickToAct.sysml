// ProjectDeliveryS351 — Sprint 351: my own fix added a second click. The server names the discharging
// panel, so the card lands on the controls in one hop. EXECUTE. 2 pts.
package ProjectDeliveryS351 {
    private import EngineElement::*;
    private import EngineWork::*;
    private import EngineVerification::*;
    private import EngineRelationships::*;

    #CharteredBy dependency from oneClickStory to d0093;

    part oneClickStory : Story {
        :>> id = "0d8005a0-0814-65a0-9b3e-0000003005a0";
        :>> title = "Sprint 351: one click to act — the server names the discharging panel (issue155, 2 pts)";
        :>> createdAt = "2026-08-19"; :>> createdBy = "claudeOpus5"; :>> kind = WorkKind::code; :>> priority = WorkPriority::p0; :>> owner = "claudeOpus5"; :>> estimatedPoints = 2;
    }

    action def DeliveryRunS351 {
        action storyOneClick;
        verification storyOneClickDoD : Test { :>> id = "0d8005a1-0814-65a1-9b3e-0000003005a1"; :>> method = VerificationMethod::demo; :>> procedureText = "THE HUMAN CONFIRMED ACT WORKS AND IMMEDIATELY FOUND THE NEXT DEFECT: 'it just provides me another button to click. why 2 clicks for a single request?' Correct, and the cause was MY FIX rather than the original design. issue154 had the console decide AFTER LANDING whether a destination could act, so a card opened a read-only view which then offered a bridge to a panel with controls - two clicks for one piece of work, and the second carried no information the first did not already imply. THE SERVER ALREADY COMPUTES EACH CLASS'S VIEW TO PRODUCE ITS COUNT, so it now names the discharging panel in the same pass and the card lands there directly. Verified live: acceptances-pending and authority-queue report dischargePanel `review`, findings-awaiting-disposition reports `dispositions`, sitting-review-due reports none and its card now reads `click to view (read-only)` instead of `click to act`. validate 379 clean; check-engine clean; 36 guards ALL PASS; 191 tests; clippy clean."; }
        part storyOneClickDoDR1 : TestResult { :>> id = "0d8005a2-0814-65a2-9b3e-0000003005a2"; :>> outcome = VerdictKind::fail; :>> judgedAgainst = "PENDING"; :>> judgedAt = "2026-08-19"; :>> judgedBy = "claudeOpus5"; }
    }

    verification ocRefineGate : Test { :>> id = "0d8005a3-0814-65a3-9b3e-0000003005a3"; :>> title = "Sprint 351 refine gate (DoR)"; :>> createdAt = "2026-08-19"; :>> createdBy = "claudeOpus5"; :>> method = VerificationMethod::inspect; :>> procedureText = "DoR. The question was 'why 2 clicks' and it has an answer rather than an excuse: because I derived the discharge target client-side, which can only happen after a fetch, which needs a landing place, which becomes the first click. Scoped as move the derivation to where the information already is. estimatedPoints=2."; }
    part ocRefineGateR1 : TestResult { :>> id = "0d8005a4-0814-65a4-9b3e-0000003005a4"; :>> outcome = VerdictKind::pass; :>> judgedAgainst = "3c7d134"; :>> judgedAt = "2026-08-19"; :>> judgedBy = "claudeOpus5"; }

    verification ocStandupGate : Test { :>> id = "0d8005a5-0814-65a5-9b3e-0000003005a5"; :>> title = "Sprint 351 standup gate"; :>> createdAt = "2026-08-19"; :>> createdBy = "claudeOpus5"; :>> method = VerificationMethod::inspect; :>> procedureText = "Approach: STATE the command-to-panel mapping with a reason per entry rather than infer it from the payload's shape. Inferring was what produced the bridge, and a regex over item `kind` strings would be a guess whose failure mode is sending the human to a panel that cannot act - the exact defect issue154 was about. Preserve the design principle by making None a FIRST-CLASS answer rather than by avoiding the mapping: a class with no discharging panel still works, still needs no console change, and now advertises itself honestly. No blockers."; }
    part ocStandupGateR1 : TestResult { :>> id = "0d8005a6-0814-65a6-9b3e-0000003005a6"; :>> outcome = VerdictKind::pass; :>> judgedAgainst = "3c7d134"; :>> judgedAt = "2026-08-19"; :>> judgedBy = "claudeOpus5"; }

    verification ocImplementGate : Test { :>> id = "0d8005a7-0814-65a7-9b3e-0000003005a7"; :>> title = "Sprint 351 implement gate"; :>> createdAt = "2026-08-19"; :>> createdBy = "claudeOpus5"; :>> method = VerificationMethod::test; :>> procedureText = "`discharge_panel(cmd)` sits beside `obligation_count`, which already computes each class's view, so naming the panel costs nothing extra. THE THREE ENTRIES AND WHY: orient and authority-queue discharge in `review` because that panel holds accept and reject for both proposed Decisions and pending confirmation gates, and pendingAcceptances and awaiting are largely the same items counted twice; dispositions discharges in the dispositions panel, which carries the per-finding controls; sitting-coverage returns NONE, because a sitting review is a human reading a sitting and recording a judgment and no console control does that - returning a panel that would merely display the work again would be the overpromise this sprint removes. THE CARD LABEL NOW MATCHES WHAT THE DESTINATION CAN DO: `click to act` where a discharging panel exists, `click to view (read-only)` where none does. That second string is the part I would defend hardest, because the original defect was never navigation - it was an affordance promising more than the destination delivered, and fixing the routing without fixing the label would have left three quarters of the lie in place. Measured live against the running console: dischargePanel review / review / dispositions / absent."; }
    part ocImplementGateR1 : TestResult { :>> id = "0d8005a8-0814-65a8-9b3e-0000003005a8"; :>> outcome = VerdictKind::pass; :>> judgedAgainst = "3c7d134"; :>> judgedAt = "2026-08-19"; :>> judgedBy = "claudeOpus5"; }

    verification ocReviewGate : Test { :>> id = "0d8005a9-0814-65a9-9b3e-0000003005a9"; :>> title = "Sprint 351 review gate"; :>> createdAt = "2026-08-19"; :>> createdBy = "claudeOpus5"; :>> method = VerificationMethod::inspect; :>> procedureText = "Reviewed. THE PATTERN ACROSS issue141, issue143, issue152, issue154 AND issue155 IS ONE DEFECT WEARING FIVE COSTUMES: an affordance that promised more than it delivered. A card bound by position promised the viewpoint it displayed; a JS-rendered marker promised to reveal a dead script; `click to act` promised a place to act; and my own bridge promised a destination while delivering a waypoint. Every fix has been the same move - make the surface say exactly what it can do - and the human has found each one by using the thing, which is the only way this class of defect is ever found. I ALSO NOTE THAT I INTRODUCED THIS ONE WHILE FIXING THE PREVIOUS ONE, one turn apart, and the reason is worth keeping: I avoided a mapping on principle (declaring a viewpoint must not require a console change) and paid for it with a worse user experience, when the principle was never in danger - None as a first-class answer preserves it completely. A principle defended past the point where it costs the user something has stopped being a principle and become a habit."; }
    part ocReviewGateR1 : TestResult { :>> id = "0d8005aa-0814-65aa-9b3e-0000003005aa"; :>> outcome = VerdictKind::pass; :>> judgedAgainst = "3c7d134"; :>> judgedAt = "2026-08-19"; :>> judgedBy = "claudeOpus5"; }

    verification ocCloseOutGate : Test { :>> id = "0d8005ab-0814-65ab-9b3e-0000003005ab"; :>> title = "Sprint 351 closeOut gate (autonomous, D0049)"; :>> createdAt = "2026-08-19"; :>> createdBy = "claudeOpus5"; :>> method = VerificationMethod::inspect; :>> procedureText = "Autonomous closeOut (D0049). issue155 recorded and triaged to dcOneClickToAct, whose result is FAILING with method=demo: three of four classes now route to a panel with controls and the fourth advertises itself read-only, all verified in the served payload, but whether a click lands in one hop is a browser behaviour D0160 says we cannot execute. Console up at 127.0.0.1:7777 on build 451fb540, served from a copy. THE ONE OBLIGATION CLASS STILL WITHOUT A CONTROL is sitting-review-due at 31 items - the largest of the four - and it is honest about it rather than fixed. pendingAcceptances d0159, d0161, d0162, d0163. validate 379 clean; check-engine clean; 36 guards ALL PASS; 191 tests; clippy clean."; }
    part ocCloseOutGateR1 : TestResult { :>> id = "0d8005ac-0814-65ac-9b3e-0000003005ac"; :>> outcome = VerdictKind::pass; :>> judgedAgainst = "3c7d134"; :>> judgedAt = "2026-08-19"; :>> judgedBy = "claudeOpus5"; }

    verification ocRetroGate : Test { :>> id = "0d8005ad-0814-65ad-9b3e-0000003005ad"; :>> title = "Sprint 351 retro gate (autonomous, D0049)"; :>> createdAt = "2026-08-19"; :>> createdBy = "claudeOpus5"; :>> method = VerificationMethod::analyze; :>> procedureText = "Autonomous retro (D0049) under D0131's retroTrack. AVOIDABLE-ISSUE: I shipped a two-click path one turn after being told the destination was wrong, and the extra click came from defending a design principle that was never actually at risk. The principle - declaring an act viewpoint must not require a console change - is good, and I read it as forbidding any command-to-panel mapping, when making None a first-class answer satisfies it exactly. THE GENERAL FORM: when a principle appears to forbid the obvious solution, check whether it forbids the solution or only the careless version of it. Mine forbade a mapping that would BREAK on an unknown command; it never forbade one that DEGRADES on an unknown command. SECOND FINDING, and it is the session's through-line: issue141, 143, 152, 154 and 155 are one defect in five costumes - an affordance promising more than it delivers. Every fix has been to make the surface state exactly what it can do, and every one was found by the human USING the thing rather than by me reading it. That is not a gap I can close by being more careful; it is an argument for the behavioural coverage D0160 deferred, and this is the fifth instance since that deferral - which is well past the trigger that Decision named. WELL: (1) the card label was fixed alongside the routing, since fixing the destination while leaving `click to act` on a read-only class would have preserved most of the original lie; (2) the mapping states a reason per entry, so the sitting-coverage None is a recorded position rather than an omission; (3) the result is recorded FAIL with method=demo rather than claiming a fourth unobserved browser behaviour. Estimate 2 pts, delivered as code with verification outstanding."; }
    part ocRetroGateR1 : TestResult { :>> id = "0d8005ae-0814-65ae-9b3e-0000003005ae"; :>> outcome = VerdictKind::pass; :>> judgedAgainst = "3c7d134"; :>> judgedAt = "2026-08-19"; :>> judgedBy = "claudeOpus5"; }
}
