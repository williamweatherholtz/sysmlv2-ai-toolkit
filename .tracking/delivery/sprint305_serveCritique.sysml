// ProjectDeliveryS305 — Sprint 305: independent Core-3 critique of the serve-discipline SR cluster.
// Five findings, all awaiting HUMAN disposition. EXECUTE. 5 pts.
package ProjectDeliveryS305 {
    private import EngineElement::*;
    private import EngineWork::*;
    private import EngineVerification::*;
    private import EngineRelationships::*;

    #CharteredBy dependency from serveCritiqueStory to issue121;

    part serveCritiqueStory : Story {
        :>> id = "0d8002c0-0814-62c0-9b3e-0000003002c0";
        :>> title = "Sprint 305: independent Core-3 critique of the serve-discipline requirements (5 pts)";
        :>> createdAt = "2026-08-15"; :>> createdBy = "claudeOpus5"; :>> kind = WorkKind::modeling; :>> priority = WorkPriority::p1; :>> owner = "claudeOpus5"; :>> estimatedPoints = 5;
    }

    action def DeliveryRunS305 {
        action storyServeCritique;
        verification storyServeCritiqueDoD : Test { :>> id = "0d8002c1-0814-62c1-9b3e-0000003002c1"; :>> method = VerificationMethod::critique; :>> procedureText = "Ran the element-critique process (D0079/D0080) over the five serve-discipline SystemRequirements: srServeModelDrivenRegistry, srServeLauncherDefinedOnly, srServeApproveGate, srServeOutputSchemaValidate, srServeScopedContext. Core-3 per the DECLARED policy (critique-policy.toml: completeness/correctness/testability for a SystemRequirement, read rather than assumed). 15 method=critique verifications, each #Verify-linked to its target: 10 survived the attack, 5 FAILED. INDEPENDENCE IS REAL AND WAS THE CONSTRAINT THAT PICKED THE TARGETS: all five are authored by wweatherholtz and critiqued by claudeOpus5, so judgedBy differs from the author as D0080 requires. 62 of the 142 uncovered elements are authored by claudeOpus5 and were therefore INELIGIBLE — I cannot critique my own work, and that limit is reported rather than worked around. FINDINGS, all raised as severity-carrying Issues (issue121-125) with D0102 typed edges back to the critique that raised each: C1/High — srServeModelDrivenRegistry requires computing each process's expected OUTPUT SCHEMA from the declared model, and no schema type can hold one (producedArtifact is free-text prose), so a Tier-1 contract is half unbuildable and two Tier-2 requirements #DependsOn it. C3/High — srServeApproveGate never constrains the approving 'operator' to a HUMAN, so an AI could approve its own routing, defeating the parent Need's stated property that the agent never silently acts on its own interpretation. C2/Medium — srServeLauncherDefinedOnly states a universal negative ('no code path shall...') that no test can demonstrate. C4/Medium — srServeOutputSchemaValidate governs the result but ignores side effects a failed attempt already caused. C5/Medium — srServeScopedContext bounds passed-in context while a launched agent reconstitutes context by READING. COVERAGE MOVED AND WAS READ BACK: SystemRequirement covered 5 -> 10, gaps 142 -> 137. All five findings are >= Medium and therefore AWAIT HUMAN DISPOSITION — none inferred. validate 330 clean; 33 guards green."; }
        part storyServeCritiqueDoDR1 : TestResult { :>> id = "0d8002c2-0814-62c2-9b3e-0000003002c2"; :>> outcome = VerdictKind::pass; :>> judgedAgainst = "db1d99f"; :>> judgedAt = "2026-08-15"; :>> judgedBy = "claudeOpus5"; }
    }

    verification scRefineGate : Test { :>> id = "0d8002c3-0814-62c3-9b3e-0000003002c3"; :>> title = "Sprint 305 refine gate (DoR)"; :>> createdAt = "2026-08-15"; :>> createdBy = "claudeOpus5"; :>> method = VerificationMethod::inspect; :>> procedureText = "DoR. Target selection was DRIVEN BY THE INDEPENDENCE RULE rather than by interest: of 142 uncovered elements, 62 are mine and disqualified outright, leaving 78. Among those, the skill prioritises requirements and needs over decisions, and the serve-discipline cluster was chosen because it is the most safety-relevant coherent set available — approve-before-execute, defined-only launch, bounded context, output validation — where an adversarial pass has the highest expected value. Batch size 5 with Core-3 each, matching the established convention. estimatedPoints=5."; }
    part scRefineGateR1 : TestResult { :>> id = "0d8002c4-0814-62c4-9b3e-0000003002c4"; :>> outcome = VerdictKind::pass; :>> judgedAgainst = "db1d99f"; :>> judgedAt = "2026-08-15"; :>> judgedBy = "claudeOpus5"; }

    verification scStandupGate : Test { :>> id = "0d8002c5-0814-62c5-9b3e-0000003002c5"; :>> title = "Sprint 305 standup gate"; :>> createdAt = "2026-08-15"; :>> createdBy = "claudeOpus5"; :>> method = VerificationMethod::inspect; :>> procedureText = "Approach: read the required lenses from the declared policy rather than assuming Core-3; read all five requirements in full; attack each through each lens with the intent to BREAK it; verify every suspected defect against the actual schema or corpus before recording it as a finding. No blockers."; }
    part scStandupGateR1 : TestResult { :>> id = "0d8002c6-0814-62c6-9b3e-0000003002c6"; :>> outcome = VerdictKind::pass; :>> judgedAgainst = "db1d99f"; :>> judgedAt = "2026-08-15"; :>> judgedBy = "claudeOpus5"; }

    verification scImplementGate : Test { :>> id = "0d8002c7-0814-62c7-9b3e-0000003002c7"; :>> title = "Sprint 305 implement gate"; :>> createdAt = "2026-08-15"; :>> createdBy = "claudeOpus5"; :>> method = VerificationMethod::test; :>> procedureText = "THE TWO HIGH FINDINGS WERE VERIFIED AGAINST THE ARTEFACTS, NOT ARGUED. C1 was checked by reading `.engine/schema/core/process.sysml` directly: `action def Process` carries purpose and cadence, `ProcessStep` carries triggerCondition, actionText, `producedArtifact : String` and owner — and `producedArtifact` is a free-text sentence about the artifact CHANGE, not a validatable schema. A grep for outputSchema / schemaRef across the schema returns nothing. C3 was checked by grepping 'operator' across the Needs and requirements: it appears only as prose and as `NeedSource::operator`, a source category rather than an actor kind, so nothing binds the approver to a human. Both were suspicions first and findings only after the check — the discipline this session repeatedly needed, because two earlier audit suspicions in sprint 303 evaporated under the same test and would have been false findings. RESTRAINT EXERCISED DELIBERATELY: three further weaknesses were NOT raised as separate findings because each is a consequence of a finding already recorded — the untestability of the output-schema clause follows from C1, and the unspecified 'recorded approval' artefact and the unspecified retry bound are subsumed by C3 and C4. Inflating five findings into eight would have made the human's disposition queue longer without telling them anything new."; }
    part scImplementGateR1 : TestResult { :>> id = "0d8002c8-0814-62c8-9b3e-0000003002c8"; :>> outcome = VerdictKind::pass; :>> judgedAgainst = "db1d99f"; :>> judgedAt = "2026-08-15"; :>> judgedBy = "claudeOpus5"; }

    verification scReviewGate : Test { :>> id = "0d8002c9-0814-62c9-9b3e-0000003002c9"; :>> title = "Sprint 305 review gate"; :>> createdAt = "2026-08-15"; :>> createdBy = "claudeOpus5"; :>> method = VerificationMethod::inspect; :>> procedureText = "Reviewed against the skill's own anti-pattern watchlist. NOT affirming instead of attacking: each of the 10 passes records what was ATTACKED and why the element survived, never that it 'looks good' — the correctness pass on srServeModelDrivenRegistry attacked it for a hidden dual-truth and for a staleness hazard before conceding. NOT self-critique: every target is authored by wweatherholtz, every result judgedBy claudeOpus5. NOT findings left as prose: all five are severity-carrying Issues with typed #Resolves and D0102 #DependsOn edges to the raising critique. NOT skipping disposition: all five are >= Medium and are recorded as awaiting the human's typed verdict, with the resolver item itself stating it is blocked on that disposition. WORTH THE HUMAN'S ATTENTION: C3 is the one to read first — the engine spent this session building attestation machinery (D0146 role, attestation-policy kinds=human, the kind-before-role check) that exists precisely to stop an AI supplying a human's attestation, and this requirement leaves the door open for a component not yet built."; }
    part scReviewGateR1 : TestResult { :>> id = "0d8002ca-0814-62ca-9b3e-0000003002ca"; :>> outcome = VerdictKind::pass; :>> judgedAgainst = "db1d99f"; :>> judgedAt = "2026-08-15"; :>> judgedBy = "claudeOpus5"; }

    verification scCloseOutGate : Test { :>> id = "0d8002cb-0814-62cb-9b3e-0000003002cb"; :>> title = "Sprint 305 closeOut gate (autonomous, D0049)"; :>> createdAt = "2026-08-15"; :>> createdBy = "claudeOpus5"; :>> method = VerificationMethod::inspect; :>> procedureText = "Autonomous closeOut (D0049). The critique work is complete; the DISPOSITIONS are not, and cannot be — a >= Medium finding needs the human's typed verdict and an AI cannot supply it (D0016/D0051/D0092). dcServeRequirementRework is authored as the resolver and states in its own DoD that it is blocked on that disposition, so the frontier cannot point a successor at rework nobody has authorised. validate 330 clean; 33 guards green; check-engine clean. Critique coverage read back from tooling rather than asserted: SystemRequirement 5 -> 10 covered, gaps 142 -> 137."; }
    part scCloseOutGateR1 : TestResult { :>> id = "0d8002cc-0814-62cc-9b3e-0000003002cc"; :>> outcome = VerdictKind::pass; :>> judgedAgainst = "db1d99f"; :>> judgedAt = "2026-08-15"; :>> judgedBy = "claudeOpus5"; }

    verification scRetroGate : Test { :>> id = "0d8002cd-0814-62cd-9b3e-0000003002cd"; :>> title = "Sprint 305 retro gate (autonomous, D0049)"; :>> createdAt = "2026-08-15"; :>> createdBy = "claudeOpus5"; :>> method = VerificationMethod::analyze; :>> procedureText = "Autonomous retro (D0049) under D0131's retroTrack. WELL: (1) the independence rule did real work rather than being a formality — it disqualified 62 of 142 candidate elements, including everything I built this session, and that constraint is what pushed the pass onto requirements a genuinely different author wrote; (2) both High findings were verified against the schema and the corpus before being recorded, and the restraint of NOT raising three derivative weaknesses as separate findings keeps the human's queue honest; (3) the required lenses were READ from critique-policy.toml rather than recalled, which matters because the policy is explicitly downstream-overridable and a remembered Core-3 would be wrong in any project that edited it. AVOIDABLE-ISSUE 1: I wrote a heredoc to git-bash /tmp and read it from Windows python again — the SAME defect recorded in sprint 301's retro, in the same session. The remedy was already written down and I did not apply it until it failed. The durable fix is not another note: use the Write tool for any file a later step must read. AVOIDABLE-ISSUE 2: a bash heredoc containing apostrophes and escaped quotes failed to parse, costing a retry; the same remedy applies and was then used. OBSERVED, NOT A FINDING OF THIS SPRINT: `keel dispositions` reports 67 undispositioned >= Medium findings across the whole model, of which these five are the newest. That backlog predates this pass and is the human's queue, not an AI's to clear. Estimate 5 pts, delivered."; }
    part scRetroGateR1 : TestResult { :>> id = "0d8002ce-0814-62ce-9b3e-0000003002ce"; :>> outcome = VerdictKind::pass; :>> judgedAgainst = "db1d99f"; :>> judgedAt = "2026-08-15"; :>> judgedBy = "claudeOpus5"; }
}
