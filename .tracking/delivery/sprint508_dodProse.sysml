// ProjectDeliveryS508 — Sprint 508: the fix for the prose trap had the prose trap. EXECUTE. 1 pt.
package ProjectDeliveryS508 {
    private import EngineElement::*;
    private import EngineWork::*;
    private import EngineVerification::*;
    private import EngineRelationships::*;

    // D0047 is the charter, not a Decision of its own: a correction that could recur must become a
    // tracked Issue AND an automated control, and that is exactly the shape of this sprint — issue325
    // plus the armed test that now holds it. Sprints 102, 148 and 263 charter here for the same reason.
    #CharteredBy dependency from dodProseStory to d0047;

    part dodProseStory : Story {
        :>> id = "6d1f8a25-93c7-4e60-b148-2f5a90c3e871";
        :>> title = "Sprint 508: the last unsanitized prose interpolation, found by it breaking the tree (1 pt)";
        :>> createdAt = "2026-09-01"; :>> createdBy = "claudeOpus5"; :>> kind = WorkKind::code; :>> priority = WorkPriority::p0; :>> owner = "claudeOpus5"; :>> estimatedPoints = 1;
    }

    action def DeliveryRunS508 {
        action storyDodProse;
        verification storyDodProseDoD : Test { :>> id = "b04e72c1-58d9-4f37-a2e6-8c15093fb4a7"; :>> method = VerificationMethod::test; :>> procedureText = "DELIVERED BACKLOG ITEMS: dcDodProseCannotBreakTheModel (resolves issue325). NOT FOUND BY LOOKING - hit one command after recording issue322 about this exact class. add_task_locked interpolated DoD prose RAW into a SysML string literal (write.rs:1193) while every other prose path in the same file bound sanitize_field. A DoD carrying a quoted phrase closed the literal and left backlog.sysml unparseable at 418:398, so the NEXT command could not read the model to do anything - including to report the problem. DONE: sanitize at the write path, not in cmd_add_task, because issue322's finding was that the previous prose defect recurred from being fixed per-command; and SWEPT every interpolation in write.rs first rather than patching the one line, confirming this was the last. VERIFY: a_dod_containing_quotes_cannot_break_the_backlog asserts the interior holds no double quote, the phrase survives as apostrophes, it stays one line, and the file still LEXES AND PARSES. ALSO recorded, not built: issue326 and issue327, two shipped-CI defects a peer session found downstream."; }
        // RAN: a_dod_containing_quotes_cannot_break_the_backlog 1/1; ARMED by commenting the sanitize call out, where it fails on the parse assertion at write.rs:1799; keel validate 578 clean after the hand repair of the corrupted line
        part storyDodProseDoDR1 : TestResult { :>> id = "f39c05b8-7e41-4d26-9053-6ba82c1e7d94"; :>> outcome = VerdictKind::pass; :>> judgedAgainst = "19eb078"; :>> judgedAt = "2026-09-01"; :>> judgedBy = "claudeOpus5"; }
    }

    verification dodProseRefineGate : Test { :>> id = "0a7e35d9-c162-4b48-9e07-5f83d201ca6b"; :>> title = "Sprint 508 refine gate (DoR)"; :>> createdAt = "2026-09-01"; :>> createdBy = "claudeOpus5"; :>> method = VerificationMethod::inspect; :>> procedureText = "READY the moment it happened: the defect arrived as a parse error naming its own line and column, and the corrupted text was mine and readable. Nothing needed investigating before the fix could be specified."; }
    verification dodProseStandupGate : Test { :>> id = "1b8f46ea-d273-4c59-af18-6094e312db7c"; :>> title = "Sprint 508 standup gate"; :>> createdAt = "2026-09-01"; :>> createdBy = "claudeOpus5"; :>> method = VerificationMethod::inspect; :>> procedureText = "THE SWEEP CAME BEFORE THE PATCH, deliberately. issue322 had just recorded that this class recurs when fixed per-command, so patching write.rs:1193 alone would have repeated the exact mistake I was fixing. Grepped every interpolation into a SysML literal in write.rs: record_issue_locked, record_decision, record_obligation, the notes path, the view-attribute path and the claim path all bind sanitize_field; add_task_locked was the only one that did not. Count of unsanitized interpolations now zero."; }
    verification dodProseImplementGate : Test { :>> id = "2c904f7b-e385-4d1a-b062-71a5c8036e9d"; :>> title = "Sprint 508 implement gate"; :>> createdAt = "2026-09-01"; :>> createdBy = "claudeOpus5"; :>> method = VerificationMethod::test; :>> procedureText = "RAN: cargo test --release --lib a_dod_containing_quotes -> 1 passed. ARMED per D0253 by commenting out the sanitize_field call and re-running -> FAILED at write.rs:1799, the parse assertion. Tree repaired by hand first (the corrupted literal's interior quotes converted to apostrophes) and keel validate read back 578 clean. The test asserts the PROPERTY rather than a character count: nothing between the procedureText delimiters reopens a literal, the hostile phrase survives as apostrophes, no newline or tab remains, and keel_parser tokenize + parse both succeed on the written file."; }
    verification dodProseReviewGate : Test { :>> id = "3da15c86-f490-4e27-8153-0b62974ae1f8"; :>> title = "Sprint 508 review gate — three passes per D0172"; :>> createdAt = "2026-09-01"; :>> createdBy = "claudeOpus5"; :>> method = VerificationMethod::inspect; :>> procedureText = "THREE PASSES. (1) IS SANITIZING A LOSS: a double quote becomes an apostrophe and whitespace collapses to single spaces. Every other prose field in the corpus already lives under that rule, so this makes add-task consistent rather than lossy, and a DoD needing a literal double quote has no way to carry one today in any field. (2) WAS THE HAND REPAIR HONEST: yes - the interior quotes were converted exactly as sanitize_field would have, so the committed text is byte-identical to what the fixed code would have written, rather than a differently-worded dodge. (3) DID I FIX THE RIGHT LAYER: the tell is that cmd_add_task needed no change at all. If the fix had belonged in the command, the write path would still corrupt for any other caller - including the console's write API."; }
    verification dodProseCloseOutGate : Test { :>> id = "4eb26d97-a501-4f38-9264-1c73085bf209"; :>> title = "Sprint 508 closeOut gate (autonomous, D0049)"; :>> createdAt = "2026-09-01"; :>> createdBy = "claudeOpus5"; :>> method = VerificationMethod::inspect; :>> procedureText = "CLOSED. issue325 resolved. issue326 and issue327 recorded from a peer session's downstream report, both verified here at file:line, both resolved by dcShippedCiRunsWhereItLands which is NOT started - deliberately, see the retro. Three prose citations corrected before commit: the ids allocated in a different order than my drafts assumed."; }
    verification dodProseRetroGate : Test { :>> id = "5fc37ea8-b612-4049-8375-2d84196cb310"; :>> title = "Sprint 508 retro gate (autonomous, D0049)"; :>> createdAt = "2026-09-01"; :>> createdBy = "claudeOpus5"; :>> method = VerificationMethod::analyze; :>> procedureText = "THREE FINDINGS. (1) THE FIX FOR THE PROSE TRAP HAD THE PROSE TRAP. `add-task --dod-from` was added THIS MORNING to close issue322 - whose recorded finding was that the class recurs when fixed per-command - and it was wired to read a file without routing the result through the sanitizer. The rule I wrote in issue322's own text described what I was about to do. The general form: adding a new INPUT to a write path is not the same as making that path safe, and the second half is the one that gets skipped because the first half feels like the fix. (2) A CORRUPTING WRITE TAKES EVERY OTHER CONTROL DOWN WITH IT. The failure surfaced as `keel record issue` refusing with 'cannot read the model to check the resolver' - the write API behaving correctly and reporting a cause that pointed at the wrong thing. Everything parses before it checks, so one unparseable file blinds the whole enforcement layer at once. That argues for treating model-corrupting defects as a severity class of their own, not merely High. (3) I PRE-WROTE THREE ISSUE IDS BEFORE THEY WERE ALLOCATED and all three were wrong - the same mis-citation class as issue320, whose lesson was to read the allocated id back. The resolver EDGES were right because the write path assigns those; only my prose was wrong, which is exactly the half no control checks."; }
}
