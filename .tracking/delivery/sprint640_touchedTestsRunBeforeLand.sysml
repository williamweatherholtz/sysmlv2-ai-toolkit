// ProjectDeliveryS640 — Sprint 640: Sprint 640: keel land computes the TOUCHED test set - the integration tests whose text names a module changed since the base - and, once D0421 is accepted, runs exactly those before the first push and refuses on a failure (dcTouchedTestsRunBeforeLand, issue416, D0421). CHANGE: a new gate on the push path, declared inert and armed by the human's acceptance (D0337). 3 pts.. EXECUTE. 3 pts.
package ProjectDeliveryS640 {
    private import EngineElement::*;
    private import EngineWork::*;
    private import EngineVerification::*;
    private import EngineRelationships::*;

    #CharteredBy dependency from touchedTestsRunBeforeLandStory to d0421;

    part touchedTestsRunBeforeLandStory : Story {
        :>> id = "22560b59-b662-478c-9ff8-ec9b8e303d16";
        :>> title = "Sprint 640: Sprint 640: keel land computes the TOUCHED test set - the integration tests whose text names a module changed since the base - and, once D0421 is accepted, runs exactly those before the first push and refuses on a failure (dcTouchedTestsRunBeforeLand, issue416, D0421). CHANGE: a new gate on the push path, declared inert and armed by the human's acceptance (D0337). 3 pts. (3 pts)";
        :>> createdAt = "2026-09-09"; :>> createdBy = "claudeOpus5"; :>> kind = WorkKind::code; :>> priority = WorkPriority::p0; :>> owner = "claudeOpus5"; :>> estimatedPoints = 3;
    }

    action def DeliveryRunS640 {
        action storyTouchedTestsRunBeforeLand;
        verification storyTouchedTestsRunBeforeLandDoD : Test { :>> id = "4d58dc90-c653-4f82-904b-c084acc6280d"; :>> method = VerificationMethod::test; :>> procedureText = "DELIVERED (dcTouchedTestsRunBeforeLand resolves issue416): keel-cli/src/touched.rs computes the set from git diff origin/<branch> (fallbacks: the suite receipt's head, HEAD~1), module_stem maps keel-cli/src/<stem>.rs and <dir>/mod.rs to a stem and main.rs/lib.rs to None, touched_tests matches stems by whole word in each keel-cli/tests/<name>.rs plus the test files the push changed; before_push prints the set on every self-build push, runs it as one cargo test --release --no-fail-fast when .engine/decisions/0421-*.sysml carries d0421AcceptR1 and refuses on failure naming failing_binaries from cargo's rerun hint, and records outcome not-run while D0421 is proposed; every path writes .keel/metrics/touched-receipt.toml; keel suite --touched routes to the same run through the shared own_image_refusal. VERIFY: cargo test --release --test touched_tests_run_before_land -> 3 passed 0 failed read from the log (a stale test naming a changed module refuses then lands once fixed, receipts pass/fail/empty; inert while proposed; the pure set's known positive and negative); --test push_gate_is_withdrawn 2 passed; --test adoption_check_can_fail 2 passed; lib unit tests including failing_binaries_are_read_from_cargos_rerun_hint ok; clippy -D warnings clean; keel validate / check-engine clean; keel guard ALL PASS exit 0; cliSuite fact in commands.sysml and cli_facts.rs names --touched and cites D0421; CLAUDE.md suite paragraph names the touched set and its arming condition; ceLandGate codeHash refreshed to the live hash."; }
        // RAN: cargo test --release --test touched_tests_run_before_land (3 passed), --test push_gate_is_withdrawn (2 passed), --test adoption_check_can_fail (2 passed), lib tests ok - read from tests640d.log; cargo clippy --workspace --all-targets -D warnings clean; keel validate/check-engine clean; keel guard --no-receipt ALL PASS exit 0
        part storyTouchedTestsRunBeforeLandDoDR1 : TestResult { :>> id = "0b4cb05e-f771-4794-bf1c-94b6b2038a71"; :>> outcome = VerdictKind::pass; :>> judgedAgainst = "c67c05c"; :>> judgedAt = "2026-09-09"; :>> judgedBy = "claudeOpus5"; }
    }

    verification touchedTestsRunBeforeLandRefineGate : Test { :>> id = "4b465dd8-599a-453b-9f7d-4b95c7d3293b"; :>> title = "Sprint 640 refine gate (DoR)"; :>> createdAt = "2026-09-09"; :>> createdBy = "claudeOpus5"; :>> method = VerificationMethod::inspect; :>> procedureText = "Definition of Ready: issue416 is recorded with dcTouchedTestsRunBeforeLand as its resolver; the DoD names the set, the point of application, the arming condition and the VERIFY with a known positive and negative (D0388); one design constraint settled up front - the refusal is a process change and stays inert until the human's word, so the sprint delivers the set, the receipt and the inert gate, and the fixture plants the acceptance token to test the armed path; 3 points: a module, a land hook, a suite route, one integration test file."; }
    // RAN: cargo test --release --test touched_tests_run_before_land (3 passed), --test push_gate_is_withdrawn (2 passed), --test adoption_check_can_fail (2 passed), lib tests ok - read from tests640d.log; cargo clippy --workspace --all-targets -D warnings clean; keel validate/check-engine clean; keel guard --no-receipt ALL PASS exit 0
    part touchedTestsRunBeforeLandRefineGateR1 : TestResult { :>> id = "49c784a2-ae17-44ba-a877-56af9fd6f15e"; :>> outcome = VerdictKind::pass; :>> judgedAgainst = "c67c05c"; :>> judgedAt = "2026-09-09"; :>> judgedBy = "claudeOpus5"; }
    verification touchedTestsRunBeforeLandStandupGate : Test { :>> id = "9c4d375c-8a70-4b0f-b675-3fd31b0cfca6"; :>> title = "Sprint 640 standup gate"; :>> createdAt = "2026-09-09"; :>> createdBy = "claudeOpus5"; :>> method = VerificationMethod::inspect; :>> procedureText = "No blocker. Two defects found and fixed in the sprint: the fixture's decision file was first written as a bare comment and every decisions-reading guard reported it unparseable, then engine-lint required import EngineWork - it is now a parseable package; and the first live run recorded failed = 1 with failing = [] because the Running header / test result pairing does not hold in a capture (stdout is read whole before stderr), so failing_binaries reads cargo's own --test <name> rerun hint and the unit test carries that capture as its known positive."; }
    // RAN: cargo test --release --test touched_tests_run_before_land (3 passed), --test push_gate_is_withdrawn (2 passed), --test adoption_check_can_fail (2 passed), lib tests ok - read from tests640d.log; cargo clippy --workspace --all-targets -D warnings clean; keel validate/check-engine clean; keel guard --no-receipt ALL PASS exit 0
    part touchedTestsRunBeforeLandStandupGateR1 : TestResult { :>> id = "74867f09-7eaa-4206-bd4a-d8c935fccec0"; :>> outcome = VerdictKind::pass; :>> judgedAgainst = "c67c05c"; :>> judgedAt = "2026-09-09"; :>> judgedBy = "claudeOpus5"; }
    verification touchedTestsRunBeforeLandImplementGate : Test { :>> id = "bbbc4ee7-9414-4a0c-a8c1-89cdefeac0de"; :>> title = "Sprint 640 implement gate"; :>> createdAt = "2026-09-09"; :>> createdBy = "claudeOpus5"; :>> method = VerificationMethod::test; :>> procedureText = "touched.rs (new): RECEIPT, module_stem, touched_tests, failing_binaries, compute, run, before_push, cmd; suite.rs: own_image_refusal public, --touched routed; sync.rs: before_push called after the tree gate with the D0421 comment; lib.rs: pub mod touched; cliSuite fact in both homes (facts640.py); touched_tests_run_before_land.rs (new, 3 tests). Records: D0421 --process-change (proposed), code-registry ceLandGate refreshed, CLAUDE.md doc-sync (docsync640.py). Tests and clippy run before the records, logs tests640*.log."; }
    // RAN: cargo test --release --test touched_tests_run_before_land (3 passed), --test push_gate_is_withdrawn (2 passed), --test adoption_check_can_fail (2 passed), lib tests ok - read from tests640d.log; cargo clippy --workspace --all-targets -D warnings clean; keel validate/check-engine clean; keel guard --no-receipt ALL PASS exit 0
    part touchedTestsRunBeforeLandImplementGateR1 : TestResult { :>> id = "431576a0-4845-4fde-ae7e-24aeb5b6c15e"; :>> outcome = VerdictKind::pass; :>> judgedAgainst = "c67c05c"; :>> judgedAt = "2026-09-09"; :>> judgedBy = "claudeOpus5"; }
    verification touchedTestsRunBeforeLandReviewGate : Test { :>> id = "90bc6522-9f5a-44f6-b207-c447132d6b1b"; :>> title = "Sprint 640 review gate — three passes per D0172"; :>> createdAt = "2026-09-09"; :>> createdBy = "claudeOpus5"; :>> method = VerificationMethod::inspect; :>> procedureText = "Three passes per D0172: (1) the gate cannot fire until the human accepts - the inert path is pinned by a test, so accepting D0421 is a real choice and not a ratification; (2) the set is text-derived and whole-word, so a stem like sync does not match synced, and lib.rs/main.rs are reported rather than silently matched or silently dropped; (3) the failing names are read from the one line cargo prints with both the name and the verdict, and the known-positive is the real capture order that broke the first cut - the check is probed before its answer is stated (D0388)."; }
    // RAN: cargo test --release --test touched_tests_run_before_land (3 passed), --test push_gate_is_withdrawn (2 passed), --test adoption_check_can_fail (2 passed), lib tests ok - read from tests640d.log; cargo clippy --workspace --all-targets -D warnings clean; keel validate/check-engine clean; keel guard --no-receipt ALL PASS exit 0
    part touchedTestsRunBeforeLandReviewGateR1 : TestResult { :>> id = "6a2b1131-a7d4-4788-9848-309592fffacb"; :>> outcome = VerdictKind::pass; :>> judgedAgainst = "c67c05c"; :>> judgedAt = "2026-09-09"; :>> judgedBy = "claudeOpus5"; }
    verification touchedTestsRunBeforeLandCloseOutGate : Test { :>> id = "9f14b097-7423-436e-ba68-2a0a8099592b"; :>> title = "Sprint 640 closeOut gate (autonomous, D0049)"; :>> createdAt = "2026-09-09"; :>> createdBy = "claudeOpus5"; :>> method = VerificationMethod::inspect; :>> procedureText = "keel validate . clean, keel check-engine . clean, keel guard ALL PASS exit 0; dcTouchedTestsRunBeforeLand stamped at the pre-commit tree; issue416 triaged through it; D0421 proposed for the human's word, its refusal inert until then; the receipt and keel suite --touched live now so the set's cost is on record before the gate is asked for."; }
    // RAN: cargo test --release --test touched_tests_run_before_land (3 passed), --test push_gate_is_withdrawn (2 passed), --test adoption_check_can_fail (2 passed), lib tests ok - read from tests640d.log; cargo clippy --workspace --all-targets -D warnings clean; keel validate/check-engine clean; keel guard --no-receipt ALL PASS exit 0
    part touchedTestsRunBeforeLandCloseOutGateR1 : TestResult { :>> id = "a36ce1bf-38ac-4813-930d-ad3dd1faaa36"; :>> outcome = VerdictKind::pass; :>> judgedAgainst = "c67c05c"; :>> judgedAt = "2026-09-09"; :>> judgedBy = "claudeOpus5"; }
    verification touchedTestsRunBeforeLandRetroGate : Test { :>> id = "f89df651-bbbf-48b4-8670-1ea8909bd7bf"; :>> title = "Sprint 640 retro gate (autonomous, D0049)"; :>> createdAt = "2026-09-09"; :>> createdBy = "claudeOpus5"; :>> method = VerificationMethod::analyze; :>> procedureText = "Avoidable-issue scan: the fixture defect (unparseable decision file) and the capture-order defect were both found by running the test before stating its answer, which is the D0388 discipline working as intended and not an issue. issue434's mechanism appeared once more - a background test wrapper exited 0 over a 1 failed log - and the verdict was read from the log; the control for that class is in land since sprint 639. No new item."; }
    // RAN: cargo test --release --test touched_tests_run_before_land (3 passed), --test push_gate_is_withdrawn (2 passed), --test adoption_check_can_fail (2 passed), lib tests ok - read from tests640d.log; cargo clippy --workspace --all-targets -D warnings clean; keel validate/check-engine clean; keel guard --no-receipt ALL PASS exit 0
    part touchedTestsRunBeforeLandRetroGateR1 : TestResult { :>> id = "d029c7db-7cf1-4d9e-92c2-2d53ce28725f"; :>> outcome = VerdictKind::pass; :>> judgedAgainst = "c67c05c"; :>> judgedAt = "2026-09-09"; :>> judgedBy = "claudeOpus5"; }
}
