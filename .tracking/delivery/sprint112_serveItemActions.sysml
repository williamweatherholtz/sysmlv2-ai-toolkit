// =====================================================================
// ProjectDeliveryS112 — Sprint 112: serveItemActions (D0094 console deepening — the FINALE that makes
// the modal ACT). The introspect modal (Sprint 111) gains per-item ACTIONS, all reusing endpoints already
// built: (a) Critique ▶ / Investigate ▶ open an SSE stream to /api/agent/stream (the local `claude` agent-
// bridge, enterprise auth, no API key) for THAT item, streamed live into a modal <pre> log; (b) for an
// Issue, Act / Accept-risk / Dismiss buttons record a disposition via /api/disposition; (c) for an action/
// task (item not authored as a Part), an Add-TestResult verdict-select posts to the NEW /api/testresult,
// which append_result's a downstream TestResult on the task's .tracking file at git HEAD (never auto-commits).
// One generic modal now critiques, investigates, dispositions, and verifies ANY item. Read paths stay cached.
// A non-hermetic BDD test surfaced mid-work was fixed + logged (issue041, D0047). Total: 5 pts. Ceremony: AUTONOMOUS (D0049).
// =====================================================================
package ProjectDeliveryS112 {
    private import EngineElement::*;
    private import EngineWork::*;
    private import EngineVerification::*;
    private import EngineRelationships::*;

    #CharteredBy dependency from serveItemActionsStory to d0094;

    part serveItemActionsStory : Story {
        :>> id = "63940516-2c7d-4e8f-c112-51627384c001";
        :>> title = "Sprint 112: serveItemActions (5 pts) — per-item Critique/Investigate/Disposition/Add-TestResult in the introspect modal (D0094 finale)";
        :>> createdAt = "2026-06-23";
        :>> createdBy = "wweatherholtz";
        :>> kind = WorkKind::code;
        :>> priority = WorkPriority::p2;
        :>> owner = "claudeOpus";
        :>> estimatedPoints = 5;
    }

    action def DeliveryRunS112 {
        action storyServeItemActions;
        verification storyServeItemActionsDoD : Test { :>> id = "63940516-2c7d-4e8f-c112-51627384c002"; :>> method = VerificationMethod::test; :>> procedureText = "D0094 finale (the human's 'everything critiqueable/expandable; add a TestResult downstream from X/Y'). serve.rs: NEW POST /api/testresult (TrReq{task,verdict,judged_at,judged_by}) -> find_task_file scans .tracking for `action <task>;`, then crate::write::append_result at git HEAD (judgedBy default wweatherholtz; 400 on a verdict not pass|fail; 404 when no such action; never auto-commits). Route registered after /api/disposition. Frontend console.html openItem modal: Critique ▶/Investigate ▶ buttons open runAgentModal(action,item) -> EventSource(/api/agent/stream?action&target) streamed into a modal <pre> (reuses renderAgentEvent); for type==Issue, Act/Accept-risk/Dismiss reuse disposition(name,verdict) (/api/disposition); for a non-Part item (found:false -> task), a verdict <select> + Add-TestResult posts to /api/testresult via addTestResult(task); closeItem closes the modal EventSource (stopModalAgent). VERIFY (LIVE, this sprint): POST /api/testresult unknown task -> 404 {error: no `action ...`}; bad verdict -> 400 {verdict must be pass or fail}; GET /api/item/issue039 -> found Issue; the served console.html contains runAgentModal + addTestResult + api/testresult + the 'Smooth sailing with AI' subtitle. clippy --workspace --all-targets -D warnings + cargo test (46 lib + all BDD, incl. orient 8/8) + keel validate 125 + guard all (13) green."; }
        part storyServeItemActionsDoDR1 : TestResult { :>> id = "63940516-2c7d-4e8f-c112-51627384c003"; :>> outcome = VerdictKind::pass; :>> judgedAgainst = "7642f1c"; :>> judgedAt = "2026-06-23"; :>> judgedBy = "claudeOpus"; }
    }

    verification serveItemActionsRefineGate : Test { :>> id = "63940516-2c7d-4e8f-c112-51627384c004"; :>> title = "Sprint 112 refine gate (DoR)"; :>> createdAt = "2026-06-23"; :>> createdBy = "claudeOpus"; :>> method = VerificationMethod::inspect; :>> procedureText = "DoR: serveLiveCache (perf+events) and serveItemIntrospect (generic expand) shipped; the last console-deepening tier per the confirmed plan is per-item ACTIONS so the human can critique/investigate any item and add a TestResult downstream from the UI. It reuses the agent-bridge (/api/agent/stream) + disposition write path (/api/disposition) + a small new /api/testresult. Resolver: serveItemActions. estimatedPoints=5. #CharteredBy d0094. DoD accepted."; }
    part serveItemActionsRefineGateR1 : TestResult { :>> id = "63940516-2c7d-4e8f-c112-51627384c005"; :>> outcome = VerdictKind::pass; :>> judgedAgainst = "7642f1c"; :>> judgedAt = "2026-06-23"; :>> judgedBy = "claudeOpus"; }

    verification serveItemActionsStandupGate : Test { :>> id = "63940516-2c7d-4e8f-c112-51627384c006"; :>> title = "Sprint 112 standup gate"; :>> createdAt = "2026-06-23"; :>> createdBy = "claudeOpus"; :>> method = VerificationMethod::inspect; :>> procedureText = "Approach: serve.rs add find_task_file + api_testresult (append_result on the task file, HEAD sha, 400/404 guards) + register /api/testresult; frontend wire the modal: runAgentModal(action,target) (modal-scoped EventSource into a <pre>), disposition buttons for Issues, addTestResult for tasks, stopModalAgent on close. All three actions reuse existing endpoints except the small new /api/testresult. No .engine/schema/process-def change -> no kernel/keystone. Verify endpoints live (404/400/introspect/frontend). No blockers."; }
    part serveItemActionsStandupGateR1 : TestResult { :>> id = "63940516-2c7d-4e8f-c112-51627384c007"; :>> outcome = VerdictKind::pass; :>> judgedAgainst = "7642f1c"; :>> judgedAt = "2026-06-23"; :>> judgedBy = "claudeOpus"; }

    verification serveItemActionsImplementGate : Test { :>> id = "63940516-2c7d-4e8f-c112-51627384c008"; :>> title = "Sprint 112 implement gate"; :>> createdAt = "2026-06-23"; :>> createdBy = "claudeOpus"; :>> method = VerificationMethod::test; :>> procedureText = "Implemented /api/testresult (+ route) + the modal actions (Critique/Investigate stream, Issue disposition, task Add-TestResult, close-closes-EventSource). VERIFY (live): POST /api/testresult unknown -> 404; bad verdict -> 400; /api/item/issue039 found Issue; served console.html has runAgentModal/addTestResult/api/testresult/subtitle. clippy -D warnings green (fixed: 3 doc_markdown backtick lints on the new TrReq/find_task_file/api_testresult docs); cargo test 46 lib + BDD all pass (orient 8/8 after the hermetic fix); keel validate 125; guard all (13) PASS. MID-WORK CORRECTION (D0047): orient_bdd 'unresolvable SHA' failed because it wrote its fixture to a system temp dir outside any git repo, so orient's conservative-on-git-failure SHA check defaulted the fake SHA to valid (done=1); fixed by git_init-ing the fixture root (now hermetic, deterministic invalidEvidence) and logged as issue041 (Low). orient semantics unchanged."; }
    part serveItemActionsImplementGateR1 : TestResult { :>> id = "63940516-2c7d-4e8f-c112-51627384c009"; :>> outcome = VerdictKind::pass; :>> judgedAgainst = "7642f1c"; :>> judgedAt = "2026-06-23"; :>> judgedBy = "claudeOpus"; }

    verification serveItemActionsReviewGate : Test { :>> id = "63940516-2c7d-4e8f-c112-51627384c00a"; :>> title = "Sprint 112 review gate"; :>> createdAt = "2026-06-23"; :>> createdBy = "claudeOpus"; :>> method = VerificationMethod::inspect; :>> procedureText = "Diff reviewed. The console is now a full cockpit: from any expanded item you can run an independent agent critique/investigation (streamed live), disposition an Issue, or append a downstream TestResult to a task -- each action reuses a path already governed by the discipline (agent inherits CLAUDE.md, no auto-commit, enterprise auth; disposition via apply-review's write path; testresult via append_result at HEAD). /api/testresult is a thin wrapper over the same write API as the CLI (find the action's file, append_result) -- one write path, two surfaces (D0093 dual-surface). The agent NEVER commits; the human commits (oversight preserved, permissions policy unchanged per the human). Read paths stay cached #View. The mid-work test fix (issue041) was logged not patched silently (D0047). Clean."; }
    part serveItemActionsReviewGateR1 : TestResult { :>> id = "63940516-2c7d-4e8f-c112-51627384c00b"; :>> outcome = VerdictKind::pass; :>> judgedAgainst = "7642f1c"; :>> judgedAt = "2026-06-23"; :>> judgedBy = "claudeOpus"; }

    verification serveItemActionsCloseOutGate : Test { :>> id = "63940516-2c7d-4e8f-c112-51627384c00c"; :>> title = "Sprint 112 closeOut gate (autonomous, D0049)"; :>> createdAt = "2026-06-23"; :>> createdBy = "claudeOpus"; :>> method = VerificationMethod::inspect; :>> procedureText = "Autonomous closeOut (D0049): storyServeItemActions DoD recorded pass; per-item Critique/Investigate/Disposition/Add-TestResult live + verified (404/400/introspect/frontend). clippy + cargo test (46 lib + BDD, orient 8/8) + keel validate 125 + guard all (13) green. Self-evidencing (D0051). The D0094 interactive console arc is COMPLETE: read tier (orient/decisions/processes/findings/reports/history) + serveLiveCache (fast, event-driven) + serveItemIntrospect (expand any item) + serveItemActions (act on any item via the agent-bridge + write API). issue041 logged + resolved by this story (D0047)."; }
    part serveItemActionsCloseOutGateR1 : TestResult { :>> id = "63940516-2c7d-4e8f-c112-51627384c00d"; :>> outcome = VerdictKind::pass; :>> judgedAgainst = "7642f1c"; :>> judgedAt = "2026-06-23"; :>> judgedBy = "claudeOpus"; }

    verification serveItemActionsRetroGate : Test { :>> id = "63940516-2c7d-4e8f-c112-51627384c00e"; :>> title = "Sprint 112 retro gate (autonomous, D0049)"; :>> createdAt = "2026-06-23"; :>> createdBy = "claudeOpus"; :>> method = VerificationMethod::analyze; :>> procedureText = "Autonomous retro (D0049). WELL: the finale was SMALL because every tier before it paid forward -- per-item Critique/Investigate is just /api/agent/stream pointed at the item, Issue disposition is just /api/disposition, and only Add-TestResult needed new server code (a thin /api/testresult over the same append_result the CLI uses) -- proving the dual-surface bet (D0093): one governed write path, two front-ends. The agent-never-commits boundary keeps human oversight intact while the UI gains write actions, exactly as the human framed it ('obvious hooks to overwrite/fix; don't change the permissions policy'). AVOIDABLE-ISSUE SCAN: one avoidable defect caught + fixed + logged (issue041, D0047, NOT patched silently): the orient_bdd 'unresolvable SHA' test was non-hermetic -- it wrote its fixture to the system temp dir and relied on that happening to sit inside a git repo, so on a temp-outside-git machine orient's conservative-on-git-failure SHA check returned done=1 instead of invalidEvidence; fixed by git_init-ing the fixture root so the test is deterministic (the hermetic test IS the permanent check); LESSON: tests that touch git must own their repo, never borrow ambient git state. Also re-confirmed: stop the running keel.exe before cargo build/test (it locks target/release/keel.exe). NON-blocking forward notes (NOT debt): (1) report:assurance cold ~17s still wants its own perf pass; (2) serveAgentCancel (Windows job-object process-tree kill so a stopped agent reaps its claude.exe grandchild); (3) an init-smoke CI test; (4) serve.rs is not yet in deliverable-manifest.txt. Estimate 5 pts held. The interactive console (D0094) is DONE; Keel now has a complete human cockpit over the CLI authority."; }
    part serveItemActionsRetroGateR1 : TestResult { :>> id = "63940516-2c7d-4e8f-c112-51627384c00f"; :>> outcome = VerdictKind::pass; :>> judgedAgainst = "7642f1c"; :>> judgedAt = "2026-06-23"; :>> judgedBy = "claudeOpus"; }
}
