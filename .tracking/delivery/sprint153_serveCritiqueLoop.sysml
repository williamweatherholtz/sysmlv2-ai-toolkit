// ProjectDeliveryS153 — Sprint 153: serveCritiqueLoop (verifies sr16ServeCritiqueLoop) — close the
// critique loop: ACT attaches a tracked #Resolves resolver (POST /api/resolver) so the finding ->
// disposition -> implement -> re-verify loop is tracked; re-verify = re-Critique; suspicion (D0086)
// holds until resolved. The fix itself is done by the process-aware agent / human. EXECUTE. 3 pts. AUTONOMOUS (D0049).
package ProjectDeliveryS153 {
    private import EngineElement::*;
    private import EngineWork::*;
    private import EngineVerification::*;
    private import EngineRelationships::*;

    #CharteredBy dependency from serveCritiqueLoopStory to sr16ServeCritiqueLoop;

    part serveCritiqueLoopStory : Story {
        :>> id = "63940516-2c7d-4e8f-c153-51627384c001";
        :>> title = "Sprint 153: serveCritiqueLoop (3 pts) — ACT attaches a tracked resolver; close the critique loop (verifies sr16)";
        :>> createdAt = "2026-06-24"; :>> createdBy = "wweatherholtz"; :>> kind = WorkKind::code; :>> priority = WorkPriority::p2; :>> owner = "claudeOpus"; :>> estimatedPoints = 3;
    }

    action def DeliveryRunS153 {
        action storyServeCritiqueLoop;
        verification storyServeCritiqueLoopDoD : Test { :>> id = "63940516-2c7d-4e8f-c153-51627384c002"; :>> method = VerificationMethod::test; :>> procedureText = "Satisfies sr16ServeCritiqueLoop. The record/disposition/suspicion clauses were already met (critique records Issues; Findings tab dispositions; critique_suspect D0086). NEW: the ACT->resolver->implement->re-verify loop. FIX: POST /api/resolver {finding,title} -> write::add_task (resolver `<finding>Fix` in backlog NextWork, method=inspect) + write::append_resolves_edge (#Resolves from the resolver to the finding); idempotent on re-click. Console: on an ACT disposition, prompt for the resolver description + POST /api/resolver (so ACT attaches a tracked resolver). The fix itself is performed by the PROCESS-AWARE agent (spawned in the repo cwd -> inherits CLAUDE.md/skills/guards, never auto-commits) or the human; RE-VERIFY = re-run Critique on the element (suspicion clears when clean). Decision (per human): the agent IS process+context-aware, so option-1 (tracked resolver) is sufficient — the agent implements aligned with triage. VERIFIED (live): POST /api/resolver {finding:issue046} -> {ok:true,resolver:issue046Fix}; the resolver action + #Resolves edge were written (then reverted). clippy -D warnings + cargo build + keel validate + guard all (12) green; sr16Verify (#Verify -> sr16) records it. (Built on the toggle-able bridge, sr152.)"; }
        part storyServeCritiqueLoopDoDR1 : TestResult { :>> id = "63940516-2c7d-4e8f-c153-51627384c003"; :>> outcome = VerdictKind::pass; :>> judgedAgainst = "21c7c7c"; :>> judgedAt = "2026-06-24"; :>> judgedBy = "claudeOpus"; }
    }

    verification serveCritiqueLoopRefineGate : Test { :>> id = "63940516-2c7d-4e8f-c153-51627384c004"; :>> title = "Sprint 153 refine gate (DoR)"; :>> createdAt = "2026-06-24"; :>> createdBy = "claudeOpus"; :>> method = VerificationMethod::inspect; :>> procedureText = "DoR: sr16's only unmet clause is 'ACT attaches a resolver the console can drive to implementation + re-verify'. Human chose option-1 (tracked resolver), precondition (process-aware agent) confirmed. estimatedPoints=3. #CharteredBy sr16ServeCritiqueLoop. DoR met."; }
    part serveCritiqueLoopRefineGateR1 : TestResult { :>> id = "63940516-2c7d-4e8f-c153-51627384c005"; :>> outcome = VerdictKind::pass; :>> judgedAgainst = "21c7c7c"; :>> judgedAt = "2026-06-24"; :>> judgedBy = "claudeOpus"; }
    verification serveCritiqueLoopStandupGate : Test { :>> id = "63940516-2c7d-4e8f-c153-51627384c006"; :>> title = "Sprint 153 standup gate"; :>> createdAt = "2026-06-24"; :>> createdBy = "claudeOpus"; :>> method = VerificationMethod::inspect; :>> procedureText = "Approach: append_resolves_edge helper (write.rs) + POST /api/resolver (add_task + edge) + console ACT->prompt->resolver. Re-verify = existing Critique. Test live + revert. No blockers."; }
    part serveCritiqueLoopStandupGateR1 : TestResult { :>> id = "63940516-2c7d-4e8f-c153-51627384c007"; :>> outcome = VerdictKind::pass; :>> judgedAgainst = "21c7c7c"; :>> judgedAt = "2026-06-24"; :>> judgedBy = "claudeOpus"; }
    verification serveCritiqueLoopImplementGate : Test { :>> id = "63940516-2c7d-4e8f-c153-51627384c008"; :>> title = "Sprint 153 implement gate"; :>> createdAt = "2026-06-24"; :>> createdBy = "claudeOpus"; :>> method = VerificationMethod::test; :>> procedureText = "Added write::append_resolves_edge + POST /api/resolver + console ACT-resolver prompt. VERIFIED live: POST /api/resolver {issue046} -> resolver action + #Resolves edge written (reverted); clippy + build + validate + guard 12 green."; }
    part serveCritiqueLoopImplementGateR1 : TestResult { :>> id = "63940516-2c7d-4e8f-c153-51627384c009"; :>> outcome = VerdictKind::pass; :>> judgedAgainst = "21c7c7c"; :>> judgedAt = "2026-06-24"; :>> judgedBy = "claudeOpus"; }
    verification serveCritiqueLoopReviewGate : Test { :>> id = "63940516-2c7d-4e8f-c153-51627384c00a"; :>> title = "Sprint 153 review gate"; :>> createdAt = "2026-06-24"; :>> createdBy = "claudeOpus"; :>> method = VerificationMethod::inspect; :>> procedureText = "Diff reviewed. ACT now creates a TRACKED resolver (the loop no longer falls off into a separate session untracked); the actual fix is the process-aware agent's job (option-1, per the human's process-awareness reasoning), and re-verify reuses Critique. The resolver write reuses the tested add_task + an idempotent edge writer. Honest scope: 'drive to implementation' = create+track the resolver + re-verify, not an in-console code-writer (that would be the heavier AI-implementer the human did not pick). Clean."; }
    part serveCritiqueLoopReviewGateR1 : TestResult { :>> id = "63940516-2c7d-4e8f-c153-51627384c00b"; :>> outcome = VerdictKind::pass; :>> judgedAgainst = "21c7c7c"; :>> judgedAt = "2026-06-24"; :>> judgedBy = "claudeOpus"; }
    verification serveCritiqueLoopCloseOutGate : Test { :>> id = "63940516-2c7d-4e8f-c153-51627384c00c"; :>> title = "Sprint 153 closeOut gate (autonomous, D0049)"; :>> createdAt = "2026-06-24"; :>> createdBy = "claudeOpus"; :>> method = VerificationMethod::inspect; :>> procedureText = "Autonomous closeOut (D0049): DoD pass; the critique loop closes (ACT -> tracked resolver -> implement -> re-verify). clippy + build + keel validate + guard all (12) green. Self-evidencing (D0051). sr16 verified; 4 of 5 serve SRs done (sr15/sr16/sr17 + the toggle). sr18 (section critique) + sr19 (white-box boundary) remain."; }
    part serveCritiqueLoopCloseOutGateR1 : TestResult { :>> id = "63940516-2c7d-4e8f-c153-51627384c00d"; :>> outcome = VerdictKind::pass; :>> judgedAgainst = "21c7c7c"; :>> judgedAt = "2026-06-24"; :>> judgedBy = "claudeOpus"; }
    verification serveCritiqueLoopRetroGate : Test { :>> id = "63940516-2c7d-4e8f-c153-51627384c00e"; :>> title = "Sprint 153 retro gate (autonomous, D0049)"; :>> createdAt = "2026-06-24"; :>> createdBy = "claudeOpus"; :>> method = VerificationMethod::analyze; :>> procedureText = "Autonomous retro (D0049). WELL: the loop closes WITHOUT adding an AI code-writer surface — leaning on the process-aware agent (the human's key insight) keeps the trust posture unchanged while making ACT attach a tracked resolver. Reused tested write primitives (add_task) + a tiny idempotent edge writer. AVOIDABLE-ISSUE SCAN: tested the write live against the real repo then REVERTED via git checkout (no test pollution) — the safe way to exercise a tracking-mutating endpoint. LESSON: to test an endpoint that writes tracking files, exercise it on the real repo + git-checkout-revert, or a throwaway copy — never leave test artifacts. NON-blocking: sr18 (section-local critique) + sr19 (AI white-box boundary) remain — both record findings (no new write-trust surface). Estimate 3 pts held."; }
    part serveCritiqueLoopRetroGateR1 : TestResult { :>> id = "63940516-2c7d-4e8f-c153-51627384c00f"; :>> outcome = VerdictKind::pass; :>> judgedAgainst = "21c7c7c"; :>> judgedAt = "2026-06-24"; :>> judgedBy = "claudeOpus"; }
}
