// ProjectDeliveryS358 — Sprint 358: phase-timed the composite view. The DoD's hypothesis was wrong for
// the third time, an optimisation was written and reverted on evidence. EXECUTE. 3 pts.
package ProjectDeliveryS358 {
    private import EngineElement::*;
    private import EngineWork::*;
    private import EngineVerification::*;
    private import EngineRelationships::*;

    #CharteredBy dependency from phaseTimingStory to d0129;

    part phaseTimingStory : Story {
        :>> id = "0d800610-0814-6610-9b3e-000000300610";
        :>> title = "Sprint 358: per-phase timing inside assured — the composite-reuse hypothesis refuted (3 pts)";
        :>> createdAt = "2026-08-20"; :>> createdBy = "claudeOpus5"; :>> kind = WorkKind::research; :>> priority = WorkPriority::p0; :>> owner = "claudeOpus5"; :>> estimatedPoints = 3;
    }

    action def DeliveryRunS358 {
        action storyPhaseTiming;
        verification storyPhaseTimingDoD : Test { :>> id = "0d800611-0814-6611-9b3e-000000300611"; :>> method = VerificationMethod::test; :>> procedureText = "Delivered by dcSharedParsedModel, and it REFUTES that item's own remaining question. It asked whether composite views should reuse their component results. Phase-timed inside `compute_readiness`: allGuards 4480ms, orientCompute 1508ms, grandfatherCritique 502ms, grandfatherCoverage 495ms, doneNames 290ms - and THE TWO COMPONENTS TOGETHER 19ms. Reusing them saves 19ms of about 7000. THE REAL DISTRIBUTION: `keel assured` runs the entire 37-guard suite inside a view (58%), computes ALL of orient to read one field (20%), and derives two grandfather sets from the commit graph (14%). AN OPTIMISATION WAS WRITTEN AND REVERTED: I memoized `grandfathered_under` on the sound argument that D0129 forbids rewriting history, then counted calls instead of timing them and got `grandfathered x2` - nothing to reuse. Memo deleted, counter kept, because the counter is the evidence. validate 389 clean; check-engine clean; 37 guards ALL PASS; 191 tests; clippy clean."; }
        part storyPhaseTimingDoDR1 : TestResult { :>> id = "0d800612-0814-6612-9b3e-000000300612"; :>> outcome = VerdictKind::pass; :>> judgedAgainst = "2236fd8"; :>> judgedAt = "2026-08-20"; :>> judgedBy = "claudeOpus5"; }
    }

    verification ptRefineGate : Test { :>> id = "0d800613-0814-6613-9b3e-000000300613"; :>> title = "Sprint 358 refine gate (DoR)"; :>> createdAt = "2026-08-20"; :>> createdBy = "claudeOpus5"; :>> method = VerificationMethod::inspect; :>> procedureText = "DoR. Top of the ranked frontier was dcSharedParsedModel, whose remaining question is composite-view reuse. Scoped as INSTRUMENT, not optimise - the item's premise has now been wrong twice (the model was already cached, and the git cost was my own guard rather than staleness), so measuring before believing it a third time was the whole plan. estimatedPoints=3."; }
    part ptRefineGateR1 : TestResult { :>> id = "0d800614-0814-6614-9b3e-000000300614"; :>> outcome = VerdictKind::pass; :>> judgedAgainst = "2236fd8"; :>> judgedAt = "2026-08-20"; :>> judgedBy = "claudeOpus5"; }

    verification ptStandupGate : Test { :>> id = "0d800615-0814-6615-9b3e-000000300615"; :>> title = "Sprint 358 standup gate"; :>> createdAt = "2026-08-20"; :>> createdBy = "claudeOpus5"; :>> method = VerificationMethod::inspect; :>> procedureText = "Approach: name every step inside `compute_readiness` and let the numbers decide. The prior instrumentation already showed the shape of the problem - assured runs 7-9s of which fingerprint, parse and git are only about 1.4s - so roughly 6s was in-view computation that no existing counter could attribute. A total cannot say which step to attack, which is the mistake that produced three wrong attributions earlier in this session. No blockers."; }
    part ptStandupGateR1 : TestResult { :>> id = "0d800616-0814-6616-9b3e-000000300616"; :>> outcome = VerdictKind::pass; :>> judgedAgainst = "2236fd8"; :>> judgedAt = "2026-08-20"; :>> judgedBy = "claudeOpus5"; }

    verification ptImplementGate : Test { :>> id = "0d800617-0814-6617-9b3e-000000300617"; :>> title = "Sprint 358 implement gate"; :>> createdAt = "2026-08-20"; :>> createdBy = "claudeOpus5"; :>> method = VerificationMethod::test; :>> procedureText = "`perf::phase(name, f)` accumulates named timings, reported slowest first so the thing to attack is at the top. Seven phases named inside `compute_readiness`. THE RESULT IS A REFUTATION AND THAT IS THE DELIVERABLE: computeCoverage 16ms and computeCritiqueCoverage 3ms, against allGuards 4480ms. The component views were never the cost. THE REVERTED OPTIMISATION IS THE PART I WOULD DEFEND HARDEST. I memoized `grandfathered_under` keyed by (root, decision), on the correct-by-construction argument that its answer is derived from history and D0129 forbids rewriting history. The phase timings after the change looked WORSE (4183 to 4811ms) which is pure run-to-run variance and proves nothing either way - and that ambiguity is exactly where sprint 342 landed a 31% improvement that turned out to be noise. So instead of timing it again I COUNTED: `grandfathered x2`, two calls per command, zero possible reuse. The memo was deleted. The counter survives because it is the evidence that settled it, and because a future reader considering the same optimisation should find the answer rather than repeat the work. COUNTING BEAT TIMING for the third time this session, after the git-spawn tally and the model-build tally."; }
    part ptImplementGateR1 : TestResult { :>> id = "0d800618-0814-6618-9b3e-000000300618"; :>> outcome = VerdictKind::pass; :>> judgedAgainst = "2236fd8"; :>> judgedAt = "2026-08-20"; :>> judgedBy = "claudeOpus5"; }

    verification ptReviewGate : Test { :>> id = "0d800619-0814-6619-9b3e-000000300619"; :>> title = "Sprint 358 review gate"; :>> createdAt = "2026-08-20"; :>> createdBy = "claudeOpus5"; :>> method = VerificationMethod::inspect; :>> procedureText = "Reviewed. THREE WRONG PREMISES IN ONE BACKLOG ITEM is the finding worth keeping, and all three were mine: dcSharedParsedModel claimed the parsed model was never cached (it was, forty lines above the function I was diagnosing), then that the cost was per-element git staleness (it was a guard I had shipped the day before), and now that composites recompute their components expensively (19ms). Each premise was plausible, each was written into a DoD as fact, and each would have directed the next session at the wrong target. The pattern is not carelessness about measurement - it is writing an INFERENCE into a field that reads as a finding. A DoD should say what to measure, not what the answer will be. WHAT I DID NOT DO: attack allGuards. `keel assured` running the guard suite is what makes readiness mean invariants hold, and making it cheaper by checking less would be trading a true answer for a fast one. The honest remaining levers are orient-computed-for-one-field and the two grandfather derivations, and neither is worth doing before someone says assured at 7s is a problem."; }
    part ptReviewGateR1 : TestResult { :>> id = "0d80061a-0814-661a-9b3e-00000030061a"; :>> outcome = VerdictKind::pass; :>> judgedAgainst = "2236fd8"; :>> judgedAt = "2026-08-20"; :>> judgedBy = "claudeOpus5"; }

    verification ptCloseOutGate : Test { :>> id = "0d80061b-0814-661b-9b3e-00000030061b"; :>> title = "Sprint 358 closeOut gate (autonomous, D0049)"; :>> createdAt = "2026-08-20"; :>> createdBy = "claudeOpus5"; :>> method = VerificationMethod::inspect; :>> procedureText = "Autonomous closeOut (D0049). issue167 records the refutation with its numbers and the reverted memo. NO PERFORMANCE FIX SHIPPED and that is stated rather than buried: the measurement is the deliverable, the one optimisation attempted was reverted on evidence, and the two remaining levers are named but not taken because nobody has said 7 seconds is a problem. dcSharedParsedModel stays open with its question ANSWERED - which is a different state from done, and the honest one. validate 389 clean; check-engine clean; 37 guards ALL PASS; 191 tests; clippy clean."; }
    part ptCloseOutGateR1 : TestResult { :>> id = "0d80061c-0814-661c-9b3e-00000030061c"; :>> outcome = VerdictKind::pass; :>> judgedAgainst = "2236fd8"; :>> judgedAt = "2026-08-20"; :>> judgedBy = "claudeOpus5"; }

    verification ptRetroGate : Test { :>> id = "0d80061d-0814-661d-9b3e-00000030061d"; :>> title = "Sprint 358 retro gate (autonomous, D0049)"; :>> createdAt = "2026-08-20"; :>> createdBy = "claudeOpus5"; :>> method = VerificationMethod::analyze; :>> procedureText = "Autonomous retro (D0049) under D0131's retroTrack. WELL: (1) the sprint was scoped to MEASURE rather than to optimise, because the item's premise had already been wrong twice - and it was wrong a third time, so the scoping was the whole value; (2) when the phase timings after my memo looked worse, I did not report a regression and did not report a win - I counted instead, which settled it in one number where timing never would have; (3) the memo was deleted rather than kept on a correct-by-construction argument, which is the second time this session an optimisation of mine failed to demonstrate a benefit and was reverted rather than landed; (4) the counter that refuted it survives, so the next reader tempted by the same idea finds the answer instead of repeating the work; (5) allGuards was left alone with a stated reason, rather than optimised because it was the biggest number. AVOIDABLE-ISSUE: I wrote a memo before measuring whether there was anything to memoize. The call count took one build to add and would have prevented the whole detour - the same ordering error as sprint 342, where the fix preceded the measurement. THE RULE, sharper than before: before optimising a repeated call, COUNT THE CALLS. Not time them, count them. Estimate 3 pts, delivered as a measurement and a refutation."; }
    part ptRetroGateR1 : TestResult { :>> id = "0d80061e-0814-661e-9b3e-00000030061e"; :>> outcome = VerdictKind::pass; :>> judgedAgainst = "2236fd8"; :>> judgedAt = "2026-08-20"; :>> judgedBy = "claudeOpus5"; }
}
