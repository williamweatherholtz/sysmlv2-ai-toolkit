// ProjectDeliveryS458 — Sprint 458: a skill declares its deployment beside itself, so an adopted unit lands GREEN instead of with a red gate (issue252, D0220). EXECUTE. 2 pts.
package ProjectDeliveryS458 {
    private import EngineElement::*;
    private import EngineWork::*;
    private import EngineVerification::*;
    private import EngineRelationships::*;

    #CharteredBy dependency from skillRegistersBesideItselfStory to d0220;

    part skillRegistersBesideItselfStory : Story {
        :>> id = "2bc08d97-b78b-47b6-86d4-95e910cad5a2";
        :>> title = "Sprint 458: adopting for real found what testing the export could not (2 pts)";
        :>> createdAt = "2026-08-24"; :>> createdBy = "claudeFable5"; :>> kind = WorkKind::code; :>> priority = WorkPriority::p0; :>> owner = "claudeFable5"; :>> estimatedPoints = 2;
    }

    action def DeliveryRunS458 {
        action storySkillRegistersBesideItself;
        verification storySkillRegistersBesideItselfDoD : Test { :>> id = "b831a8da-6e8e-40e7-bfc6-04ea88ed8257"; :>> method = VerificationMethod::test; :>> procedureText = "DELIVERED: dcSkillRegistersBesideItself (resolves issue252, HIGH, discoveredInField). Found by ACTUALLY adopting the decision-channel unit on asirobots/penumbra rather than testing the export in this repository. The bundle carried the process definition, the SKILL.md and the mechanism, but the entry that BINDS skill to process lives in .engine/skills/skills-registry.sysml - one shared file holding all 37 skills - and stayed home. So process-skill FAILED in penumbra on the very first run: 'process .engine/processes/decision-channel.sysml has NO deploying skill (inert process)'. A new project's first experience of an adopted unit was a red gate it could only clear by hand-editing a shared engine file, which is both a fork of the mechanism and exactly the adoption friction D0054 names as the top risk. THE FIX: a skill may declare its deployment BESIDE ITSELF in any .sysml under .engine/skills/, and BOTH readers of that declaration now scan the directory rather than the single central file - the process-skill guard and activation::deploying_skills. decisionChannelSkill is MOVED, not copied, into .engine/skills/decision-channel/registry.sysml, and unit_files carries skills/<name>/registry.sysml when present. The rules layer had already met this exact problem and solved it by carrying rules BY NAME instead of copying a shared file; skills had no equivalent, and the alternative - having import APPEND the declaration into the receiving project's shared registry - would have been a text merge into a file that project also edits, the clobber hazard the rules layer deliberately avoided. VERIFIED end to end by re-adopting: export now carries 7 files and after import penumbra reports validate 73 clean, process-skill 22 scanned / 0 violations, and [guard] ALL PASS, where the identical adoption previously left it FAILING; this repository stays green at process-skill 24/0; 256 lib tests pass; clippy clean."; }
        part storySkillRegistersBesideItselfDoDR1 : TestResult { :>> id = "58ff4d94-6b1d-45c6-88ce-4251b7033080"; :>> outcome = VerdictKind::pass; :>> judgedAgainst = "232c0cd491c0a3cb15250180df1a2c689c3c8867"; :>> judgedAt = "2026-08-24"; :>> judgedBy = "claudeFable5"; }
    }

    verification skillRegistersBesideItselfRefineGate : Test { :>> id = "eea21769-61c4-415a-8e1b-7eeb62f87be0"; :>> title = "Sprint 458 refine gate (DoR)"; :>> createdAt = "2026-08-24"; :>> createdBy = "claudeFable5"; :>> method = VerificationMethod::inspect; :>> procedureText = "DoR. Resolves issue252, raised in the field by adopting the channel on another project. Scope: make a unit able to carry its own skill registration, and prove it by re-adopting. 2 points."; }
    part skillRegistersBesideItselfRefineGateR1 : TestResult { :>> id = "a90ce45d-ed9b-424e-87da-d5a426b92ad7"; :>> outcome = VerdictKind::pass; :>> judgedAgainst = "232c0cd491c0a3cb15250180df1a2c689c3c8867"; :>> judgedAt = "2026-08-24"; :>> judgedBy = "claudeFable5"; }
    verification skillRegistersBesideItselfStandupGate : Test { :>> id = "c6aa8e1a-a05e-4f36-87f3-02eebec5fd22"; :>> title = "Sprint 458 standup gate"; :>> createdAt = "2026-08-24"; :>> createdBy = "claudeFable5"; :>> method = VerificationMethod::inspect; :>> procedureText = "Approach: widen what SATISFIES the rule rather than weaken the rule - a skill's registration sitting next to the skill is at least as discoverable as one buried in a 37-entry file, and it makes the unit self-describing, which is the property srPortModularProcessUnit actually asks for. Reject the append-into-shared-registry alternative on the clobber hazard the rules layer already priced. guards.rs is on the frozen enforcement surface, so D0220 co-commits. No blockers."; }
    part skillRegistersBesideItselfStandupGateR1 : TestResult { :>> id = "c1bf6e5f-db1b-459f-8b8b-0c37074164de"; :>> outcome = VerdictKind::pass; :>> judgedAgainst = "232c0cd491c0a3cb15250180df1a2c689c3c8867"; :>> judgedAt = "2026-08-24"; :>> judgedBy = "claudeFable5"; }
    verification skillRegistersBesideItselfImplementGate : Test { :>> id = "71a0bddd-97da-47e5-878b-931ff520eab2"; :>> title = "Sprint 458 implement gate"; :>> createdAt = "2026-08-24"; :>> createdBy = "claudeFable5"; :>> method = VerificationMethod::test; :>> procedureText = "Verified by re-running the whole adoption rather than by re-reading the code: export goes 5 -> 7 files; import into penumbra leaves it validate-clean with process-skill 22/0 and guard ALL PASS; this repo stays 24/0. cargo test --lib -> 256 passed; clippy --workspace --all-targets clean after three lint passes (a mangled char literal from a heredoc, a single-char push_str, and an orphaned doc comment)."; }
    part skillRegistersBesideItselfImplementGateR1 : TestResult { :>> id = "b07ca24f-895d-4a39-b627-ebb18c73e183"; :>> outcome = VerdictKind::pass; :>> judgedAgainst = "232c0cd491c0a3cb15250180df1a2c689c3c8867"; :>> judgedAt = "2026-08-24"; :>> judgedBy = "claudeFable5"; }
    verification skillRegistersBesideItselfReviewGate : Test { :>> id = "37e4c480-36d0-496c-bca0-1ed90864bd63"; :>> title = "Sprint 458 review gate — three passes per D0172"; :>> createdAt = "2026-08-24"; :>> createdBy = "claudeFable5"; :>> method = VerificationMethod::inspect; :>> procedureText = "PASS 1, CLAIMS: both projects' guard counts and the export file counts are quoted read-backs from the built binary, and the penumbra numbers are read AFTER the import rather than predicted. PASS 2, BOUNDARY: (i) the central registry stays valid and is still the right home for a skill with no unit of its own - this widens, it does not migrate anything else; (ii) the directory scan concatenates every .sysml under .engine/skills/, so a malformed file there degrades skill discovery for all units rather than one, which is a real coupling and is stated; (iii) only decision-channel has been moved, so the other 36 skills remain centrally declared and are unaffected. PASS 3, OWN DIFF: two defects were caught in the doing rather than assumed away, and both were mine. duplicate-identity REFUSED my first attempt because I copied the entry instead of moving it - the guard working on its author, at the point of edit. Then moving it silently dropped the export from 6 files to 5, LOSING the skill, because activation::deploying_skills also read only the central file; I found that by re-checking the export instead of trusting the success message, which is the same lesson as sprint457 one turn earlier. WHAT A REVIEWER SHOULD ATTACK: whether concatenating the whole skills directory is too blunt - a per-file parse would isolate a malformed declaration, and the current shape trades that for simplicity."; }
    part skillRegistersBesideItselfReviewGateR1 : TestResult { :>> id = "d414f7c9-7f93-4521-986a-f90b3163374c"; :>> outcome = VerdictKind::pass; :>> judgedAgainst = "232c0cd491c0a3cb15250180df1a2c689c3c8867"; :>> judgedAt = "2026-08-24"; :>> judgedBy = "claudeFable5"; }
    verification skillRegistersBesideItselfCloseOutGate : Test { :>> id = "5d2706ea-5ce7-4b0c-b3c8-03c0793b16d6"; :>> title = "Sprint 458 closeOut gate (autonomous, D0049)"; :>> createdAt = "2026-08-24"; :>> createdBy = "claudeFable5"; :>> method = VerificationMethod::inspect; :>> procedureText = "Autonomous closeOut (D0049). issue252 resolved and proven by re-adoption; penumbra now holds the channel with a green gate; this repo green. The human has since directed that the channel's bespoke scripts be folded into the binary or a process, which supersedes the current mechanism shape and is the next work - the scripts still ship as unit extras until then."; }
    part skillRegistersBesideItselfCloseOutGateR1 : TestResult { :>> id = "9b207dde-7043-45f5-9d99-342699c6382c"; :>> outcome = VerdictKind::pass; :>> judgedAgainst = "232c0cd491c0a3cb15250180df1a2c689c3c8867"; :>> judgedAt = "2026-08-24"; :>> judgedBy = "claudeFable5"; }
    verification skillRegistersBesideItselfRetroGate : Test { :>> id = "bbd01fc8-f599-4163-a3bc-c8e95f20ac54"; :>> title = "Sprint 458 retro gate (autonomous, D0049)"; :>> createdAt = "2026-08-24"; :>> createdBy = "claudeFable5"; :>> method = VerificationMethod::analyze; :>> procedureText = "Autonomous retro (D0049). AVOIDABLE-ISSUE SCAN under rcRecurrence: (1) THE lesson, and it is the same one two sprints running: a success message is not the claim. sprint457 learned that a file COUNT is not the claim when moving data; here the count itself dropped from 6 to 5 and would have gone unnoticed had I not re-listed the bundle. The durable form: after any change to what a bundle CONTAINS, re-list the bundle. (2) Adopting on a real second project found in one pass two defects that testing the export in this repository had not, across two sprints - which is direct evidence that a portability claim can only be verified by an actual adoption, and worth remembering the next time a unit is declared transferable. (3) The heredoc-escaping class recurred a fifth time; I switched to literal edits after two wasted passes. WELL: every defect this sprint was caught by a control or by re-reading a destination, none by luck. Estimate 2 pts, delivered 2."; }
    part skillRegistersBesideItselfRetroGateR1 : TestResult { :>> id = "20335813-89c3-4560-8987-51fb740f4bea"; :>> outcome = VerdictKind::pass; :>> judgedAgainst = "232c0cd491c0a3cb15250180df1a2c689c3c8867"; :>> judgedAt = "2026-08-24"; :>> judgedBy = "claudeFable5"; }
}
