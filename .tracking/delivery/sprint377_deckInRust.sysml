// ProjectDeliveryS377 — Sprint 377: the deck moves into the engine, its save loop tested end-to-end
// with httpx BEFORE deploy. Their architecture, their words. EXECUTE. 8 pts.
package ProjectDeliveryS377 {
    private import EngineElement::*;
    private import EngineWork::*;
    private import EngineVerification::*;
    private import EngineRelationships::*;

    #CharteredBy dependency from deckInRustStory to d0171;

    part deckInRustStory : Story {
        :>> id = "0d800740-0814-6740-9b3e-000000300740";
        :>> title = "Sprint 377: keel deck — built by the engine, saved through its API, tested with httpx before deploy (8 pts)";
        :>> createdAt = "2026-08-21"; :>> createdBy = "claudeOpus5"; :>> kind = WorkKind::code; :>> priority = WorkPriority::p0; :>> owner = "claudeOpus5"; :>> estimatedPoints = 8;
    }

    action def DeliveryRunS377 {
        action storyDeckInRust;
        verification storyDeckInRustDoD : Test { :>> id = "0d800741-0814-6741-9b3e-000000300741"; :>> method = VerificationMethod::test; :>> procedureText = "DELIVERED BACKLOG ITEMS: dcDeckInRust. Clears issue192 under D0171. THE ARCHITECTURE MOVED per their instruction: `keel deck` (keel-cli/src/deck.rs) generates the page from the same computed views the console reads; `keel serve` serves it at /deck; every tap saves through the server's OWN POST endpoints - findings via /api/disposition, signatures via /api/decision/accept|reject, sitting reviews via the new /api/deck/sitting, which records the HUMAN critique with its #Covers edge and REFUSES any non-Person. The artifact live-doc mechanism is a FALLBACK selected only when same-origin /api/version does not answer. TESTED BEFORE DEPLOY, their word thoroughly: unit tests at the source (the emitted script parses under node --check, no synced text writes, marker last) plus test_deck_e2e.py driving the full loop with httpx against a served COPY - 13 checks, every verdict read back from the COMPUTED VIEW, all green. THE E2E CAUGHT FOUR REAL DEFECTS PRE-DEPLOY that would each have been a round-trip through the human: missing actor binding, an actor NAME in the CriticKind enum field, a sitting critique counting for nothing without its Covers edge, naive reads inside D0167's staleness window. Advertised in the CLI per st011: the help catalogue (its coverage test enforces the line) and the serve banner. The python generator is retired - deleted, not tombstoned. validate 409 clean; check-engine clean; 38 guards ALL PASS; 209 tests; clippy clean."; }
        part storyDeckInRustDoDR1 : TestResult { :>> id = "0d800742-0814-6742-9b3e-000000300742"; :>> outcome = VerdictKind::pass; :>> judgedAgainst = "4871624"; :>> judgedAt = "2026-08-21"; :>> judgedBy = "claudeOpus5"; }
    }

    verification drRefineGate : Test { :>> id = "0d800743-0814-6743-9b3e-000000300743"; :>> title = "Sprint 377 refine gate (DoR)"; :>> createdAt = "2026-08-21"; :>> createdBy = "claudeOpus5"; :>> method = VerificationMethod::inspect; :>> procedureText = "DoR. Their question - how is this so hard - was treated as the architectural instruction it is, and issue192 answers it without flinching: the save path lived in the ONE component that cannot run locally, so five versions shipped on inference and none was testable before deploy. The route was CHANGE (the save path moves) and the triage is us016: architecture, not implementationChange. estimatedPoints=8."; }
    part drRefineGateR1 : TestResult { :>> id = "0d800744-0814-6744-9b3e-000000300744"; :>> outcome = VerdictKind::pass; :>> judgedAgainst = "4871624"; :>> judgedAt = "2026-08-21"; :>> judgedBy = "claudeOpus5"; }

    verification drStandupGate : Test { :>> id = "0d800745-0814-6745-9b3e-000000300745"; :>> title = "Sprint 377 standup gate"; :>> createdAt = "2026-08-21"; :>> createdBy = "claudeOpus5"; :>> method = VerificationMethod::inspect; :>> procedureText = "Approach: reuse, do not rebuild - the write endpoints existed and were already exercised by the console, so the deck becomes a mobile-friendly skin over a tested API rather than a new save mechanism. The one NEW endpoint (/api/deck/sitting) exists because sitting reviews had no HTTP write path, and it enforces the human gate server-side: a non-Person `by` is a 400, tested. HONEST LIMIT, stated where it belongs: on the PHONE the page cannot reach a local server, so the artifact fallback is still the mobile transport - what changed is that the page, its script, its rendering and its whole local save loop are now machine-verified, and the fallback is one small, contract-shaped function instead of the entire architecture."; }
    part drStandupGateR1 : TestResult { :>> id = "0d800746-0814-6746-9b3e-000000300746"; :>> outcome = VerdictKind::pass; :>> judgedAgainst = "4871624"; :>> judgedAt = "2026-08-21"; :>> judgedBy = "claudeOpus5"; }

    verification drImplementGate : Test { :>> id = "0d800747-0814-6747-9b3e-000000300747"; :>> title = "Sprint 377 implement gate"; :>> createdAt = "2026-08-21"; :>> createdBy = "claudeOpus5"; :>> method = VerificationMethod::test; :>> procedureText = "THE E2E EARNED ITS EXISTENCE IN ITS FIRST RUN: four failures, four real defects, zero of them findable by reading. (1) The copy tree had no actor binding, so dispositions refused - the test now supplies KEEL_ACTOR the way a real session does. (2) I wrote the reviewer's NAME into critiqued_by, which is the CriticKind ENUM - validate rejected the tree the endpoint had written, which is the honest-state gate doing its job against the sanctioned write path. (3) The sitting critique counted for NOTHING: sitting-coverage computes over #Covers edges, and the endpoint now authors the edge and reports a partial write rather than leaving a critique that silently covers nothing. (4) Naive read-after-write landed in D0167's stale window; the test polls, which is the honest read. TWO MORE OWN-GOALS: wire_deck.py aborted before writing main.rs, so the catalogue advertised `keel deck` while nothing dispatched it - caught by RUNNING the command rather than trusting the patch, and the coverage control's inverse blind spot (documented-implies-dispatched) is noted in issue192. And three format! strings shipped with unescaped inner quotes through a python triple-quote - the compiler caught all three."; }
    part drImplementGateR1 : TestResult { :>> id = "0d800748-0814-6748-9b3e-000000300748"; :>> outcome = VerdictKind::pass; :>> judgedAgainst = "4871624"; :>> judgedAt = "2026-08-21"; :>> judgedBy = "claudeOpus5"; }

    verification drReviewGate : Test { :>> id = "0d800749-0814-6749-9b3e-000000300749"; :>> title = "Sprint 377 review gate — three passes per D0172"; :>> createdAt = "2026-08-21"; :>> createdBy = "claudeOpus5"; :>> method = VerificationMethod::inspect; :>> procedureText = "PASS 1, CLAIMS vs computed/emitted: 13 e2e checks green over real HTTP including view read-backs; 209 unit tests; node --check green at the source AND on the served page; clippy zero; 38 guards - all from runs. PASS 2, BOUNDARY: the human gate probed with an AI actor (400), a non-Person string (400), the empty-note path, and the staleness window; the e2e runs on a COPY per the standing rule for probes that write. PASS 3, THE SPRINT'S OWN DIFF: found the advertised-but-not-dispatched command (my own patch aborting mid-file) and the enum-field misuse - both mine, both caught by executing rather than reading. WHAT A REVIEWER SHOULD ATTACK: the artifact fallback path is still not machine-testable - it is now ~20 lines shaped exactly like the contract's documented pattern, but the five failed versions were also shaped like my reading of the contract. The difference this time is scope: if the fallback fails, everything else still works locally, and the debug log runs because the script provably parses."; }
    part drReviewGateR1 : TestResult { :>> id = "0d80074a-0814-674a-9b3e-00000030074a"; :>> outcome = VerdictKind::pass; :>> judgedAgainst = "4871624"; :>> judgedAt = "2026-08-21"; :>> judgedBy = "claudeOpus5"; }

    verification drCloseOutGate : Test { :>> id = "0d80074b-0814-674b-9b3e-00000030074b"; :>> title = "Sprint 377 closeOut gate (autonomous, D0049)"; :>> createdAt = "2026-08-21"; :>> createdBy = "claudeOpus5"; :>> method = VerificationMethod::inspect; :>> procedureText = "Autonomous closeOut (D0049). issue192 cleared by dcDeckInRust; the obligation-review process and skill registry updated to name the Rust generator and the e2e; the python generator DELETED per the doc-removal rule; /deck advertised in the help catalogue and the serve banner (st011). The artifact republishes from `keel deck --out` output. validate 409 clean; check-engine clean; 38 guards ALL PASS; 209 tests; clippy clean."; }
    part drCloseOutGateR1 : TestResult { :>> id = "0d80074c-0814-674c-9b3e-00000030074c"; :>> outcome = VerdictKind::pass; :>> judgedAgainst = "4871624"; :>> judgedAt = "2026-08-21"; :>> judgedBy = "claudeOpus5"; }

    verification drRetroGate : Test { :>> id = "0d80074d-0814-674d-9b3e-00000030074d"; :>> title = "Sprint 377 retro gate (autonomous, D0049)"; :>> createdAt = "2026-08-21"; :>> createdBy = "claudeOpus5"; :>> method = VerificationMethod::analyze; :>> procedureText = "Autonomous retro (D0049). AVOIDABLE-ISSUE SCAN under rcRecurrence: (1) the aborted patch that left main.rs unwritten while its later sibling patched the catalogue is occurrence FIVE of the anchor-edit class - dcAuthorViaWriteTool's rule gains its final clause: a multi-step patch VERIFIES EACH STEP BY RUNNING THE RESULT, not by reading the patch's own success prints, which is exactly how the un-dispatched command was caught; (2) unescaped quotes through a python triple-quote into Rust format! is the shell-mangling family, occurrence NINE, same disposition - compiler-caught, no new item. WELL: (1) their architectural instruction was implemented as architecture, not as a sixth patch to the old one; (2) the e2e found four real defects at a cost of one local test run each, against the previous cost of one HUMAN round-trip each - the arithmetic that justifies the whole move; (3) the endpoint enforces the human gate SERVER-SIDE and the refusal is a tested behaviour, not a comment; (4) the fallback's honest limit is stated in the standup gate rather than discovered later. THE SERIES LESSON, now structural: testability is not a property you add to a design - it is a property of WHERE THE CRITICAL PATH LIVES, and their one-line question relocated it better than five of my fixes. Estimate 8 pts, delivered."; }
    part drRetroGateR1 : TestResult { :>> id = "0d80074e-0814-674e-9b3e-00000030074e"; :>> outcome = VerdictKind::pass; :>> judgedAgainst = "4871624"; :>> judgedAt = "2026-08-21"; :>> judgedBy = "claudeOpus5"; }
}
