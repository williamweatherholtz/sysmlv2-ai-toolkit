// ProjectDeliveryS142 — Sprint 142: introductionDryRun (D0093) — walked the `introduction` onboarding
// skill end-to-end on a fresh `keel init` project. Found + FIXED two real onboarding gaps: (1) the
// tracking-template had duplicate :>> id lines on 3 example items (a newcomer copying them would author
// malformed items); (2) a fresh scaffold shipped NO .tracking/actors.sysml, so the newcomer's FIRST
// recorded fact failed the actors guard (D0037). Verified the init->author->close->orient loop works on
// a fresh project. 3 pts. AUTONOMOUS (D0049).
package ProjectDeliveryS142 {
    private import EngineElement::*;
    private import EngineWork::*;
    private import EngineVerification::*;
    private import EngineRelationships::*;

    #CharteredBy dependency from introductionDryRunStory to d0093;

    part introductionDryRunStory : Story {
        :>> id = "63940516-2c7d-4e8f-c142-51627384c001";
        :>> title = "Sprint 142: introductionDryRun (3 pts) — onboarding dry-run; fix template dup-ids + ship a starter actors registry (D0093)";
        :>> createdAt = "2026-06-23"; :>> createdBy = "wweatherholtz"; :>> kind = WorkKind::code; :>> priority = WorkPriority::p2; :>> owner = "claudeOpus"; :>> estimatedPoints = 3;
    }

    action def DeliveryRunS142 {
        action storyIntroductionDryRun;
        verification storyIntroductionDryRunDoD : Test { :>> id = "63940516-2c7d-4e8f-c142-51627384c002"; :>> method = VerificationMethod::demo; :>> procedureText = "D0093 first-value UX: walked the `introduction` skill's 5 steps on a fresh `keel init` project (init_smoke proves init+validate+guard, not the onboarding flow). FINDINGS + FIXES: (1) .engine/docs/tracking-template.sysml — the canonical authoring template a newcomer copies — had DUPLICATE `:>> id` lines on 3 example items (exampleBrief/exampleNeed/exampleDecision, a migration leftover); removed the stale first id of each (kept the placeholder 3f1c9a2e-* ids). (2) a fresh scaffold shipped NO .tracking/actors.sysml, so the newcomer's FIRST recorded fact (any createdBy/judgedBy) FAILED the actors guard (D0037) with 'unknown actor' — there was nothing to reference; added STARTER_ACTORS (a `you : Person` + `ai : Actor` placeholder registry) written by cmd_init, and init_smoke asserts it ships. VERIFIED the loop on a fresh project: authored a backlog action def + task -> orient (1 ready) -> append-result (write API) -> orient (1 done); after the actors fix, judgedBy=ai PASSES guard actors. CONFIRMED the skill's step 4 (full sprint ceremony) is load-bearing — closing a task without a delivery sprint trips sprint-coverage (by design, D0064). VERIFY: clippy --workspace --all-targets -D warnings green; cargo test 48 lib + init_smoke (+ the new actors assertion) + BDD pass; repo keel validate 155 + guard all (13) green; the kernel validate_instances re-checks the corrected template in pre-commit."; }
        part storyIntroductionDryRunDoDR1 : TestResult { :>> id = "63940516-2c7d-4e8f-c142-51627384c003"; :>> outcome = VerdictKind::pass; :>> judgedAgainst = "7bd115f"; :>> judgedAt = "2026-06-23"; :>> judgedBy = "claudeOpus"; }
    }

    verification introductionDryRunRefineGate : Test { :>> id = "63940516-2c7d-4e8f-c142-51627384c004"; :>> title = "Sprint 142 refine gate (DoR)"; :>> createdAt = "2026-06-23"; :>> createdBy = "claudeOpus"; :>> method = VerificationMethod::inspect; :>> procedureText = "DoR: deployment-readiness #6. init_smoke proves init mechanics, not onboarding UX; walk the introduction skill as a newcomer + fix friction. Resolver: introductionDryRun. estimatedPoints=3. #CharteredBy d0093. DoD accepted."; }
    part introductionDryRunRefineGateR1 : TestResult { :>> id = "63940516-2c7d-4e8f-c142-51627384c005"; :>> outcome = VerdictKind::pass; :>> judgedAgainst = "7bd115f"; :>> judgedAt = "2026-06-23"; :>> judgedBy = "claudeOpus"; }
    verification introductionDryRunStandupGate : Test { :>> id = "63940516-2c7d-4e8f-c142-51627384c006"; :>> title = "Sprint 142 standup gate"; :>> createdAt = "2026-06-23"; :>> createdBy = "claudeOpus"; :>> method = VerificationMethod::inspect; :>> procedureText = "Approach: keel init a fresh project; follow the 5 steps; for each friction point, fix at the source (template / scaffold) + regression-guard in init_smoke. Verify the loop closes + actors guard passes a newcomer's first fact. No blockers."; }
    part introductionDryRunStandupGateR1 : TestResult { :>> id = "63940516-2c7d-4e8f-c142-51627384c007"; :>> outcome = VerdictKind::pass; :>> judgedAgainst = "7bd115f"; :>> judgedAt = "2026-06-23"; :>> judgedBy = "claudeOpus"; }
    verification introductionDryRunImplementGate : Test { :>> id = "63940516-2c7d-4e8f-c142-51627384c008"; :>> title = "Sprint 142 implement gate"; :>> createdAt = "2026-06-23"; :>> createdBy = "claudeOpus"; :>> method = VerificationMethod::demo; :>> procedureText = "Fixed template dup-ids (3 items) + added STARTER_ACTORS scaffolding + init_smoke actors assertion. VERIFIED (live): fresh init ships actors.sysml; newcomer's append-result(judgedBy=ai) -> guard actors PASS; orient computes 1 ready -> 1 done. clippy green (fixed: ProjectActors doc backticks); cargo test 48 lib + init_smoke pass; repo validate 155 + guard all (13) PASS."; }
    part introductionDryRunImplementGateR1 : TestResult { :>> id = "63940516-2c7d-4e8f-c142-51627384c009"; :>> outcome = VerdictKind::pass; :>> judgedAgainst = "7bd115f"; :>> judgedAt = "2026-06-23"; :>> judgedBy = "claudeOpus"; }
    verification introductionDryRunReviewGate : Test { :>> id = "63940516-2c7d-4e8f-c142-51627384c00a"; :>> title = "Sprint 142 review gate"; :>> createdAt = "2026-06-23"; :>> createdBy = "claudeOpus"; :>> method = VerificationMethod::inspect; :>> procedureText = "Diff reviewed. The dry-run earned its keep: a passive read of the skill would have missed BOTH gaps — the duplicate-id template (a copy-paste trap) and the missing actors registry (a hard blocker: a newcomer literally could not record a guard-passing fact day one). Both fixed at the source + regression-guarded in init_smoke. The init->author->close->orient loop is verified on a fresh instance, and the skill's full-ceremony step is confirmed load-bearing. Clean."; }
    part introductionDryRunReviewGateR1 : TestResult { :>> id = "63940516-2c7d-4e8f-c142-51627384c00b"; :>> outcome = VerdictKind::pass; :>> judgedAgainst = "7bd115f"; :>> judgedAt = "2026-06-23"; :>> judgedBy = "claudeOpus"; }
    verification introductionDryRunCloseOutGate : Test { :>> id = "63940516-2c7d-4e8f-c142-51627384c00c"; :>> title = "Sprint 142 closeOut gate (autonomous, D0049)"; :>> createdAt = "2026-06-23"; :>> createdBy = "claudeOpus"; :>> method = VerificationMethod::inspect; :>> procedureText = "Autonomous closeOut (D0049): DoD pass; 2 onboarding gaps fixed + guarded; the fresh-project loop verified. clippy + cargo test + keel validate 155 + guard all (13) green. Self-evidencing (D0051). Deployment-readiness 7/8 done (of the 4 internal: only serveDownstreamDegrade remains)."; }
    part introductionDryRunCloseOutGateR1 : TestResult { :>> id = "63940516-2c7d-4e8f-c142-51627384c00d"; :>> outcome = VerdictKind::pass; :>> judgedAgainst = "7bd115f"; :>> judgedAt = "2026-06-23"; :>> judgedBy = "claudeOpus"; }
    verification introductionDryRunRetroGate : Test { :>> id = "63940516-2c7d-4e8f-c142-51627384c00e"; :>> title = "Sprint 142 retro gate (autonomous, D0049)"; :>> createdAt = "2026-06-23"; :>> createdBy = "claudeOpus"; :>> method = VerificationMethod::analyze; :>> procedureText = "Autonomous retro (D0049). WELL: actually WALKING the onboarding (not just reading the skill) surfaced two real gaps a static review misses — the duplicate-id template trap (latent since the id migration) and the missing actors registry (a hard day-one blocker). Both fixed at the source + regression-guarded in init_smoke so they can't recur. AVOIDABLE-ISSUE SCAN: the template dup-ids were a #ProcessDefect-class migration leftover (the attrModel/id migration added new ids without removing the originals) — now guarded by the kernel validate_instances + the fix; the missing-actors gap is guarded by the new init_smoke assertion. LESSON: a scaffold must let the newcomer pass EVERY guard on their first real fact — actors registry is a day-one prerequisite, not optional. NON-blocking: serveDownstreamDegrade is the last internal task; releaseWorkflow + releaseTag010 await the human's ship decision. Estimate 3 pts held."; }
    part introductionDryRunRetroGateR1 : TestResult { :>> id = "63940516-2c7d-4e8f-c142-51627384c00f"; :>> outcome = VerdictKind::pass; :>> judgedAgainst = "7bd115f"; :>> judgedAt = "2026-06-23"; :>> judgedBy = "claudeOpus"; }
}
