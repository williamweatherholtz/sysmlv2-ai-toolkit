// ProjectDeliveryS276 — Sprint 276: an assumption is COMPUTED, not authored (issue105). Corrects my
// "genuine loss" claim in D0142's rationale. EXECUTE. 2 pts.
package ProjectDeliveryS276 {
    private import EngineElement::*;
    private import EngineWork::*;
    private import EngineVerification::*;
    private import EngineRelationships::*;

    #CharteredBy dependency from assumptionsStory to d0142;

    part assumptionsStory : Story {
        :>> id = "0d8000ec-0814-60ec-9b3e-0000003000ec";
        :>> title = "Sprint 276: keel assumptions — the class the deleted type only labelled (2 pts)";
        :>> createdAt = "2026-08-14"; :>> createdBy = "claudeOpus5"; :>> kind = WorkKind::code; :>> priority = WorkPriority::p1; :>> owner = "claudeOpus5"; :>> estimatedPoints = 2;
    }

    action def DeliveryRunS276 {
        action storyAssumptions;
        verification storyAssumptionsDoD : Test { :>> id = "0d8000ed-0814-60ed-9b3e-0000003000ed"; :>> method = VerificationMethod::test; :>> procedureText = "Covers dcAssumptionsView (issue105). D0142's rationale called the deleted `Assumption` type 'the one genuine loss'. The human corrected it: an accepted unverified requirement with downstream non-verification dependencies IS an assumption, so the class is COMPUTABLE, and CLAUDE.md §1.1 is explicit that anything regenerable from authored facts is a VIEW rather than a type. The behaviour the type was justified by — downstream suspicion when an assumption breaks — already exists per relationships.sysml:29-31 and worked the entire time the type sat at zero instances, which is itself the evidence the type never delivered it. DELIVERED: `keel assumptions`, computing unverified-AND-depended-upon over Need / SystemRequirement / SubsystemRequirement / Decision. Verification edges are excluded from the dependency test on purpose: a Test pointing at a requirement DISCHARGES the assumption rather than resting on it, so counting it would make every verified requirement look like one. VERIFIED BOTH DIRECTIONS: reports 73; the verified Need `n01AtomicItems` is correctly ABSENT; every listed item carries at least one dependent; the represented types are Decision, Need and SystemRequirement. clippy clean; 161 tests; validate + all 28 guards + check-engine green."; }
        part storyAssumptionsDoDR1 : TestResult { :>> id = "0d8000ee-0814-60ee-9b3e-0000003000ee"; :>> outcome = VerdictKind::pass; :>> judgedAgainst = "79e7b06"; :>> judgedAt = "2026-08-14"; :>> judgedBy = "claudeOpus5"; }
    }

    verification asRefineGate : Test { :>> id = "0d8000ef-0814-60ef-9b3e-0000003000ef"; :>> title = "Sprint 276 refine gate (DoR)"; :>> createdAt = "2026-08-14"; :>> createdBy = "claudeOpus5"; :>> method = VerificationMethod::inspect; :>> procedureText = "DoR: the human challenged a claim I made in an accepted Decision's rationale and was right. The correct response is not to re-add the type but to deliver the computation that shows why the type was never needed — and to record the correction so the Decision's rationale is not left standing unchallenged. estimatedPoints=2. DoR met."; }
    part asRefineGateR1 : TestResult { :>> id = "0d8000f0-0814-60f0-9b3e-0000003000f0"; :>> outcome = VerdictKind::pass; :>> judgedAgainst = "79e7b06"; :>> judgedAt = "2026-08-14"; :>> judgedBy = "claudeOpus5"; }

    verification asStandupGate : Test { :>> id = "0d8000f1-0814-60f1-9b3e-0000003000f1"; :>> title = "Sprint 276 standup gate"; :>> createdAt = "2026-08-14"; :>> createdBy = "claudeOpus5"; :>> method = VerificationMethod::inspect; :>> procedureText = "Approach: check the claim before implementing — confirm the edge kinds needed actually exist in the model and that no equivalent lens already exists. Both confirmed. Then test the NEGATIVE direction, since a lens that lists everything would look plausible and be useless. No blockers."; }
    part asStandupGateR1 : TestResult { :>> id = "0d8000f2-0814-60f2-9b3e-0000003000f2"; :>> outcome = VerdictKind::pass; :>> judgedAgainst = "79e7b06"; :>> judgedAt = "2026-08-14"; :>> judgedBy = "claudeOpus5"; }

    verification asImplementGate : Test { :>> id = "0d8000f3-0814-60f3-9b3e-0000003000f3"; :>> title = "Sprint 276 implement gate"; :>> createdAt = "2026-08-14"; :>> createdBy = "claudeOpus5"; :>> method = VerificationMethod::test; :>> procedureText = "Two scoping decisions. (1) `Story` is excluded: its discharge is a DoD TestResult, not a `#Verify` edge, so including it would report the entire backlog as assumptions and the lens would be ignored within a day. (2) An unverified item with NO dependents is excluded — that is merely unverified, which `tier-satisfaction` already reports. An assumption is specifically something OTHER WORK RESTS ON, which is what makes it worth naming."; }
    part asImplementGateR1 : TestResult { :>> id = "0d8000f4-0814-60f4-9b3e-0000003000f4"; :>> outcome = VerdictKind::pass; :>> judgedAgainst = "79e7b06"; :>> judgedAt = "2026-08-14"; :>> judgedBy = "claudeOpus5"; }

    verification asReviewGate : Test { :>> id = "0d8000f5-0814-60f5-9b3e-0000003000f5"; :>> title = "Sprint 276 review gate"; :>> createdAt = "2026-08-14"; :>> createdBy = "claudeOpus5"; :>> method = VerificationMethod::inspect; :>> procedureText = "Reviewed. The transferable lesson is sharper than the feature: when a schema comment argues a type is 'first-class because <behaviour>', the question is whether the BEHAVIOUR exists without the type. Here it did, for a year, while the type had zero instances — and the zero-instance count was itself the evidence, which I had in hand and read as a reason to mourn the type rather than as a reason to doubt the argument for it."; }
    part asReviewGateR1 : TestResult { :>> id = "0d8000f6-0814-60f6-9b3e-0000003000f6"; :>> outcome = VerdictKind::pass; :>> judgedAgainst = "79e7b06"; :>> judgedAt = "2026-08-14"; :>> judgedBy = "claudeOpus5"; }

    verification asCloseOutGate : Test { :>> id = "0d8000f7-0814-60f7-9b3e-0000003000f7"; :>> title = "Sprint 276 closeOut gate (autonomous, D0049)"; :>> createdAt = "2026-08-14"; :>> createdBy = "claudeOpus5"; :>> method = VerificationMethod::inspect; :>> procedureText = "Autonomous closeOut (D0049). dcAssumptionsView carries a passing DoD TestResult; issue105 resolves and records the correction to D0142's rationale, which is left standing as written since an accepted Decision is a record rather than a living document. clippy clean; 161 tests; validate + all 28 guards + check-engine green. No gate bypassed."; }
    part asCloseOutGateR1 : TestResult { :>> id = "0d8000f8-0814-60f8-9b3e-0000003000f8"; :>> outcome = VerdictKind::pass; :>> judgedAgainst = "79e7b06"; :>> judgedAt = "2026-08-14"; :>> judgedBy = "claudeOpus5"; }

    verification asRetroGate : Test { :>> id = "0d8000f9-0814-60f9-9b3e-0000003000f9"; :>> title = "Sprint 276 retro gate (autonomous, D0049)"; :>> createdAt = "2026-08-14"; :>> createdBy = "claudeOpus5"; :>> method = VerificationMethod::analyze; :>> procedureText = "Autonomous retro (D0049) under D0131's retroTrack. WELL: (1) the correction was implemented as a COMPUTATION rather than argued in prose, so the claim 'this class is computable' is now demonstrated by 73 results rather than asserted; (2) the negative direction was tested — a verified Need is absent — which is the only check that distinguishes a working lens from one that lists everything; (3) the two exclusions (Story, no-dependents) were reasoned from what would make the lens ignored rather than from what was easiest. AVOIDABLE-ISSUE 1: I accepted a schema comment's argument for the `Assumption` type at face value while holding the measurement that refuted it — zero instances in a year. The type's own justification described a behaviour that suspicion already provided, and the empty instance count was the evidence. NO NEW ITEM, reason stated: this is the read-the-evidence-you-already-have failure, the same shape as trusting a subagent's claim in sprint 268 and the prose-inflated census in sprint 275; it is behavioural rather than gate-able, and the general form is now recorded in issue105 where the next reader of that schema comment will meet it. Estimate 2 pts, delivered."; }
    part asRetroGateR1 : TestResult { :>> id = "0d8000fa-0814-60fa-9b3e-0000003000fa"; :>> outcome = VerdictKind::pass; :>> judgedAgainst = "79e7b06"; :>> judgedAt = "2026-08-14"; :>> judgedBy = "claudeOpus5"; }
}
