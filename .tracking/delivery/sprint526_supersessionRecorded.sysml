// ProjectDeliveryS526 — Sprint 526: the supersession is recorded, and withdrawal is a Decision. RECORD + CHANGE. 1 pt.
package ProjectDeliveryS526 {
    private import EngineElement::*;
    private import EngineWork::*;
    private import EngineVerification::*;
    private import EngineRelationships::*;

    #CharteredBy dependency from supersessionRecordedStory to d0290;

    part supersessionRecordedStory : Story {
        :>> id = "fe771092-7dbe-49be-8b3c-c8ed47331dbc";
        :>> title = "Sprint 526: D0289 carries its supersede edge to D0178 layer 3 and the human's word as receipt; withdrawal is a superseding Decision, not a deleted line (1 pt)";
        :>> createdAt = "2026-09-03"; :>> createdBy = "claudeOpus5"; :>> kind = WorkKind::modeling; :>> priority = WorkPriority::p0; :>> owner = "claudeOpus5"; :>> estimatedPoints = 1;
    }

    action def DeliveryRunS526 {
        action storySupersessionRecorded;
        verification storySupersessionRecordedDoD : Test { :>> id = "df879109-40b2-402d-ab07-696e62dc2778"; :>> method = VerificationMethod::test; :>> procedureText = "DELIVERED BACKLOG ITEMS: dcSupersessionIsRecorded. The human asked whether D0289 had to be superseded to be ineffective going forward - yes - and gave the authoritative word (st075) naming what it supersedes. DONE: d0289AcceptAttest1 quotes them verbatim, so the acceptance is theirs and the supersession is scoped to D0178 layer 3; the edges D0289 lacked - #Supersede d0178, dependency d0192, #DerivedFrom us076; the policy contract's four TO WITHDRAW comments now say withdrawal is a Decision that #Supersedes the grant with the line deleted in the same commit (D0290). VERIFY: keel show why d0289 reads the edges back; guards pass under D0290's marker."; }
        // RAN: keel show why d0289 -> d0289 ->supersede d0178, d0289 ->dependency d0192; keel validate 603 clean; keel guard . ALL PASS; keel show trace d0289 empty for every Decision (GitHub #34, open, pre-existing)
        part storySupersessionRecordedDoDR1 : TestResult { :>> id = "0019aa7f-0b73-4f3d-917a-2a9e3b40f8d3"; :>> outcome = VerdictKind::pass; :>> judgedAgainst = "f72aef4"; :>> judgedAt = "2026-09-03"; :>> judgedBy = "claudeOpus5"; }
    }

    verification supersessionRecordedRefineGate : Test { :>> id = "45219552-cdd2-47b8-9369-4240aa30d872"; :>> title = "Sprint 526 refine gate (DoR)"; :>> createdAt = "2026-09-03"; :>> createdBy = "claudeOpus5"; :>> method = VerificationMethod::inspect; :>> procedureText = "READY when the human's question was checked against the tree: D0289 had no edges at all, and the policy's withdrawal comments described the mechanism as the record. The human then supplied the one thing I could not - the authoritative word - after being told exactly which Decision and which layer."; }
    verification supersessionRecordedStandupGate : Test { :>> id = "d2ed2058-b0a7-49d8-8606-6a2292395797"; :>> title = "Sprint 526 standup gate"; :>> createdAt = "2026-09-03"; :>> createdBy = "claudeOpus5"; :>> method = VerificationMethod::inspect; :>> procedureText = "ONE CHOICE: the edges and receipt were appended to D0289's own file rather than a new one - additive statements under D0108, touching none of the accepted text - because an edge declared in a different file is legal SysML and bad navigation. The scope 'layer 3 only' lives in the receipt text because the schema has no clause-level edge (issue331/issue336)."; }
    verification supersessionRecordedImplementGate : Test { :>> id = "088752b1-7056-497d-b761-8fa2f5606b48"; :>> title = "Sprint 526 implement gate"; :>> createdAt = "2026-09-03"; :>> createdBy = "claudeOpus5"; :>> method = VerificationMethod::test; :>> procedureText = "RAN: the receipt and three edges appended; validate clean; keel show why d0289 read both edges back. keel show trace d0289 returned nothing - and so did trace d0149, which has carried Supersede edges for weeks - so that is GitHub #34, not this change, and the receipt says so rather than claiming trace as evidence."; }
    verification supersessionRecordedReviewGate : Test { :>> id = "e6f5c127-e0c9-4125-9c27-acfe2a98f851"; :>> title = "Sprint 526 review gate — three passes per D0172"; :>> createdAt = "2026-09-03"; :>> createdBy = "claudeOpus5"; :>> method = VerificationMethod::inspect; :>> procedureText = "THREE PASSES. (1) IS THE QUOTE EXACT: copied from the message, compared character by character against st075. (2) IS THE SCOPE HONEST: the edge says d0289 supersedes d0178; the receipt says layer 3 only and that layers 1 and 2 stand - a reader following the edge reaches the receipt in the same file. (3) DOES THE RULE APPLY TO ITSELF: D0290's removal path is a superseding Decision plus the comments rewritten."; }
    verification supersessionRecordedCloseOutGate : Test { :>> id = "e88f2ae3-ab68-4e6d-82e9-a3d0682e4c25"; :>> title = "Sprint 526 closeOut gate (autonomous, D0049)"; :>> createdAt = "2026-09-03"; :>> createdBy = "claudeOpus5"; :>> method = VerificationMethod::inspect; :>> procedureText = "CLOSED. What is in force is now computable: D0178 layer 3 is superseded by D0289 on the human's word; every delegation in the policy names how it ends."; }
    verification supersessionRecordedRetroGate : Test { :>> id = "6b8e39b9-6692-4db3-96e5-f4ed126ae970"; :>> title = "Sprint 526 retro gate (autonomous, D0049)"; :>> createdAt = "2026-09-03"; :>> createdBy = "claudeOpus5"; :>> method = VerificationMethod::analyze; :>> procedureText = "no new item - already tracked: two findings, both already carried. A Decision that changes another's clause landed with no edge because record decision --from has no field for what it supersedes - the human noticed, not a guard; decision-requirement-link warns when prose names an item without an edge, and would have here had D0289's text named d0178 by id. That gap belongs to dcProcessStepsBindToChecks' clause-addressability half (issue336). And trace reading no marker edges is GitHub #34, open."; }
}
