// ProjectDeliveryS329 — Sprint 329: critique pass 5 — the five encoding SystemRequirements. EXECUTE. 3 pts.
package ProjectDeliveryS329 {
    private import EngineElement::*;
    private import EngineWork::*;
    private import EngineVerification::*;
    private import EngineRelationships::*;

    #CharteredBy dependency from critPass5Story to d0080;

    part critPass5Story : Story {
        :>> id = "0d800440-0814-6440-9b3e-000000300440";
        :>> title = "Sprint 329: critique pass 5 — 5 encoding SRs x Core-3, 11 fail / 4 pass (3 pts)";
        :>> createdAt = "2026-08-17"; :>> createdBy = "claudeOpus5"; :>> kind = WorkKind::modeling; :>> priority = WorkPriority::p0; :>> owner = "claudeOpus5"; :>> estimatedPoints = 3;
    }

    action def DeliveryRunS329 {
        action storyCritPass5;
        verification storyCritPass5DoD : Test { :>> id = "0d800441-0814-6441-9b3e-000000300441"; :>> method = VerificationMethod::analyze; :>> procedureText = "Pass 5, the first SystemRequirement pass: srEncodingModular, srEncodingOverride, srEncodingRender, srEncodingSchemaSemantics, srEncodingSpec — all wweatherholtz-authored, all derived from N-18. 11 fail, 4 pass. THE FINDING WITH THE MOST TEETH IS GROUNDED IN THE IMPLEMENTATION: srEncodingSchemaSemantics specifies the kind vocabulary as enum, numeric, temporal, categorical, and view::stat_kind maps the DECLARED type with everything not enum/Integer/Real/Timestamp falling through to categorical — so `title`, free text with hundreds of distinct values, and `owner`, with about eight, both report categorical, and an auto-encoder told to colour a categorical attribute would attempt a palette over several hundred titles. That is the requirement's defect, not the implementation's: it chose the vocabulary. SECOND: 'observed distinct values (capped)' names no cap, so the threshold lives only in the code it governs (64, in attribute_stats) and a test can only assert the number the code chose. THIRD, and this is sprint 328's prediction coming true: srEncodingSpec's 'sensible defaults per kind' INHERITS N-18's unverifiable 'semantically enough' clause — the concrete cost of an unfalsifiable clause in an accepted Need is that it does not stay in the Need. READ BACK: SystemRequirement coverage 5 -> 10 of 72. validate 357 clean; 35 guards ALL PASS."; }
        part storyCritPass5DoDR1 : TestResult { :>> id = "0d800442-0814-6442-9b3e-000000300442"; :>> outcome = VerdictKind::pass; :>> judgedAgainst = "41a237f"; :>> judgedAt = "2026-08-17"; :>> judgedBy = "claudeOpus5"; }
    }

    verification c5RefineGate : Test { :>> id = "0d800443-0814-6443-9b3e-000000300443"; :>> title = "Sprint 329 refine gate (DoR)"; :>> createdAt = "2026-08-17"; :>> createdBy = "claudeOpus5"; :>> method = VerificationMethod::inspect; :>> procedureText = "DoR. These are the five SRs sprint 328 deferred when checking their parent Need turned into a defect hunt. Before writing, I verified what the engine already does rather than assuming these were unbuilt: /api/schema exists and is routed, view::schema_json composes declared types and enums with attribute_stats, and attribute_stats already computes kind, capped distinct values with a truncated flag, and numeric and string min/max. So srEncodingSchemaSemantics is substantially IMPLEMENTED, which changes the critique from what is missing in delivery to what is wrong in the requirement. estimatedPoints=3."; }
    part c5RefineGateR1 : TestResult { :>> id = "0d800444-0814-6444-9b3e-000000300444"; :>> outcome = VerdictKind::pass; :>> judgedAgainst = "41a237f"; :>> judgedAt = "2026-08-17"; :>> judgedBy = "claudeOpus5"; }

    verification c5StandupGate : Test { :>> id = "0d800445-0814-6445-9b3e-000000300445"; :>> title = "Sprint 329 standup gate"; :>> createdAt = "2026-08-17"; :>> createdBy = "claudeOpus5"; :>> method = VerificationMethod::inspect; :>> procedureText = "Approach: read the IMPLEMENTATION before critiquing a requirement that may already be met, so a finding is about the words rather than about a gap that does not exist; keep every factual claim traceable to a named function or file. No blockers."; }
    part c5StandupGateR1 : TestResult { :>> id = "0d800446-0814-6446-9b3e-000000300446"; :>> outcome = VerdictKind::pass; :>> judgedAgainst = "41a237f"; :>> judgedAt = "2026-08-17"; :>> judgedBy = "claudeOpus5"; }

    verification c5ImplementGate : Test { :>> id = "0d800447-0814-6447-9b3e-000000300447"; :>> title = "Sprint 329 implement gate"; :>> createdAt = "2026-08-17"; :>> createdBy = "claudeOpus5"; :>> method = VerificationMethod::analyze; :>> procedureText = "TWO REQUIREMENTS PERMIT THE BAD ANSWER WITHOUT SAYING SO, which is the pattern across this batch. srEncodingModular requires a channel REGISTRY and never says where it lives, so a registry compiled into the viewer satisfies every word while violating nServeReuseModel (no separately-maintained list that can drift) and D0150 (vocabulary derived, not restated) — and the engine already has that exact failure in VIEW_SUBCOMMANDS. srEncodingSpec calls the thing an 'encoding viewpoint' and then says 'the viewer shall model' it, pointing both ways: a Viewpoint in the model would need a frozen-core schema addition with human sign-off, as `surface` did under D0154, while a viewer-side object is invisible to every computed view. Neither requirement is wrong; both are underdetermined in exactly the place where the two answers cost different amounts and only one of them lets a project extend the tool."; }
    part c5ImplementGateR1 : TestResult { :>> id = "0d800448-0814-6448-9b3e-000000300448"; :>> outcome = VerdictKind::pass; :>> judgedAgainst = "41a237f"; :>> judgedAt = "2026-08-17"; :>> judgedBy = "claudeOpus5"; }

    verification c5ReviewGate : Test { :>> id = "0d800449-0814-6449-9b3e-000000300449"; :>> title = "Sprint 329 review gate"; :>> createdAt = "2026-08-17"; :>> createdBy = "claudeOpus5"; :>> method = VerificationMethod::inspect; :>> procedureText = "Reviewed. THE FOUR PASSES ARE LOAD-BEARING HERE rather than filler. srEncodingModular's testability passes on a diff-based negative case — add one channel module and require the diff to touch nothing else — which is the rare test that is cheaper than the argument about whether it is met, and which fails the first time someone reaches into the apply pass for a special case. srEncodingOverride passes correctness because 'layered on top of the semantic defaults' is exactly right: an override as a delta over a regenerable base means a schema change can refresh defaults without discarding intent. srEncodingSchemaSemantics passes testability because it is already exercised in substance. WHAT I DELIBERATELY DID NOT DO: raise an Issue for the categorical-kind defect. It is a requirement-quality finding against a human-owned requirement, so it is recorded where the owner will meet it, and the fix (a fifth kind, or a distinct-count threshold) is theirs to choose."; }
    part c5ReviewGateR1 : TestResult { :>> id = "0d80044a-0814-644a-9b3e-00000030044a"; :>> outcome = VerdictKind::pass; :>> judgedAgainst = "41a237f"; :>> judgedAt = "2026-08-17"; :>> judgedBy = "claudeOpus5"; }

    verification c5CloseOutGate : Test { :>> id = "0d80044b-0814-644b-9b3e-00000030044b"; :>> title = "Sprint 329 closeOut gate (autonomous, D0049)"; :>> createdAt = "2026-08-17"; :>> createdBy = "claudeOpus5"; :>> method = VerificationMethod::inspect; :>> procedureText = "Autonomous closeOut (D0049). SystemRequirement coverage 5 -> 10 of 72; 20 critiquable SRs and 22 critiquable Decisions remain, plus 87 elements blocked on a critic who is not claudeOpus5. Zero open issues; ready frontier empty; D0159 queued. `rustToolchainFix` shows drift from sprint 328's code change and will be cleared with reverify at the end of the critique run rather than after each no-code pass. validate 357 clean; check-engine clean; 35 guards ALL PASS; no code changed this sprint."; }
    part c5CloseOutGateR1 : TestResult { :>> id = "0d80044c-0814-644c-9b3e-00000030044c"; :>> outcome = VerdictKind::pass; :>> judgedAgainst = "41a237f"; :>> judgedAt = "2026-08-17"; :>> judgedBy = "claudeOpus5"; }

    verification c5RetroGate : Test { :>> id = "0d80044d-0814-644d-9b3e-00000030044d"; :>> title = "Sprint 329 retro gate (autonomous, D0049)"; :>> createdAt = "2026-08-17"; :>> createdBy = "claudeOpus5"; :>> method = VerificationMethod::analyze; :>> procedureText = "Autonomous retro (D0049) under D0131's retroTrack. WELL: (1) reading the implementation FIRST changed the whole batch — srEncodingSchemaSemantics turned out to be substantially built, so the critique moved from imagined delivery gaps to the requirement's own vocabulary, and produced the sharpest finding of the pass by tracing stat_kind's fallthrough; (2) sprint 328's prediction was checked rather than assumed: N-18's unfalsifiable clause IS inherited by srEncodingSpec, which is the concrete cost the earlier record only forecast; (3) every factual claim names a function or file, so a reader can disagree with the evidence rather than with my judgment. AVOIDABLE-ISSUE: none this sprint. OBSERVATION WORTH CARRYING: three passes now have found that a requirement is underdetermined precisely at the boundary between the MODEL and the BINARY — where the registry lives, where the spec lives, whether a channel is declared. That is the same boundary that produced issue138's unit question and issue139's hardcoded path, and it suggests the model has no vocabulary for saying which side of that line a thing belongs on. Estimate 3 pts, delivered."; }
    part c5RetroGateR1 : TestResult { :>> id = "0d80044e-0814-644e-9b3e-00000030044e"; :>> outcome = VerdictKind::pass; :>> judgedAgainst = "41a237f"; :>> judgedAt = "2026-08-17"; :>> judgedBy = "claudeOpus5"; }
}
