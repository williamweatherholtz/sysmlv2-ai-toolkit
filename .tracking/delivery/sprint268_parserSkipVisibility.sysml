// ProjectDeliveryS268 — Sprint 268: what keel-parser cannot read is now REPORTED instead of silently
// discarded (issue102). The safety property the rest of the base-first pass depends on. EXECUTE. 3 pts.
package ProjectDeliveryS268 {
    private import EngineElement::*;
    private import EngineWork::*;
    private import EngineVerification::*;
    private import EngineRelationships::*;

    #CharteredBy dependency from parserSkipStory to d0139;

    part parserSkipStory : Story {
        :>> id = "0d800066-0814-6066-9b3e-000000300066";
        :>> title = "Sprint 268: Package.skipped + parser-coverage guard — skipping stops being silent (3 pts)";
        :>> createdAt = "2026-08-14"; :>> createdBy = "claudeOpus5"; :>> kind = WorkKind::code; :>> priority = WorkPriority::p0; :>> owner = "claudeOpus5"; :>> estimatedPoints = 3;
    }

    action def DeliveryRunS268 {
        action storyParserSkip;
        verification storyParserSkipDoD : Test { :>> id = "0d800067-0814-6067-9b3e-000000300067"; :>> method = VerificationMethod::test; :>> procedureText = "Covers dcParserSkipVisibility (issue102). MEASURED FIRST, with the undeclared-name discriminator against `validate`: the control `part x : NoSuchTypeAnywhere` produces 1 semantic diagnostic, while `ref e : NoSuchTypeAnywhere`, `port p : NoSuchPortDef`, `assert constraint c : NoSuchConstraint` and `connect ghostA.p to ghostB.p` ALL validate clean — so those statements are invisible, not merely unresolved. Every construct D0139 converts toward sits in that set, so a conversion landing before the reader would make its edges parse clean and vanish while all 27 guards reported green. DELIVERED: `Package.skipped: Vec<SkippedStatement>` (line + leading token), recorded inside `skip_item` itself because that is the single choke point every skip passes through — no threading through a dozen call sites; and the warning-level `parser-coverage` guard reporting counts grouped by lead token. FOUND IMMEDIATELY, previously invisible: 165 skipped statements across 473 files — 52 `:>` SPECIALIZATION clauses, so the type hierarchy is unread and `:>` is precisely the derivation form D0140 names for #DerivedFrom; 57 `use case` USAGES, since only `use case def` is handled; 18 `flow`; plus 39 benign semicolons and brace blocks. ALSO CORRECTED HERE: the panel antagonist's claim that the engine's own schema 'is not parsed as SysML' is half wrong — `parser.rs` has a generic `<ident> def Name` arm and `metadata`/`occurrence`/`port` lex as identifiers, so their def NAMES are captured and `: Name` resolves. Only members and relationship statements are lost. 27 guards (19 hard, 8 warning-only); clippy clean; 161 tests; validate + guard + check-engine green."; }
        part storyParserSkipDoDR1 : TestResult { :>> id = "0d800068-0814-6068-9b3e-000000300068"; :>> outcome = VerdictKind::pass; :>> judgedAgainst = "4e9fd63"; :>> judgedAt = "2026-08-14"; :>> judgedBy = "claudeOpus5"; }
    }

    verification pkRefineGate : Test { :>> id = "0d800069-0814-6069-9b3e-000000300069"; :>> title = "Sprint 268 refine gate (DoR)"; :>> createdAt = "2026-08-14"; :>> createdBy = "claudeOpus5"; :>> method = VerificationMethod::inspect; :>> procedureText = "DoR: the human accepted that things may be unsafe mid-construction, which makes VISIBILITY the highest-value next increment rather than capability — an unsafe state you can see is workable, an unsafe state that reports green is not. Chosen over capturing constructs first for that reason. estimatedPoints=3. DoR met."; }
    part pkRefineGateR1 : TestResult { :>> id = "0d80006a-0814-606a-9b3e-00000030006a"; :>> outcome = VerdictKind::pass; :>> judgedAgainst = "4e9fd63"; :>> judgedAt = "2026-08-14"; :>> judgedBy = "claudeOpus5"; }

    verification pkStandupGate : Test { :>> id = "0d80006b-0814-606b-9b3e-00000030006b"; :>> title = "Sprint 268 standup gate"; :>> createdAt = "2026-08-14"; :>> createdBy = "claudeOpus5"; :>> method = VerificationMethod::inspect; :>> procedureText = "Approach: MEASURE what is actually lost before building anything, because the panel's claim was stated in terms of def names and I suspected it was imprecise — it was. Then record at `skip_item` rather than at each of its dozen call sites. No blockers."; }
    part pkStandupGateR1 : TestResult { :>> id = "0d80006c-0814-606c-9b3e-00000030006c"; :>> outcome = VerdictKind::pass; :>> judgedAgainst = "4e9fd63"; :>> judgedAt = "2026-08-14"; :>> judgedBy = "claudeOpus5"; }

    verification pkImplementGate : Test { :>> id = "0d80006d-0814-606d-9b3e-00000030006d"; :>> title = "Sprint 268 implement gate"; :>> createdAt = "2026-08-14"; :>> createdBy = "claudeOpus5"; :>> method = VerificationMethod::test; :>> procedureText = "Two choices worth recording. (1) Recording inside `skip_item` rather than at its call sites: there are a dozen sites across three body-parsing loops, and threading a collector through all of them would have been a large diff with a real chance of missing one — the choke point makes completeness structural rather than diligent. (2) The report ranks by count and collapses the tail, because the FIRST version printed 57 singleton element names (a skipped `use case <name>` reports its own name as the lead token) and buried the four findings that mattered. A control whose output nobody reads is not a control, and I only noticed because I read my own guard's output rather than assuming it was fine."; }
    part pkImplementGateR1 : TestResult { :>> id = "0d80006e-0814-606e-9b3e-00000030006e"; :>> outcome = VerdictKind::pass; :>> judgedAgainst = "4e9fd63"; :>> judgedAt = "2026-08-14"; :>> judgedBy = "claudeOpus5"; }

    verification pkReviewGate : Test { :>> id = "0d80006f-0814-606f-9b3e-00000030006f"; :>> title = "Sprint 268 review gate"; :>> createdAt = "2026-08-14"; :>> createdBy = "claudeOpus5"; :>> method = VerificationMethod::inspect; :>> procedureText = "Reviewed. The sprint delivers exactly what it claims and no more: skipping is now REPORTED, not READ. That distinction is stated plainly in the Issue and in the follow-on item because it is the thing a reader would most easily overstate — 165 statements are now visible and still unreadable, so the conversions remain blocked, they are merely no longer dangerous to attempt. The `:>` finding is the most consequential thing this guard surfaced: D0140 names `:>` as the derivation form for #DerivedFrom on the strength of kernel evidence, and it turns out our own parser does not read specialization clauses at all — so that migration had a second, undiscovered blocker beyond the one D0140 recorded."; }
    part pkReviewGateR1 : TestResult { :>> id = "0d800070-0814-6070-9b3e-000000300070"; :>> outcome = VerdictKind::pass; :>> judgedAgainst = "4e9fd63"; :>> judgedAt = "2026-08-14"; :>> judgedBy = "claudeOpus5"; }

    verification pkCloseOutGate : Test { :>> id = "0d800071-0814-6071-9b3e-000000300071"; :>> title = "Sprint 268 closeOut gate (autonomous, D0049)"; :>> createdAt = "2026-08-14"; :>> createdBy = "claudeOpus5"; :>> method = VerificationMethod::inspect; :>> procedureText = "Autonomous closeOut (D0049). dcParserSkipVisibility carries a passing DoD TestResult; issue102 resolves. dcParserReadBase declared as the follow-on with per-construct verification criteria, ranked by what the pass needs first. Doc-sync: guards.md count 26 -> 27, 7 -> 8 warning-only, plus the catalogue entry; CLAUDE.md §5. clippy clean; 161 tests; validate + all 27 guards + check-engine green. No gate bypassed."; }
    part pkCloseOutGateR1 : TestResult { :>> id = "0d800072-0814-6072-9b3e-000000300072"; :>> outcome = VerdictKind::pass; :>> judgedAgainst = "4e9fd63"; :>> judgedAt = "2026-08-14"; :>> judgedBy = "claudeOpus5"; }

    verification pkRetroGate : Test { :>> id = "0d800073-0814-6073-9b3e-000000300073"; :>> title = "Sprint 268 retro gate (autonomous, D0049)"; :>> createdAt = "2026-08-14"; :>> createdBy = "claudeOpus5"; :>> method = VerificationMethod::analyze; :>> procedureText = "Autonomous retro (D0049) under D0131's retroTrack. WELL: (1) I measured the panel's claim instead of implementing against it, and it was half wrong in a way that would have sent me to add tokens the parser already effectively handles — the generic `<ident> def` arm meant def names were never the problem; (2) the undeclared-name discriminator, learned from the `objective` finding two sprints ago, transferred directly and settled four constructs in one command; (3) I read my own guard's output and found it unreadable, which is the same read-back discipline applied to a control's usability rather than its correctness. AVOIDABLE-ISSUE 1: a Python patch script crashed on `UnicodeEncodeError` when printing source text containing an em-dash to a cp1252 console, and because the print preceded the write, the edit was silently NOT applied — I could easily have believed it had been. NO NEW ITEM, reason stated: this is the host/shell-adaptation class already tracked as issue094 with dcShellAdaptationGate as its resolver, and the specific lesson (never print source text from a patch script; write first, verify by reading the file) is narrower than a gate can enforce. It does add one concrete detail worth having in that item: a failed patch that printed before writing leaves NO trace of not having applied. AVOIDABLE-ISSUE 2: I asserted in the previous turn's report that 29 engine-schema statements were 'silently discarded', repeating the antagonist's framing before measuring it. The real number is 165 across the repo and the mechanism is different. NO NEW ITEM, reason stated: this is the seventh instance of the read-back principle in this sitting and it is already the accepted response contract; but it is the first time I repeated a SUBAGENT's unverified claim in my own voice to the human, which is a distinct and worse failure than trusting my own intermediate — a subagent's finding is evidence to check, not a result to relay. Estimate 3 pts, delivered."; }
    part pkRetroGateR1 : TestResult { :>> id = "0d800074-0814-6074-9b3e-000000300074"; :>> outcome = VerdictKind::pass; :>> judgedAgainst = "4e9fd63"; :>> judgedAt = "2026-08-14"; :>> judgedBy = "claudeOpus5"; }
}
