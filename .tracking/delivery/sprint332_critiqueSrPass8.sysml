// ProjectDeliveryS332 — Sprint 332: critique pass 8. A finding I published last pass was overstated and
// is corrected here; the corrected version is sharper. EXECUTE. 3 pts.
package ProjectDeliveryS332 {
    private import EngineElement::*;
    private import EngineWork::*;
    private import EngineVerification::*;
    private import EngineRelationships::*;

    #CharteredBy dependency from critPass8Story to d0080;

    part critPass8Story : Story {
        :>> id = "0d800470-0814-6470-9b3e-000000300470";
        :>> title = "Sprint 332: critique pass 8 — 5 viewer SRs x Core-3, 8 fail / 7 pass, plus one correction (3 pts)";
        :>> createdAt = "2026-08-17"; :>> createdBy = "claudeOpus5"; :>> kind = WorkKind::modeling; :>> priority = WorkPriority::p0; :>> owner = "claudeOpus5"; :>> estimatedPoints = 3;
    }

    action def DeliveryRunS332 {
        action storyCritPass8;
        verification storyCritPass8DoD : Test { :>> id = "0d800471-0814-6471-9b3e-000000300471"; :>> method = VerificationMethod::analyze; :>> procedureText = "Pass 8: srViewerRelationshipGrammar, srViewerInProgramEdit, srViewerIterativeCritique, srViewerKeelApi, srViewerNavHistory. 8 fail, 7 pass. A CORRECTION FIRST: pass 7's critique of srViewerCreateLinkage said a create flow would have to INVENT the pair-to-kinds mapping in viewer code. It would not — /api/grammar exists and returns (sourceType, edge, targetType) triples, and AUTHORABLE_EDGE_KINDS bounds what the write surface may author. I had not looked far enough. The corrected finding is SHARPER: view::grammar_json builds its triples by iterating THE MODEL'S EXISTING EDGES, so the grammar is DESCRIPTIVE where the requirement is PRESCRIPTIVE — a valid triple nobody has authored yet is absent, so a client offering only observed triples refuses a legitimate first-of-its-kind connection and the grammar cannot bootstrap; and one mistaken edge legitimises its own triple forever. Recorded against srViewerRelationshipGrammar with the measurement that its named prescriptive source is nearly empty: rules.sysml declares three objectType values, two wildcards and one Need, so the EdgeRule layer supplies exactly ONE constrained pair. SECOND: srViewerKeelApi promises that 'breaking changes bump the version' with nothing detecting a breaking change — no recorded baseline contract to diff against, so removing an endpoint or renaming a field passes every gate with the version untouched, and manual vigilance is not a control (D0047). READ BACK: SystemRequirement coverage 20 -> 25 of 72."; }
        part storyCritPass8DoDR1 : TestResult { :>> id = "0d800472-0814-6472-9b3e-000000300472"; :>> outcome = VerdictKind::pass; :>> judgedAgainst = "643d0da"; :>> judgedAt = "2026-08-17"; :>> judgedBy = "claudeOpus5"; }
    }

    verification c8RefineGate : Test { :>> id = "0d800473-0814-6473-9b3e-000000300473"; :>> title = "Sprint 332 refine gate (DoR)"; :>> createdAt = "2026-08-17"; :>> createdBy = "claudeOpus5"; :>> method = VerificationMethod::inspect; :>> procedureText = "DoR. Five SRs, and reading the first one is what exposed the pass-7 overstatement: srViewerRelationshipGrammar's title named the very thing I had just claimed keel could not derive, so I followed it to /api/grammar and to grammar_json. Reading the NEXT requirement in a family is the cheapest available check on a finding about the family — the answer to my objection was one element away in the same file. estimatedPoints=3."; }
    part c8RefineGateR1 : TestResult { :>> id = "0d800474-0814-6474-9b3e-000000300474"; :>> outcome = VerdictKind::pass; :>> judgedAgainst = "643d0da"; :>> judgedAt = "2026-08-17"; :>> judgedBy = "claudeOpus5"; }

    verification c8StandupGate : Test { :>> id = "0d800475-0814-6475-9b3e-000000300475"; :>> title = "Sprint 332 standup gate"; :>> createdAt = "2026-08-17"; :>> createdBy = "claudeOpus5"; :>> method = VerificationMethod::inspect; :>> procedureText = "Approach: correct the pass-7 clause IN PLACE with the correction visible, as sprint 328 did, rather than silently rewriting it; then judge this batch, crediting by name the two requirements that repair defects I faulted their Needs for, since a critic who only records failures is not measuring. No blockers."; }
    part c8StandupGateR1 : TestResult { :>> id = "0d800476-0814-6476-9b3e-000000300476"; :>> outcome = VerdictKind::pass; :>> judgedAgainst = "643d0da"; :>> judgedAt = "2026-08-17"; :>> judgedBy = "claudeOpus5"; }

    verification c8ImplementGate : Test { :>> id = "0d800477-0814-6477-9b3e-000000300477"; :>> title = "Sprint 332 implement gate"; :>> createdAt = "2026-08-17"; :>> createdBy = "claudeOpus5"; :>> method = VerificationMethod::analyze; :>> procedureText = "SEVEN PASSES OF FIFTEEN, THE HIGHEST RATE OF THE RUN, AND THE REASON IS STRUCTURAL RATHER THAN CHARITABLE: these five requirements were written after their Needs had been used, and three of them REPAIR a defect I had faulted the Need for. srViewerInProgramEdit replaces N-16's unsatisfiable 'written back through the write API' with the enumerated write PROCESSES and reframes an edit as a SUPERSESSION, which is the correct move in this engine and converts an impossible clause into a buildable one. srViewerIterativeCritique names 'the independent-critic + provenance discipline', which is exactly the omission I charged N-15 with. srViewerNavHistory's parenthetical draws the line that makes an undo feature safe here — model writes are reversed through supersession and git, not through client history — and that single sentence prevents a second write path. Crediting these by name matters: the corpus should show that decomposition sometimes FIXES its parent, or a reader will read every fail as inherited and every pass as leniency."; }
    part c8ImplementGateR1 : TestResult { :>> id = "0d800478-0814-6478-9b3e-000000300478"; :>> outcome = VerdictKind::pass; :>> judgedAgainst = "643d0da"; :>> judgedAt = "2026-08-17"; :>> judgedBy = "claudeOpus5"; }

    verification c8ReviewGate : Test { :>> id = "0d800479-0814-6479-9b3e-000000300479"; :>> title = "Sprint 332 review gate"; :>> createdAt = "2026-08-17"; :>> createdBy = "claudeOpus5"; :>> method = VerificationMethod::inspect; :>> procedureText = "Reviewed. THIS IS THE SECOND PUBLISHED CLAIM I HAVE HAD TO CORRECT IN FIVE PASSES, and the two failures have the same shape: I asserted the ABSENCE of a mechanism after checking one place. In sprint 328 I trusted a comment over the record three lines below it; here I checked rules.sysml for a pair algebra, found almost nothing, and concluded the derivation was impossible — while /api/grammar was serving exactly that derivation. Absence is the hardest thing to establish and the easiest thing to assert, and both times the correcting evidence was within one file or one endpoint of where I had already looked. The guard added in sprint 328 cannot help here: no control can catch a critique that claims something does not exist. What can: when a finding turns on ABSENCE, search by capability rather than by the one location I expect, and say what I searched. Both corrections are left visible in the critiques."; }
    part c8ReviewGateR1 : TestResult { :>> id = "0d80047a-0814-647a-9b3e-00000030047a"; :>> outcome = VerdictKind::pass; :>> judgedAgainst = "643d0da"; :>> judgedAt = "2026-08-17"; :>> judgedBy = "claudeOpus5"; }

    verification c8CloseOutGate : Test { :>> id = "0d80047b-0814-647b-9b3e-00000030047b"; :>> title = "Sprint 332 closeOut gate (autonomous, D0049)"; :>> createdAt = "2026-08-17"; :>> createdBy = "claudeOpus5"; :>> method = VerificationMethod::inspect; :>> procedureText = "Autonomous closeOut (D0049). SystemRequirement coverage 20 -> 25 of 72; 5 critiquable SRs and 22 critiquable Decisions remain, plus 42 SRs and 45 other elements blocked on a critic who is not claudeOpus5. Zero open issues; ready frontier empty; D0159 queued. validate clean; check-engine clean; 35 guards ALL PASS; no code changed."; }
    part c8CloseOutGateR1 : TestResult { :>> id = "0d80047c-0814-647c-9b3e-00000030047c"; :>> outcome = VerdictKind::pass; :>> judgedAgainst = "643d0da"; :>> judgedAt = "2026-08-17"; :>> judgedBy = "claudeOpus5"; }

    verification c8RetroGate : Test { :>> id = "0d80047d-0814-647d-9b3e-00000030047d"; :>> title = "Sprint 332 retro gate (autonomous, D0049)"; :>> createdAt = "2026-08-17"; :>> createdBy = "claudeOpus5"; :>> method = VerificationMethod::analyze; :>> procedureText = "Autonomous retro (D0049) under D0131's retroTrack. AVOIDABLE-ISSUE, AND IT IS A REPEAT OF A CLASS RATHER THAN OF A MISTAKE: an ABSENCE claim published without an adequate search. Pass 7 said the pair-to-kinds mapping would have to be invented in viewer code; /api/grammar was already computing it, one grep away. Sprint 328's false claim had the same shape. THE REMEDY IS A SEARCH DISCIPLINE, and it is narrow enough to state: a finding whose content is that something DOES NOT EXIST must be preceded by a search on the CAPABILITY (grep the concept across the crate and the routes), not on the one file where I expect it, and the critique should say where I looked. No guard can enforce this — it constrains what I assert, which is D0151's residual — so it is recorded in the corpus where the next reader of these critiques will see both corrections. WELL: reading the next requirement in the family is what caught it, which is a cheap habit worth keeping; and three requirements were credited BY NAME for repairing their Needs' defects, so the corpus shows decomposition working and not only failing. Estimate 3 pts, delivered."; }
    part c8RetroGateR1 : TestResult { :>> id = "0d80047e-0814-647e-9b3e-00000030047e"; :>> outcome = VerdictKind::pass; :>> judgedAgainst = "643d0da"; :>> judgedAt = "2026-08-17"; :>> judgedBy = "claudeOpus5"; }
}
