// ProjectDeliveryS401 — Sprint 401: critique pass 5: the merge/sync cluster - the remote config probed TRUE, the raw-push hole found (issue209). EXECUTE. 2 pts.
package ProjectDeliveryS401 {
    private import EngineElement::*;
    private import EngineWork::*;
    private import EngineVerification::*;
    private import EngineRelationships::*;

    #CharteredBy dependency from critiquePass5Story to d0172;

    part critiquePass5Story : Story {
        :>> id = "6dbf8a00-5a19-4f02-93c6-1f802f53d768";
        :>> title = "Sprint 401: critique pass 5 over the srDc merge/sync cluster (2 pts)";
        :>> createdAt = "2026-08-21"; :>> createdBy = "claudeFable5"; :>> kind = WorkKind::code; :>> priority = WorkPriority::p0; :>> owner = "claudeFable5"; :>> estimatedPoints = 2;
    }

    action def DeliveryRunS401 {
        action storyCritiquePass5;
        verification storyCritiquePass5DoD : Test { :>> id = "6e4c5f73-67bd-4b02-9ed5-92684213ff07"; :>> method = VerificationMethod::test; :>> procedureText = "DELIVERED: 15 Core-3 critiques over srDcMergeOnlyIntegration, srDcGateOnMergedTree, srDcSyncAwareOrient, srDcPortableGate, srDcStaleClaimExpiry (batch 5). The pass PROBED THE REMOTE rather than trusting convention: GitHub branch protection on main is live (enforce_admins, force-push and deletion disabled) and the repository's merge methods are squash=false rebase=false merge=true - the enforced-by-remote-configuration clause, the one that is usually aspirational, probed TRUE; .gitattributes exists declaring model-file normalization and citing the SR itself; the claim machinery computes staleness from git time with the stale/superseded distinction. ONE ATTACK LANDED: issue209 (srDcGateOnMergedTree - no pre-push hook exists, so a raw git push lands a contribution gated only in isolation with CI catching it post-hoc, against the SR's NEVER-land letter; resolver dcPrePushBehindCheck: a behind-ness refusal naming keel land as the path, never a duplicate full gate). Fourteen survived on probe-grade evidence."; }
        part storyCritiquePass5DoDR1 : TestResult { :>> id = "15867117-472e-45aa-9e1b-3814126b2e8d"; :>> outcome = VerdictKind::pass; :>> judgedAgainst = "addc43c"; :>> judgedAt = "2026-08-21"; :>> judgedBy = "claudeFable5"; }
    }

    verification critiquePass5RefineGate : Test { :>> id = "0dac58d7-df98-470f-ad09-efc6fc06d083"; :>> title = "Sprint 401 refine gate (DoR)"; :>> createdAt = "2026-08-21"; :>> createdBy = "claudeFable5"; :>> method = VerificationMethod::inspect; :>> procedureText = "DoR. Chartered by d0172; batch 5, the merge/sync cluster the pass-4 retro steered toward as least-recently-exercised. 2 points."; }
    part critiquePass5RefineGateR1 : TestResult { :>> id = "2e30e4db-e176-4544-800b-01d4f747c57e"; :>> outcome = VerdictKind::pass; :>> judgedAgainst = "addc43c"; :>> judgedAt = "2026-08-21"; :>> judgedBy = "claudeFable5"; }
    verification critiquePass5StandupGate : Test { :>> id = "e25702aa-1d35-461e-8591-44bb7d072c6a"; :>> title = "Sprint 401 standup gate"; :>> createdAt = "2026-08-21"; :>> createdBy = "claudeFable5"; :>> method = VerificationMethod::inspect; :>> procedureText = "Approach: probe the REMOTE configuration via gh api before judging the enforcement clause - the one clause a local read cannot verify - plus .gitattributes, the hook inventory, and claim.rs. No blockers."; }
    part critiquePass5StandupGateR1 : TestResult { :>> id = "74b569c9-1cbd-4cf1-bc50-dfb363e382ba"; :>> outcome = VerdictKind::pass; :>> judgedAgainst = "addc43c"; :>> judgedAt = "2026-08-21"; :>> judgedBy = "claudeFable5"; }
    verification critiquePass5ImplementGate : Test { :>> id = "a6449020-f713-4901-8d5f-695308ddc3e8"; :>> title = "Sprint 401 implement gate"; :>> createdAt = "2026-08-21"; :>> createdBy = "claudeFable5"; :>> method = VerificationMethod::test; :>> procedureText = "15 method=critique Tests + results + #Verify edges; outcomes 14 pass / 1 fail. Probes captured: gh api branch protection + merge methods (live values quoted in the records), .githooks inventory (pre-push ABSENT - the finding), .gitattributes header, CLAIM_EXPIRY_DAYS + state fork in claim.rs. issue209 recorded with resolver dcPrePushBehindCheck in NextWork. validate 439 clean."; }
    part critiquePass5ImplementGateR1 : TestResult { :>> id = "dea72214-fde7-4ade-b5ea-8e695af407e3"; :>> outcome = VerdictKind::pass; :>> judgedAgainst = "addc43c"; :>> judgedAt = "2026-08-21"; :>> judgedBy = "claudeFable5"; }
    verification critiquePass5ReviewGate : Test { :>> id = "6f7112b6-ec27-4a79-9951-b29e2681e652"; :>> title = "Sprint 401 review gate — three passes per D0172"; :>> createdAt = "2026-08-21"; :>> createdBy = "claudeFable5"; :>> method = VerificationMethod::inspect; :>> procedureText = "PASS 1, CLAIMS: the remote-config pass rests on API-read values quoted verbatim, not on repository settings remembered; the finding rests on a directory listing anyone can reproduce. PASS 2, BOUNDARY: the srDcSyncAwareOrient stale-remote-tracking-ref residual (orient reports against the last fetch) is stated rather than glossed. PASS 3, OWN DIFF: the issue209 resolver deliberately scopes to behind-ness detection, NOT a full pre-push gate - a duplicate gate would slow every push to re-verify what keel land already gates, which is the friction class D0054 names as the #1 risk. WHAT A REVIEWER SHOULD ATTACK: whether behind-ness refusal alone actually closes the letter (an up-to-date-but-isolation-gated push still lands; the record argues the fetch-refusal forces the loop in practice since keel land is then the path of least resistance - that argument is judgment, not proof)."; }
    part critiquePass5ReviewGateR1 : TestResult { :>> id = "f93b9e89-2d6f-45c8-b469-37f4acb3c749"; :>> outcome = VerdictKind::pass; :>> judgedAgainst = "addc43c"; :>> judgedAt = "2026-08-21"; :>> judgedBy = "claudeFable5"; }
    verification critiquePass5CloseOutGate : Test { :>> id = "8187715a-5b39-462f-a98c-17abe779823c"; :>> title = "Sprint 401 closeOut gate (autonomous, D0049)"; :>> createdAt = "2026-08-21"; :>> createdBy = "claudeFable5"; :>> method = VerificationMethod::inspect; :>> procedureText = "Autonomous closeOut (D0049). Finding triaged at recording; lens gains 5 examined SRs; validate + all 44 guards green."; }
    part critiquePass5CloseOutGateR1 : TestResult { :>> id = "49130cf3-ca80-40c8-b7ad-fba180789eef"; :>> outcome = VerdictKind::pass; :>> judgedAgainst = "addc43c"; :>> judgedAt = "2026-08-21"; :>> judgedBy = "claudeFable5"; }
    verification critiquePass5RetroGate : Test { :>> id = "f66da235-5d3d-4d12-8287-681ea62bf2ef"; :>> title = "Sprint 401 retro gate (autonomous, D0049)"; :>> createdAt = "2026-08-21"; :>> createdBy = "claudeFable5"; :>> method = VerificationMethod::analyze; :>> procedureText = "Autonomous retro (D0049). AVOIDABLE-ISSUE SCAN under rcRecurrence: issue209 is enforcement-at-the-wrong-layer rather than the uncounted-event family - first instance of its shape this campaign (CI verifies what a hook should have prevented); noted, one instance, no control demanded yet. WELL: probing the remote caught the strongest PASS of the campaign - the branch-protection clause would have been unverifiable by any local read, and the probe cost one API call. PACE: 18 SRs remain, ~4 passes. Estimate 2 pts, delivered 2."; }
    part critiquePass5RetroGateR1 : TestResult { :>> id = "bf5c475f-57fc-4eda-b836-4be8aef31bc2"; :>> outcome = VerdictKind::pass; :>> judgedAgainst = "addc43c"; :>> judgedAt = "2026-08-21"; :>> judgedBy = "claudeFable5"; }
}
