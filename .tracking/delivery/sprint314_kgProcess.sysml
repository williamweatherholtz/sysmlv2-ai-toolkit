// ProjectDeliveryS314 — Sprint 314: an external artefact becomes a portable keel process unit.
// EXECUTE. 5 pts.
package ProjectDeliveryS314 {
    private import EngineElement::*;
    private import EngineWork::*;
    private import EngineVerification::*;
    private import EngineRelationships::*;

    #CharteredBy dependency from kgProcessStory to d0153;

    part kgProcessStory : Story {
        :>> id = "0d800350-0814-6350-9b3e-000000300350";
        :>> title = "Sprint 314: Knowledge-Graph Memory as a shareable process unit (5 pts)";
        :>> createdAt = "2026-08-16"; :>> createdBy = "claudeOpus5"; :>> kind = WorkKind::modeling; :>> priority = WorkPriority::p1; :>> owner = "claudeOpus5"; :>> estimatedPoints = 5;
    }

    action def DeliveryRunS314 {
        action storyKgProcess;
        verification storyKgProcessDoD : Test { :>> id = "0d800351-0814-6351-9b3e-000000300351"; :>> method = VerificationMethod::inspect; :>> procedureText = "Applies D0153 (accepted by wweatherholtz 2026-08-16, verbatim 'proposed and accepted'). The human supplied an external artefact — 'Applying Knowledge Graphs', Glitch Cat Club, 16 Aug 2026 — and asked for it 'as a generateable shareable process', which nProcessPortability defines precisely: DEFINITION + DEPLOYING SKILL + declared rules/guards + metadata, importable and activatable per project. DELIVERED: `.engine/processes/knowledge-graph-memory.sysml` (a Process with eight ProcessSteps and their successions), `.engine/skills/knowledge-graph-memory/SKILL.md` (the deploying skill — D0059 forbids an inert process), and the skills-registry entry that makes the pairing machine-checkable. THE ORDER IS PRESERVED FROM THE SOURCE BECAUSE IT IS THE LOAD-BEARING PART: questions, then vocabulary, then logical model, then extraction — a vocabulary derived from documents describes the documents, one derived from questions answers them. Two steps are owned by the HUMAN deliberately (the questions; the closed vocabulary), because every later step is measured against them and a model should not choose them alone. VERIFIED: process-skill guard 18 scanned 0 violations — the pairing resolves; check-engine clean; the process is inert until a project activates it, so nothing changes for anyone who does not. validate 341 clean; 33 guards green."; }
        part storyKgProcessDoDR1 : TestResult { :>> id = "0d800352-0814-6352-9b3e-000000300352"; :>> outcome = VerdictKind::pass; :>> judgedAgainst = "8507239"; :>> judgedAt = "2026-08-16"; :>> judgedBy = "claudeOpus5"; }
    }

    verification kgRefineGate : Test { :>> id = "0d800353-0814-6353-9b3e-000000300353"; :>> title = "Sprint 314 refine gate (DoR)"; :>> createdAt = "2026-08-16"; :>> createdBy = "claudeOpus5"; :>> method = VerificationMethod::inspect; :>> procedureText = "DoR. THE CONTENT WAS NOT AVAILABLE AT FIRST and no work started until it was: the shared artefact could not be fetched — 'served to you as a public (non-member) reader' — so the title was known and nothing else. Building a knowledge-graph process from a title would have been precisely the invention D0151 forbids, so the request was blocked on the human supplying the PDF, then extracted (13 pages, 15026 chars) and read in full. CONSUMER CHECK (dorConsumer, D0144): the consumer is a DOWNSTREAM project importing the unit, so the process had to be general — it names no store, no language and no harness — and the deploying skill had to carry the vocabulary a reader needs to apply it. estimatedPoints=5."; }
    part kgRefineGateR1 : TestResult { :>> id = "0d800354-0814-6354-9b3e-000000300354"; :>> outcome = VerdictKind::pass; :>> judgedAgainst = "8507239"; :>> judgedAt = "2026-08-16"; :>> judgedBy = "claudeOpus5"; }

    verification kgStandupGate : Test { :>> id = "0d800355-0814-6355-9b3e-000000300355"; :>> title = "Sprint 314 standup gate"; :>> createdAt = "2026-08-16"; :>> createdBy = "claudeOpus5"; :>> method = VerificationMethod::inspect; :>> procedureText = "Approach: read the source in full before designing; match the portable-unit shape the engine already defines rather than inventing a delivery form; keep the engine's own model out of it, so the pattern stays shareable. No blockers once the content arrived."; }
    part kgStandupGateR1 : TestResult { :>> id = "0d800356-0814-6356-9b3e-000000300356"; :>> outcome = VerdictKind::pass; :>> judgedAgainst = "8507239"; :>> judgedAt = "2026-08-16"; :>> judgedBy = "claudeOpus5"; }

    verification kgImplementGate : Test { :>> id = "0d800357-0814-6357-9b3e-000000300357"; :>> title = "Sprint 314 implement gate"; :>> createdAt = "2026-08-16"; :>> createdBy = "claudeOpus5"; :>> method = VerificationMethod::test; :>> procedureText = "THE TEMPTATION WORTH NAMING WAS TO BUILD IT AGAINST KEEL ITSELF. keel's model already IS a knowledge graph — typed items are entities, typed edges are relations — and keel already has a UserPromptSubmit hook, which is the artefact's exact injection point. Implementing there would have been fast, demonstrable, and WRONG for the request: it produces the instance rather than the pattern, and an instance cannot be imported by another project, which is the whole meaning of 'shareable'. Rejected explicitly in D0153 and recorded as the obvious next application rather than lost. TWO PROVENANCE DISCIPLINES: the source's measurements — a small model going from wrong to correct with zero tool calls and millisecond retrieval — are recorded as ITS claims, measured on one corpus and one question by its authors, and the skill tells an adopting project to measure its own. And the unit ships with NO GUARDS, stated rather than left as a gap: every candidate depends on a store this engine does not own and cannot read, so it would be unenforceable or would have the engine gating a file it has no business knowing. A PROCESS-SKILL PAIRING WAS INITIALLY MISSED: the guard reads the skills REGISTRY, not the skill file's own metadata, and refused the commit until the registry entry existed — the control working, and a reminder that a skill file alone does not deploy anything."; }
    part kgImplementGateR1 : TestResult { :>> id = "0d800358-0814-6358-9b3e-000000300358"; :>> outcome = VerdictKind::pass; :>> judgedAgainst = "8507239"; :>> judgedAt = "2026-08-16"; :>> judgedBy = "claudeOpus5"; }

    verification kgReviewGate : Test { :>> id = "0d800359-0814-6359-9b3e-000000300359"; :>> title = "Sprint 314 review gate"; :>> createdAt = "2026-08-16"; :>> createdBy = "claudeOpus5"; :>> method = VerificationMethod::inspect; :>> procedureText = "Reviewed. The skill's anti-pattern watchlist is where the source's hard-won detail survives in usable form: the DECORATIVE GRAPH (the model still searches; detection is that it makes tool calls to answer), VOCABULARY FROM DOCUMENTS rather than from questions, OPEN VOCABULARY that grows per document during extraction, LOOKED-UP IDENTITY (detection: re-running the build duplicates nodes), EASY-QUESTION VERIFICATION (detection: the before/after control also passes), SILENT EMPTY RECALL where the model answers from priors anyway, and DEPTH PANIC — the source is emphatic that the limit is never hops, six hops being six edges, and that the real axes are density, size, vagueness and ambiguity. Each carries a detection and a resolution rather than being a caution."; }
    part kgReviewGateR1 : TestResult { :>> id = "0d80035a-0814-635a-9b3e-00000030035a"; :>> outcome = VerdictKind::pass; :>> judgedAgainst = "8507239"; :>> judgedAt = "2026-08-16"; :>> judgedBy = "claudeOpus5"; }

    verification kgCloseOutGate : Test { :>> id = "0d80035b-0814-635b-9b3e-00000030035b"; :>> title = "Sprint 314 closeOut gate (autonomous, D0049)"; :>> createdAt = "2026-08-16"; :>> createdBy = "claudeOpus5"; :>> method = VerificationMethod::inspect; :>> procedureText = "Autonomous closeOut (D0049); the process-definition change carries wweatherholtz's explicit sign-off as D0153, recorded after the files were committed as proposed so they could be READ before the gate rather than judged from a summary. Nothing is enforced on any project that does not activate the unit. validate 341 clean; check-engine clean; 33 guards green including process-skill."; }
    part kgCloseOutGateR1 : TestResult { :>> id = "0d80035c-0814-635c-9b3e-00000030035c"; :>> outcome = VerdictKind::pass; :>> judgedAgainst = "8507239"; :>> judgedAt = "2026-08-16"; :>> judgedBy = "claudeOpus5"; }

    verification kgRetroGate : Test { :>> id = "0d80035d-0814-635d-9b3e-00000030035d"; :>> title = "Sprint 314 retro gate (autonomous, D0049)"; :>> createdAt = "2026-08-16"; :>> createdBy = "claudeOpus5"; :>> method = VerificationMethod::analyze; :>> procedureText = "Autonomous retro (D0049) under D0131's retroTrack. WELL: (1) the work BLOCKED on missing content rather than proceeding from a title, which a day earlier would not reliably have happened — D0151 was accepted hours before and this is its first real test; (2) matching the portable-unit shape the engine already defines meant the deliverable was discovered rather than designed, and the process-skill guard could then check it; (3) the instance-versus-pattern temptation was named in the Decision rather than silently avoided, so a successor sees why keel's own model was left alone. AVOIDABLE-ISSUE: I wrote the skill file and assumed that constituted the pairing; the process-skill guard refused the commit because the pairing lives in the skills REGISTRY. Cheap to fix and caught immediately, but the tell generalises — a file existing in the right directory is not the same as being DECLARED, and this engine consistently reads declarations rather than directory contents. NO NEW ITEM: the guard is the control and it worked. OPEN, and worth a successor knowing: the console design (D0152, six SRs) is landed but nothing is refined into delivery items, and this tangent interrupted that. Estimate 5 pts, delivered."; }
    part kgRetroGateR1 : TestResult { :>> id = "0d80035e-0814-635e-9b3e-00000030035e"; :>> outcome = VerdictKind::pass; :>> judgedAgainst = "8507239"; :>> judgedAt = "2026-08-16"; :>> judgedBy = "claudeOpus5"; }
}
