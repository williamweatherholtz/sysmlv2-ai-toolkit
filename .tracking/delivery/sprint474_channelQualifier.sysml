// ProjectDeliveryS474 - Sprint 474: the channel wrote one id and looked up another. Four gaps, three of them the same shape - two implementations of one fact. EXECUTE. 3 pts.
package ProjectDeliveryS474 {
    private import EngineElement::*;
    private import EngineWork::*;
    private import EngineVerification::*;
    private import EngineRelationships::*;

    #CharteredBy dependency from qualifierStory to d0240;

    part qualifierStory : Story {
        :>> id = "54055384-a646-480b-89ee-087dcd5dc55b";
        :>> title = "Sprint 474: the channel decision id round-trips - one join, one split, one marker, and the deciders resolved per project (3 pts)";
        :>> createdAt = "2026-08-27"; :>> createdBy = "claudeOpus5"; :>> kind = WorkKind::code; :>> priority = WorkPriority::p1; :>> owner = "claudeOpus5"; :>> estimatedPoints = 3;
    }

    action def DeliveryRunS474 {
        action storyQualifier;
        verification storyQualifierDoD : Test { :>> id = "4766aa2c-b614-4875-90ea-d1a368ea3e00"; :>> method = VerificationMethod::test; :>> procedureText = "DELIVERED: dcChannelQualifierRoundTrips (issue279) under D0240, all four gaps. The opener writes the QUALIFIED id into the durable marker, where it wrote the bare name while every lookup in the same file used the qualified one - and ensure_override_threads already wrote qualified, so the two writers disagreed with each other. decision_in_gesture reads the label-slash-dNNNN form and returns it whole, staying strict - a URL is not a project label. The recorder's HUMAN branch splits the id and enters the project exactly as its AUTO branch does, and the decider is resolved AFTER the split, in the project the decision belongs to. keel github-decider takes --root, and the opener reads deciders from every project. The JOIN moved into the binary beside the split it must invert, so the pair cannot drift again."; }
    // RAN: cargo test --release => 11 suites 0 failures, 16 github tests incl join_and_split_are_inverses, a_gesture_naming_a_qualified_decision_keeps_its_project, the_decider_table_is_resolved_from_the_root_flag_when_given, and four channel_script_tests reading the two scripts | cargo clippy --release --all-targets => 0 errors | the opener's own qualify() exercised live against the binary: qualify('.','d0240',False) => 'd0240', qualify('alpha','d0001',True) => 'alpha/d0001', qualify('.','d0007',True) => 'd0007' (root stays bare in a multi repo) | workspace() => 1 project, multiProject False; decider_logins() => ['williamweatherholtz'] | keel github-decider exercised four ways: no arg lists, login maps, --root + login maps, --root alone lists; a nonexistent root authorises NOBODY (exit 1) | bash -n record_decision.sh clean | keel validate . => 529 clean; guard => 0 of 52 failing.
        part storyQualifierDoDR1 : TestResult { :>> id = "4df5a836-6c5c-4aa7-b0af-b3b8cc5b7009"; :>> outcome = VerdictKind::pass; :>> judgedAgainst = "3576bba"; :>> judgedAt = "2026-08-27"; :>> judgedBy = "claudeOpus5"; }
    }

    verification qualifierRefineGate : Test { :>> id = "c04258e2-6fa6-4d2e-b98e-0801086e02f9"; :>> title = "Sprint 474 refine gate (DoR)"; :>> createdAt = "2026-08-27"; :>> createdBy = "claudeOpus5"; :>> method = VerificationMethod::inspect; :>> procedureText = "DoR: with all four workspace Criticals closed in sprints 472-473, dcChannelQualifierRoundTrips ranked first - a High, and the last of the panel's findings that touches whether a HUMAN's judgment lands in the right tree. Read all four gaps in the source before designing, and found a fifth thing worth fixing: the join lived in Python while the split lived in Rust, which is WHY they disagreed. Resolver: dcChannelQualifierRoundTrips. estimatedPoints=3. #CharteredBy d0240."; }
    part qualifierRefineGateR1 : TestResult { :>> id = "fad069c4-f01d-46d9-8f0f-fe9f8e56ce62"; :>> outcome = VerdictKind::pass; :>> judgedAgainst = "3576bba"; :>> judgedAt = "2026-08-27"; :>> judgedBy = "claudeOpus5"; }
    verification qualifierStandupGate : Test { :>> id = "0b60395c-7df9-4fe7-9700-3c7478c23569"; :>> title = "Sprint 474 standup gate"; :>> createdAt = "2026-08-27"; :>> createdBy = "claudeOpus5"; :>> method = VerificationMethod::inspect; :>> procedureText = "Approach: fix the four, then remove the CAUSE of three of them by giving the join one home beside the split (D0105) with a test pinning them as inverses. Two gaps live in scripts that nothing read, so they get static checks from github.rs rather than no check at all. Ordering matters in the recorder: the decider lookup ran BEFORE the gesture was parsed, so it could not know which project the decision belonged to - moving it after the split fixes the decider gap for the recorder as a consequence rather than as a separate patch. This changes the channel process's mechanism, so it rides a co-committed #ProspectiveChange Decision (D0240)."; }
    part qualifierStandupGateR1 : TestResult { :>> id = "bcba9f37-c926-4588-a424-84cf3e56e76b"; :>> outcome = VerdictKind::pass; :>> judgedAgainst = "3576bba"; :>> judgedAt = "2026-08-27"; :>> judgedBy = "claudeOpus5"; }
    verification qualifierImplementGate : Test { :>> id = "d3b47d8c-84f4-4244-b928-21dbcc3abc3f"; :>> title = "Sprint 474 implement gate"; :>> createdAt = "2026-08-27"; :>> createdBy = "claudeOpus5"; :>> method = VerificationMethod::test; :>> procedureText = "Implemented all four plus the join relocation. keel github-decider needed a --root flag, and adding it meant the login finder had to stop treating --root's VALUE as a login - caught immediately by exercising all four invocations rather than only the new one. Two clippy fail-loud lints blocked the commit and were fixed rather than bypassed. The opener's qualify() was exercised live through the binary in all three cases, including the one that matters for compatibility: the ROOT project's id stays bare even in a multi-project repo, so every issue already open in every existing repo keeps resolving."; }
    // RAN: cargo test --release => 11 suites 0 failures, 16 github tests incl join_and_split_are_inverses, a_gesture_naming_a_qualified_decision_keeps_its_project, the_decider_table_is_resolved_from_the_root_flag_when_given, and four channel_script_tests reading the two scripts | cargo clippy --release --all-targets => 0 errors | the opener's own qualify() exercised live against the binary: qualify('.','d0240',False) => 'd0240', qualify('alpha','d0001',True) => 'alpha/d0001', qualify('.','d0007',True) => 'd0007' (root stays bare in a multi repo) | workspace() => 1 project, multiProject False; decider_logins() => ['williamweatherholtz'] | keel github-decider exercised four ways: no arg lists, login maps, --root + login maps, --root alone lists; a nonexistent root authorises NOBODY (exit 1) | bash -n record_decision.sh clean | keel validate . => 529 clean; guard => 0 of 52 failing.
    part qualifierImplementGateR1 : TestResult { :>> id = "e5d33227-29b6-4ece-afda-34f282168aa8"; :>> outcome = VerdictKind::pass; :>> judgedAgainst = "3576bba"; :>> judgedAt = "2026-08-27"; :>> judgedBy = "claudeOpus5"; }
    verification qualifierReviewGate : Test { :>> id = "1cec46a6-f432-47bd-9587-27c4cfacdeab"; :>> title = "Sprint 474 review gate"; :>> createdAt = "2026-08-27"; :>> createdBy = "claudeOpus5"; :>> method = VerificationMethod::inspect; :>> procedureText = "Diff reviewed. What is NOT claimed is stated in D0240 rather than left implied: there has been no end-to-end run of the channel against GitHub. These fixes are verified by unit tests, by static checks over the two scripts, and by exercising the binary and the opener's Python directly - the channel's live behaviour in a real multi-project repository is unexercised, because doing so means opening real issues in a real repository. The first workspace that adopts the channel is where that gets its first live test. Saying so is the point: the verification that shipped WITH this defect tested the join in isolation and never checked what gets written into an issue body, and the honest version of that is to name the gap rather than let a green test suite imply coverage it does not have."; }
    part qualifierReviewGateR1 : TestResult { :>> id = "01a3e1cd-cd2c-47b8-942b-de51bfca0f9d"; :>> outcome = VerdictKind::pass; :>> judgedAgainst = "3576bba"; :>> judgedAt = "2026-08-27"; :>> judgedBy = "claudeOpus5"; }
    verification qualifierCloseOutGate : Test { :>> id = "f5b725c5-60f8-457c-a82d-2b3b6c092d83"; :>> title = "Sprint 474 closeOut gate (autonomous, D0049)"; :>> createdAt = "2026-08-27"; :>> createdBy = "claudeOpus5"; :>> method = VerificationMethod::inspect; :>> procedureText = "Autonomous closeOut (D0049): the DoD is recorded pass with its RAN receipt; the frontier was read back from keel whats-next. Remaining from the panel: dcLandGatesBeforeThePush, dcNoCommandReportsGreenOverNothing, dcOneGateDefinition, dcPanelRecordCorrections and dcEveryAdvertisedViewIsBound - none Critical. Self-evidencing (D0051): no human confirmation is claimed anywhere in this sprint, and D0240 records what was NOT exercised."; }
    part qualifierCloseOutGateR1 : TestResult { :>> id = "062b12c6-10ac-43b3-acb7-f6a12b2ff4fa"; :>> outcome = VerdictKind::pass; :>> judgedAgainst = "3576bba"; :>> judgedAt = "2026-08-27"; :>> judgedBy = "claudeOpus5"; }
    verification qualifierRetroGate : Test { :>> id = "57fae20d-73a9-4fe6-8479-68389271fb78"; :>> title = "Sprint 474 retro gate (autonomous, D0049)"; :>> createdAt = "2026-08-27"; :>> createdBy = "claudeOpus5"; :>> method = VerificationMethod::analyze; :>> procedureText = "Autonomous retro (D0049). WELL: reading all four gaps in the source BEFORE designing found the cause rather than four symptoms - three of the four are one shape, two implementations of one fact disagreeing, and the join/split pair now has one home and one test that would have failed on the shipped code. FINDING, and it is the third sprint in a row to find this: the defect survived because NOTHING READ THE SCRIPTS. Two of these four gaps are one-line facts about a text file - a marker written bare, a splitter not called - and the test that catches them took twenty lines. The engine has 52 guards over .sysml and Rust, and had zero checks over the shell and Python that carry a human's judgment into the tree. AVOIDABLE-ISSUE SCAN: the verification recorded with D0234 tested the join function in ISOLATION, which is the hollow-verification shape this session has now hit four times - a unit test over a pure function while the integration that uses it is unexercised. Candidate forward control, stated not built: a guard that every executable under .github/scripts and .engine/tools is exercised by at least one test. Estimate 3 pts held."; }
    part qualifierRetroGateR1 : TestResult { :>> id = "858cb2a6-794d-48d5-badd-33ba8e5e581f"; :>> outcome = VerdictKind::pass; :>> judgedAgainst = "3576bba"; :>> judgedAt = "2026-08-27"; :>> judgedBy = "claudeOpus5"; }
}
