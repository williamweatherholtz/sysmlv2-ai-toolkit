// ProjectDeliveryS461 — Sprint 461: the guards that police how a Decision is recorded become undeactivatable, and the write path stops accepting tool output as authored prose. EXECUTE. 3 pts.
package ProjectDeliveryS461 {
    private import EngineElement::*;
    private import EngineWork::*;
    private import EngineVerification::*;
    private import EngineRelationships::*;

    #CharteredBy dependency from decisionAuthoringIsCoreStory to d0223;
    // D0224 came OUT of recording D0223 - the injection happened while writing it - so one sprint
    // charters both (D0188: an accepted ProspectiveChange must be reachable from the work delivering it).
    #CharteredBy dependency from decisionAuthoringIsCoreStory to d0224;

    part decisionAuthoringIsCoreStory : Story {
        :>> id = "d814ed2a-dadc-4c6e-8a02-57706b2ce134";
        :>> title = "Sprint 461: core by not claiming, and the injection that had already landed (3 pts)";
        :>> createdAt = "2026-08-24"; :>> createdBy = "claudeFable5"; :>> kind = WorkKind::code; :>> priority = WorkPriority::p0; :>> owner = "claudeFable5"; :>> estimatedPoints = 3;
    }

    action def DeliveryRunS461 {
        action storyDecisionAuthoringIsCore;
        verification storyDecisionAuthoringIsCoreDoD : Test { :>> id = "4142baad-bc8b-4197-b415-bdfa63631996"; :>> method = VerificationMethod::test; :>> procedureText = "DELIVERED: dcDecisionAuthoringIsCore (issue254, D0223) and dcNoShellInjectionIntoRecords (issue255 + issue256, D0224). FIRST: the human said they were fine with the process for defining and cementing processes being undisable-able and shipped with the software, and asked whether that was what we were discussing. It was NOT - process-change has been a core never-deactivatable guard all along and change-request sits outside the activation model, so both halves of their sentence were already true. Saying so instead of accepting the premise turned up the real gap next door: decision-authoring CLAIMED five guards, and a guard is core precisely when no unit claims it, so keel deactivate decision-authoring switched off confirmationAuthenticity - the guard that stops an AI recording a human acceptance that never happened. Removing the claims makes all five core and strictly more portable, since an adopting project gets them with no activation step; the link is recorded as core = [...] in process-enforcement.toml and hardening counts core guards as enforced, because otherwise a core-enforced process reports guards 0 and reads as NOT enforced. SECOND, and it came out of recording the first: a BACKTICK inside a double-quoted shell argument is command substitution, so the D0223 prose NAMED a keel command, sh RAN it, and roughly 2000 characters of JSON landed in the decision field of a governance record - caught only because that JSON carried an escape the parser rejects. Investigating it found the same injection had ALREADY LANDED and been accepted: D0214's context held 13,136 characters of console transcript, substituted mid-sentence exactly where a backticked command name stood, pushed undetected. So the write path now REFUSES prose carrying captured tool output in both observed shapes, naming the backtick mechanism in the refusal; keel record decision --from FILE became the sanctioned authoring path so no shell layer exists to run anything; and D0214's dump was excised with its sentence restored and its acceptance receipt untouched."; }
        part storyDecisionAuthoringIsCoreDoDR1 : TestResult { :>> id = "e31b0076-0d9d-4566-8ce8-9fdfbf79b5ec"; :>> outcome = VerdictKind::pass; :>> judgedAgainst = "016cada"; :>> judgedAt = "2026-08-24"; :>> judgedBy = "claudeFable5"; }
        part storyDecisionAuthoringIsCoreDoDR2 : TestResult { :>> id = "6ce806ba-d6cc-467f-af58-66dde16a608e"; :>> outcome = VerdictKind::pass; :>> judgedAgainst = "016cadaa627a5dda4345e66d1167859e60e8e5ec"; :>> judgedAt = "2026-08-24"; :>> judgedBy = "claudeFable5"; }
    }

    verification decisionAuthoringIsCoreRefineGate : Test { :>> id = "8474f571-9951-4891-bb8c-d864b6f4622f"; :>> title = "Sprint 461 refine gate (DoR)"; :>> createdAt = "2026-08-24"; :>> createdBy = "claudeFable5"; :>> method = VerificationMethod::inspect; :>> procedureText = "DoR. Resolves issue254 (human-directed, after I declined their premise and named the real gap), then issue255 and issue256 which the work itself produced. Scope: make the Decision-authoring guards core; then make the injection that surfaced while doing it impossible to repeat. 3 points."; }
    part decisionAuthoringIsCoreRefineGateR1 : TestResult { :>> id = "b3d72e4e-39a7-4cd0-a135-d4358beb0e16"; :>> outcome = VerdictKind::pass; :>> judgedAgainst = "016cada"; :>> judgedAt = "2026-08-24"; :>> judgedBy = "claudeFable5"; }
    part decisionAuthoringIsCoreRefineGateR2 : TestResult { :>> id = "41afecf4-8fe4-4f44-bd00-f5315b770728"; :>> outcome = VerdictKind::pass; :>> judgedAgainst = "016cadaa627a5dda4345e66d1167859e60e8e5ec"; :>> judgedAt = "2026-08-24"; :>> judgedBy = "claudeFable5"; }
    verification decisionAuthoringIsCoreStandupGate : Test { :>> id = "4d08eefa-6866-47d5-9f7c-b1b7dc7cd785"; :>> title = "Sprint 461 standup gate"; :>> createdAt = "2026-08-24"; :>> createdBy = "claudeFable5"; :>> method = VerificationMethod::inspect; :>> procedureText = "Approach: make guards core by REMOVING claims rather than adding a Rust special case, so the existing rule (unclaimed means core) is applied rather than excepted. For the injection, refuse at the write path and ALSO build the easy road, because a lesson is not a control and friction is the top risk. Calibrate the detector against the whole existing corpus before trusting it. .engine/processes/ and .engine/contracts/ are keystone-locked, so D0223 and D0224 co-commit. No blockers."; }
    part decisionAuthoringIsCoreStandupGateR1 : TestResult { :>> id = "542ba44a-03db-4bff-b824-6db7a0ffa7e5"; :>> outcome = VerdictKind::pass; :>> judgedAgainst = "016cada"; :>> judgedAt = "2026-08-24"; :>> judgedBy = "claudeFable5"; }
    part decisionAuthoringIsCoreStandupGateR2 : TestResult { :>> id = "553a0260-0c83-4ed5-a151-f4603c656a8b"; :>> outcome = VerdictKind::pass; :>> judgedAgainst = "016cadaa627a5dda4345e66d1167859e60e8e5ec"; :>> judgedAt = "2026-08-24"; :>> judgedBy = "claudeFable5"; }
    verification decisionAuthoringIsCoreImplementGate : Test { :>> id = "3ec162db-39bc-4cd1-8c14-34c2a63e2a0a"; :>> title = "Sprint 461 implement gate"; :>> createdAt = "2026-08-24"; :>> createdBy = "claudeFable5"; :>> method = VerificationMethod::test; :>> procedureText = "Verified by read-back, not by report. All five guards read CORE; keel deactivate decision-authoring REFUSES with the accurate message; hardening moved decisionAuthoring from undeclared to enforced, 15 to 16, accountedPct 89; audit-adherence treats Active to Core as a strengthening and does not flag it. The D0223 injection and the D0214 transcript are each refused by name with the offending region quoted; a clean decision quoting guard names still records; D0224 was itself recorded through --from. validate 512 clean, all 49 guards ALL PASS, check-engine clean, rules 0 violations, clippy clean, 264 + 9 + 1 + 32 tests pass across every target."; }
    part decisionAuthoringIsCoreImplementGateR1 : TestResult { :>> id = "0c4e8b0f-d0d7-44a7-a3a9-bc707b4e28f7"; :>> outcome = VerdictKind::pass; :>> judgedAgainst = "016cada"; :>> judgedAt = "2026-08-24"; :>> judgedBy = "claudeFable5"; }
    part decisionAuthoringIsCoreImplementGateR2 : TestResult { :>> id = "064130cb-e2a8-4727-ae83-f145cef4e734"; :>> outcome = VerdictKind::pass; :>> judgedAgainst = "016cadaa627a5dda4345e66d1167859e60e8e5ec"; :>> judgedAt = "2026-08-24"; :>> judgedBy = "claudeFable5"; }
    verification decisionAuthoringIsCoreReviewGate : Test { :>> id = "6b487893-bca8-4333-b37c-2374a20946f2"; :>> title = "Sprint 461 review gate — three passes per D0172"; :>> createdAt = "2026-08-24"; :>> createdBy = "claudeFable5"; :>> method = VerificationMethod::inspect; :>> procedureText = "PASS 1, CLAIMS: every number above is a quoted read-back from the tool, including the 13,136-character measurement of the landed dump. PASS 2, BOUNDARY: (i) the detector is a HEURISTIC over two observed shapes and will miss tool output that is neither JSON-shaped nor a guard transcript - it narrows the hole, and the durable protection is --from, which the refusal message teaches; (ii) the transcript threshold was calibrated at four strong markers because authored prose quotes guard lines as evidence and an earlier draft refused D0213's context for doing so - deliberately conservative; (iii) making decision-authoring core removes a downstream project's ability to opt out of Decision discipline, which is a real cost, stated in D0223 rather than buried. PASS 3, OWN DIFF: the honest finding is that the control was written because I broke the thing it protects, in the same turn, in a script I wrote. Worse, the FIRST draft of the detector caught only the shape I had just produced; it took investigating an unread warning-severity rule flag to discover the class had already landed and been accepted months of commits ago. WHAT A REVIEWER SHOULD ATTACK: whether excising 13,136 characters from an ACCEPTED Decision is a legitimate correction or an edit to an attested record. The defence is that the acceptance receipt is untouched and the excised text was never authored by anyone - but the reviewer is right to look, and D0214 is the place to look."; }
    part decisionAuthoringIsCoreReviewGateR1 : TestResult { :>> id = "de54fb5a-b32b-4753-875d-e4c0880334f8"; :>> outcome = VerdictKind::pass; :>> judgedAgainst = "016cada"; :>> judgedAt = "2026-08-24"; :>> judgedBy = "claudeFable5"; }
    part decisionAuthoringIsCoreReviewGateR2 : TestResult { :>> id = "19996a42-70ff-4417-a4ca-576af47bea34"; :>> outcome = VerdictKind::pass; :>> judgedAgainst = "016cadaa627a5dda4345e66d1167859e60e8e5ec"; :>> judgedAt = "2026-08-24"; :>> judgedBy = "claudeFable5"; }
    verification decisionAuthoringIsCoreCloseOutGate : Test { :>> id = "027cde7c-82a1-4ec6-9660-3c2d8c04d79e"; :>> title = "Sprint 461 closeOut gate (autonomous, D0049)"; :>> createdAt = "2026-08-24"; :>> createdBy = "claudeFable5"; :>> method = VerificationMethod::inspect; :>> procedureText = "Autonomous closeOut (D0049). issue254, issue255 and issue256 resolved. The five Decision-authoring guards can no longer be switched off, and a governance record can no longer silently contain what nobody wrote. validate + all 49 guards + check-engine + rules green at 016cada."; }
    part decisionAuthoringIsCoreCloseOutGateR1 : TestResult { :>> id = "b087296c-ada8-4d36-8153-831723c34604"; :>> outcome = VerdictKind::pass; :>> judgedAgainst = "016cada"; :>> judgedAt = "2026-08-24"; :>> judgedBy = "claudeFable5"; }
    part decisionAuthoringIsCoreCloseOutGateR2 : TestResult { :>> id = "ecb71d90-db73-4fc7-bf36-5594f58f32b8"; :>> outcome = VerdictKind::pass; :>> judgedAgainst = "016cadaa627a5dda4345e66d1167859e60e8e5ec"; :>> judgedAt = "2026-08-24"; :>> judgedBy = "claudeFable5"; }
    verification decisionAuthoringIsCoreRetroGate : Test { :>> id = "1ca1d54e-ac3b-43fd-b47c-a8b11def5449"; :>> title = "Sprint 461 retro gate (autonomous, D0049)"; :>> createdAt = "2026-08-24"; :>> createdBy = "claudeFable5"; :>> method = VerificationMethod::analyze; :>> procedureText = "Autonomous retro (D0049). AVOIDABLE-ISSUE SCAN under rcRecurrence: (1) THE recurrence, eighth instance this session and the first to damage a RECORD rather than a build: shell escaping. Every prior instance announced itself with a red build; this one produced a file that parsed only by luck. The fix had to be a road (--from) and not a rule, because I had already known the rule for seven instances. (2) A warning-severity rule had been flagging the landed D0214 injection the whole time and nobody read it - which is precisely what D0214 ITSELF was recorded to fix, so the unread-warning defect was hiding evidence of its own cause. That is the strongest argument yet for triaging the 79 standing warnings rather than adding detectors. (3) My first detector caught only the instance I had just created; generalising from one observation is how a control ends up fitting the sample instead of the class. WELL: declining the human's premise instead of accepting it is what surfaced issue254 at all - and the same instinct, checking rather than assuming, is what turned an unread warning into issue256. Estimate 3 pts, delivered 3."; }
    part decisionAuthoringIsCoreRetroGateR1 : TestResult { :>> id = "1eb83cc3-b7eb-4cef-80c9-65da776971f6"; :>> outcome = VerdictKind::pass; :>> judgedAgainst = "016cada"; :>> judgedAt = "2026-08-24"; :>> judgedBy = "claudeFable5"; }
    part decisionAuthoringIsCoreRetroGateR2 : TestResult { :>> id = "6095d9ba-e973-4364-ade6-aa4262325132"; :>> outcome = VerdictKind::pass; :>> judgedAgainst = "016cadaa627a5dda4345e66d1167859e60e8e5ec"; :>> judgedAt = "2026-08-24"; :>> judgedBy = "claudeFable5"; }
}
