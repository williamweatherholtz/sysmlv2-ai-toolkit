// ProjectDeliveryS253 — Sprint 253: retro findings become tracked items, not prose (issue085, D0131).
// The process step that was MISSING is the deliverable; the guard only backs it. EXECUTE. 3 pts.
package ProjectDeliveryS253 {
    private import EngineElement::*;
    private import EngineWork::*;
    private import EngineVerification::*;
    private import EngineRelationships::*;

    #CharteredBy dependency from retroToBacklogStory to d0131;

    part retroToBacklogStory : Story {
        :>> id = "0d6c0001-0813-4c01-9b3e-0000001c0001";
        :>> title = "Sprint 253: retroTrack process step + retro-backlog guard (3 pts)";
        :>> createdAt = "2026-08-13"; :>> createdBy = "claudeOpus5"; :>> kind = WorkKind::code; :>> priority = WorkPriority::p0; :>> owner = "claudeOpus5"; :>> estimatedPoints = 3;
    }

    action def DeliveryRunS253 {
        action storyRetroToBacklog;
        verification storyRetroToBacklogDoD : Test { :>> id = "0d6c0002-0813-4c02-9b3e-0000001c0002"; :>> method = VerificationMethod::demo; :>> procedureText = "Delivers dcRetroToBacklog (issue085/D0131). ROOT CAUSE was in the DEFINITION, not the behaviour: the retrospective had ONE step (retroPromote) whose actionText was 'Create a Decision; update Process/schema if needed' and whose owner was Owner::human — stale since D0049 made the retro autonomous — and the obligation to TRACK a finding was never defined anywhere, living only as an expectation in the sprint-retro skill's description. A retro that merely DESCRIBED a lesson therefore passed its gate identically to one that TRACKED it, with no artifact to check. BUILT: (A) PROCESS — three Owner::ai steps in .engine/processes/agile-workflow.sysml: retroIdentify (name what was AVOIDABLE, including findings against this thread's own earlier work), retroTrack (each avoidable issue becomes a tracked Issue with severity PLUS its resolving backlog action at its correct PRIORITY per D0052 — declaration order IS priority, so ranking means placing it in the file — or the retro states why none is needed; writing the lesson into a doc, commit message or agent memory INSTEAD is forbidden, since it then carries no severity/priority/resolver/id and is invisible to orient, D0018), retroPromote (behaviour-changing findings become Decisions via the Change Request path). (B) SKILL — sprint-retro's registered purpose updated so the deploying skill and the process agree (D0059). (C) GUARD — `retro-backlog` (22 guards; 17 hard + 5 warning-only), git-diff-aware in the doc-sync (D0113) shape, satisfied EITHER by a co-recorded tracked item OR by an explicit no-item justification, so it enforces that the CHOICE is explicit rather than that an item always exists. VERIFY: pure-function test covers all four cases (finding + nothing tracked + no reason -> warn; finding + co-staged issues/backlog -> clean; finding + 'no new item' justification -> clean; no findings -> clean, so the guard never DEMANDS findings). D0131 co-committed with the #ProspectiveChange marker, satisfying the D0070 keystone for the process-def change. clippy clean; 155 tests; validate + all 22 guards + check-engine green at ee2512d."; }
        part storyRetroToBacklogDoDR1 : TestResult { :>> id = "0d6c0003-0813-4c03-9b3e-0000001c0003"; :>> outcome = VerdictKind::pass; :>> judgedAgainst = "ee2512d"; :>> judgedAt = "2026-08-13"; :>> judgedBy = "claudeOpus5"; }
    }

    verification rbRefineGate : Test { :>> id = "0d6c0004-0813-4c04-9b3e-0000001c0004"; :>> title = "Sprint 253 refine gate (DoR)"; :>> createdAt = "2026-08-13"; :>> createdBy = "claudeOpus5"; :>> method = VerificationMethod::inspect; :>> procedureText = "DoR: taken from the top of the ranked frontier by ORDER (D0052). Scope: the process step, the skill, the guard, and the governing Decision — a process-def change requires a co-committed #ProspectiveChange Decision (D0070 keystone), so D0131 is in scope by necessity, not choice. EXCLUDED: retro-converting the two sprint-247 lessons that escaped into prose — they are already durable guidance in CLAUDE.md section 6 and re-tracking them now would be theatre; issue085 stays the record that they escaped. estimatedPoints=3. DoR met."; }
    part rbRefineGateR1 : TestResult { :>> id = "0d6c0005-0813-4c05-9b3e-0000001c0005"; :>> outcome = VerdictKind::pass; :>> judgedAgainst = "ee2512d"; :>> judgedAt = "2026-08-13"; :>> judgedBy = "claudeOpus5"; }

    verification rbStandupGate : Test { :>> id = "0d6c0006-0813-4c06-9b3e-0000001c0006"; :>> title = "Sprint 253 standup gate"; :>> createdAt = "2026-08-13"; :>> createdBy = "claudeOpus5"; :>> method = VerificationMethod::inspect; :>> procedureText = "Approach: read the PROCESS DEFINITION before writing the check, on the theory that a repeatedly-skipped obligation is usually undefined rather than disobeyed. That was correct and was the sprint's main finding — the retro step was a stale single human-owned line predating D0049. Design the guard around an explicit ESCAPE (say why no item is needed) rather than an absolute demand, so it cannot manufacture duplicate Issues; a noisy guard gets ignored, which is how D0113's own lesson was learned. No blockers."; }
    part rbStandupGateR1 : TestResult { :>> id = "0d6c0007-0813-4c07-9b3e-0000001c0007"; :>> outcome = VerdictKind::pass; :>> judgedAgainst = "ee2512d"; :>> judgedAt = "2026-08-13"; :>> judgedBy = "claudeOpus5"; }

    verification rbImplementGate : Test { :>> id = "0d6c0008-0813-4c08-9b3e-0000001c0008"; :>> title = "Sprint 253 implement gate"; :>> createdAt = "2026-08-13"; :>> createdBy = "claudeOpus5"; :>> method = VerificationMethod::demo; :>> procedureText = "Implemented at ee2512d. The process/skill/guard trio was kept consistent in ONE commit — process defines the obligation, skill deploys it, guard backs it — which is the D0059 shape and avoids the state this sprint was fixing (an expectation with no owning definition). The keystone guard (D0070) forced D0131 into the same commit, which is the control working as designed rather than an obstacle."; }
    part rbImplementGateR1 : TestResult { :>> id = "0d6c0009-0813-4c09-9b3e-0000001c0009"; :>> outcome = VerdictKind::pass; :>> judgedAgainst = "ee2512d"; :>> judgedAt = "2026-08-13"; :>> judgedBy = "claudeOpus5"; }

    verification rbReviewGate : Test { :>> id = "0d6c000a-0813-4c0a-9b3e-0000001c000a"; :>> title = "Sprint 253 review gate"; :>> createdAt = "2026-08-13"; :>> createdBy = "claudeOpus5"; :>> method = VerificationMethod::inspect; :>> procedureText = "Reviewed. The important half is the PROCESS, not the guard: the previous state proves that an expectation living only in a skill description is unenforceable and unarguable — there was nothing to point at when it was skipped. Also corrected in passing: the retro step's Owner::human was stale by ~200 sprints relative to D0049's autonomous-ceremony decision, which is itself a small instance of the doc/definition drift the doc-sync guard exists for. Weakness accepted: the guard reads the WORKING TREE rather than the index, so a partially-staged sprint file could be misread — stated in the doc comment and one more reason it warns rather than blocks."; }
    part rbReviewGateR1 : TestResult { :>> id = "0d6c000b-0813-4c0b-9b3e-0000001c000b"; :>> outcome = VerdictKind::pass; :>> judgedAgainst = "ee2512d"; :>> judgedAt = "2026-08-13"; :>> judgedBy = "claudeOpus5"; }

    verification rbCloseOutGate : Test { :>> id = "0d6c000c-0813-4c0c-9b3e-0000001c000c"; :>> title = "Sprint 253 closeOut gate (autonomous, D0049)"; :>> createdAt = "2026-08-13"; :>> createdBy = "claudeOpus5"; :>> method = VerificationMethod::inspect; :>> procedureText = "Autonomous closeOut (D0049). dcRetroToBacklog carries a passing DoD TestResult at ee2512d; validate + all 22 guards + check-engine green; 155 tests; clippy clean. ALL FOUR tracking-mechanism controls from sprint 248 are now delivered: verification-trace (issue082), attestation-substance (issue083), priority-inversion (issue084), retro-backlog (issue085). D0131 is PROPOSED and awaits the human alongside the per-sitting review. Frontier advances to dcStaleKernelInstanceGate (issue081, High)."; }
    part rbCloseOutGateR1 : TestResult { :>> id = "0d6c000d-0813-4c0d-9b3e-0000001c000d"; :>> outcome = VerdictKind::pass; :>> judgedAgainst = "ee2512d"; :>> judgedAt = "2026-08-13"; :>> judgedBy = "claudeOpus5"; }

    verification rbRetroGate : Test { :>> id = "0d6c000e-0813-4c0e-9b3e-0000001c000e"; :>> title = "Sprint 253 retro gate (autonomous, D0049)"; :>> createdAt = "2026-08-13"; :>> createdBy = "claudeOpus5"; :>> method = VerificationMethod::analyze; :>> procedureText = "Autonomous retro (D0049) — the first run under D0131's own retroTrack step, and it is applied to itself. WELL: (1) looking at the process DEFINITION before writing the check found the real cause (an undefined obligation, plus an Owner::human that D0049 had invalidated ~200 sprints earlier) rather than treating repeated non-compliance as a discipline problem; (2) the guard was given an explicit escape hatch, so it forces a stated choice instead of manufacturing duplicate Issues; (3) the previous sprint's OBSERVATION — that a new control tends to find far more than the instance motivating it — was honoured by not predicting a count for this one, which is diff-scoped and correctly finds nothing on a clean commit. AVOIDABLE-ISSUE 1: clippy rejected `p.ends_with(\".sysml\")` as a case-sensitive extension comparison, a lint I have now hit repeatedly in this codebase without internalising it. NO NEW ITEM — clippy already IS the permanent automated control for this class and it caught it before commit, which is exactly the intended behaviour; recorded here so a pattern of the same lint recurring is visible. NO OTHER FINDINGS: correct for a well-scoped sprint, not a failure to look. Estimate 3 pts, delivered."; }
    part rbRetroGateR1 : TestResult { :>> id = "0d6c000f-0813-4c0f-9b3e-0000001c000f"; :>> outcome = VerdictKind::pass; :>> judgedAgainst = "ee2512d"; :>> judgedAt = "2026-08-13"; :>> judgedBy = "claudeOpus5"; }
}
