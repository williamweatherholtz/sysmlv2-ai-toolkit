// ProjectDeliveryS342 — Sprint 342: measured the performance question and got it wrong three times before
// getting it right; redesigned D0161 after the human called draft 1 low value. EXECUTE. 5 pts.
package ProjectDeliveryS342 {
    private import EngineElement::*;
    private import EngineWork::*;
    private import EngineVerification::*;
    private import EngineRelationships::*;

    #CharteredBy dependency from perfDiagStory to d0161;

    part perfDiagStory : Story {
        :>> id = "0d800510-0814-6510-9b3e-000000300510";
        :>> title = "Sprint 342: perf diagnosis (issue142) + D0161 second draft as a retrieval index (5 pts)";
        :>> createdAt = "2026-08-18"; :>> createdBy = "claudeOpus5"; :>> kind = WorkKind::research; :>> priority = WorkPriority::p0; :>> owner = "claudeOpus5"; :>> estimatedPoints = 5;
    }

    action def DeliveryRunS342 {
        action storyPerfDiag;
        verification storyPerfDiagDoD : Test { :>> id = "0d800511-0814-6511-9b3e-000000300511"; :>> method = VerificationMethod::analyze; :>> procedureText = "TWO PARTS, and the first one is mostly a record of my own bad measurement. (1) PERFORMANCE, issue142: the human asked why SysML ingestion is slow and whether threading is missing. IT IS NOT INGESTION AND THREADING IS NOT THE LEVER — one full parse of all 577 files (6.0 MB) costs about 156ms, against a 65ms process-startup baseline. The real finding is recomputation: only the JSON OUTPUT is cached, never the parsed model; view.rs holds 74 Model::build call sites; composite views call other views; and a cold burst of the eight endpoints a console load requests takes 5.2s where the same burst warm takes 0.5s — a ten-fold gap that is entirely recomputation. I ALSO REVERTED MY OWN FIX: memoising two git helpers looked like a 31% win on single samples, and five runs of each build showed the memo (3565-3709ms) and the baseline (3625-3892ms) are statistically identical, so the change was reverted rather than landed on an unverifiable claim. (2) KNOWLEDGE, D0161 second draft: the human called draft 1 low value and said what they want — keel storing knowledge about ITSELF, why it is designed as it is, to drive decisions. That reasoning is already authored (161 Decisions with both context and rationale, 88 requirement rationales, 1540 typed edges) and the traversal machinery already exists, so the redesign is a RETRIEVAL INDEX — declared questions plus a lexicon — rather than a second corpus. validate 370 clean; check-engine clean; 35 guards ALL PASS; 229 tests; clippy clean; no net code change."; }
        part storyPerfDiagDoDR1 : TestResult { :>> id = "0d800512-0814-6512-9b3e-000000300512"; :>> outcome = VerdictKind::pass; :>> judgedAgainst = "860cb10"; :>> judgedAt = "2026-08-18"; :>> judgedBy = "claudeOpus5"; }
    }

    verification pdRefineGate : Test { :>> id = "0d800513-0814-6513-9b3e-000000300513"; :>> title = "Sprint 342 refine gate (DoR)"; :>> createdAt = "2026-08-18"; :>> createdBy = "claudeOpus5"; :>> method = VerificationMethod::inspect; :>> procedureText = "DoR. The performance question was taken as a MEASUREMENT task rather than an optimisation task, which was right, and I then executed it badly three times before getting a defensible number. The knowledge question was taken as a REDESIGN rather than a defence of draft 1, which the human's two words ('low value?') warranted: they followed it with exactly what they wanted, and draft 1 did not serve it. estimatedPoints=5."; }
    part pdRefineGateR1 : TestResult { :>> id = "0d800514-0814-6514-9b3e-000000300514"; :>> outcome = VerdictKind::pass; :>> judgedAgainst = "860cb10"; :>> judgedAt = "2026-08-18"; :>> judgedBy = "claudeOpus5"; }

    verification pdStandupGate : Test { :>> id = "0d800515-0814-6515-9b3e-000000300515"; :>> title = "Sprint 342 standup gate"; :>> createdAt = "2026-08-18"; :>> createdBy = "claudeOpus5"; :>> method = VerificationMethod::inspect; :>> procedureText = "Approach: measure before changing anything, and measure the harness that matters — a CLI run is one view per process, which is precisely the case where memoisation has nothing to reuse, so the server burst is the right harness for a caching change. Revise draft 1 of D0161 IN PLACE rather than proposing a rival: it is mine, it was never accepted, and one governance home per question (D0105) applies to a question whose answer changed as much as to one whose answer held. No blockers."; }
    part pdStandupGateR1 : TestResult { :>> id = "0d800516-0814-6516-9b3e-000000300516"; :>> outcome = VerdictKind::pass; :>> judgedAgainst = "860cb10"; :>> judgedAt = "2026-08-18"; :>> judgedBy = "claudeOpus5"; }

    verification pdImplementGate : Test { :>> id = "0d800517-0814-6517-9b3e-000000300517"; :>> title = "Sprint 342 implement gate"; :>> createdAt = "2026-08-18"; :>> createdBy = "claudeOpus5"; :>> method = VerificationMethod::test; :>> procedureText = "THREE MEASUREMENT TRAPS, ALL THREE MINE, ALL THREE RECORDED IN ISSUE142 BECAUSE THEY WILL RECUR. (1) THE FIRST RUN OF A FRESHLY BUILT BINARY IS 10-15x SLOWER on this host: 31.7s and later 34.0s for commands that stably run 2.2s and 3.6s — Windows scanning a newly linked executable. I nearly reported a catastrophic regression from a cosmetic change. (2) REMOVING GIT FROM PATH IS NOT A VALID COST ATTRIBUTION, and this one produced a headline number I stated to the human before catching it. I measured coverage at 4.0s with git and 1.5s without and concluded git was 62% of its cost. Wrong: with git unavailable the code takes DIFFERENT paths — D0050 makes grandfathered_under return None and callers then treat everything as grandfathered — so the experiment removed the WORK GIT'S RESULTS ENABLE, not just the subprocesses. (3) SINGLE SAMPLES: the 31% improvement I measured for the git memos vanished under five-run comparison. THE 33-SECOND FIGURE I HAD BEEN CITING ALL DAY IS ALSO NOT REPRODUCIBLE — a cold eight-endpoint burst is 5.2s — and was most likely taken while a cargo build saturated the machine. It had already propagated into D0161's rationale as a load-bearing measurement, and that rationale is corrected."; }
    part pdImplementGateR1 : TestResult { :>> id = "0d800518-0814-6518-9b3e-000000300518"; :>> outcome = VerdictKind::pass; :>> judgedAgainst = "860cb10"; :>> judgedAt = "2026-08-18"; :>> judgedBy = "claudeOpus5"; }

    verification pdReviewGate : Test { :>> id = "0d800519-0814-6519-9b3e-000000300519"; :>> title = "Sprint 342 review gate"; :>> createdAt = "2026-08-18"; :>> createdBy = "claudeOpus5"; :>> method = VerificationMethod::inspect; :>> procedureText = "Reviewed. THE STRONGEST EVIDENCE THAT D0161's SECOND DRAFT IS RIGHT IS THAT BOTH INVARIANT EXCEPTIONS DISAPPEARED. Draft 1 needed two: a third model (breaking the two-model rule) and computed identity (breaking §1.3's minted UUID). Draft 2 needs neither, for the same stated purpose — there is no third model because the index REFERENCES the existing one, and no computed identity because the entities are existing items that already carry UUIDs. A design requiring two exceptions and a design requiring none, for one purpose, is not a close call, and I should have reached the second by asking what the human wanted to DO rather than by reading the process I had. WHY I REVERTED A WORKING CHANGE: the git memos are correct by construction — D0129 forbids history rewriting, so commit-graph facts are immutable and safely cacheable — but I could not demonstrate a win, and the measurement that motivated them was invalid. Landing mutable global state in the core read path on an undemonstrated benefit is exactly the pattern D0157 and D0159 refuse, and applying that standard to my own optimisation rather than only to other people's features is the point."; }
    part pdReviewGateR1 : TestResult { :>> id = "0d80051a-0814-651a-9b3e-00000030051a"; :>> outcome = VerdictKind::pass; :>> judgedAgainst = "860cb10"; :>> judgedAt = "2026-08-18"; :>> judgedBy = "claudeOpus5"; }

    verification pdCloseOutGate : Test { :>> id = "0d80051b-0814-651b-9b3e-00000030051b"; :>> title = "Sprint 342 closeOut gate (autonomous, D0049)"; :>> createdAt = "2026-08-18"; :>> createdBy = "claudeOpus5"; :>> method = VerificationMethod::inspect; :>> procedureText = "Autonomous closeOut (D0049). issue142 recorded with the measurements and the three traps, triaged to dcSharedParsedModel which is ranked ready. D0161 second draft PROPOSED and awaiting the human. D0159 and D0161 both queued. NO PERFORMANCE FIX SHIPPED, stated plainly rather than buried: the diagnosis is delivered and the optimisation is not, because the one I tried could not be shown to work. The next step is instrumentation — per-phase timing inside Model::build and a per-view parse counter — because three separate wall-clock inferences were wrong and the fourth should not be a guess. validate 370 clean; check-engine clean; 35 guards ALL PASS; 229 tests; clippy clean; the working tree carries no net code change."; }
    part pdCloseOutGateR1 : TestResult { :>> id = "0d80051c-0814-651c-9b3e-00000030051c"; :>> outcome = VerdictKind::pass; :>> judgedAgainst = "860cb10"; :>> judgedAt = "2026-08-18"; :>> judgedBy = "claudeOpus5"; }

    verification pdRetroGate : Test { :>> id = "0d80051d-0814-651d-9b3e-00000030051d"; :>> title = "Sprint 342 retro gate (autonomous, D0049)"; :>> createdAt = "2026-08-18"; :>> createdBy = "claudeOpus5"; :>> method = VerificationMethod::analyze; :>> procedureText = "Autonomous retro (D0049) under D0131's retroTrack. AVOIDABLE-ISSUE: I reported a 62% git cost and a 31% improvement to the human, and both were artefacts of bad method — an invalid attribution experiment and single samples. That is the fifth time this session I stated something confidently that checking would have refuted, and the first time the false statement was a NUMBER rather than a claim about the code. Numbers feel like evidence, which is exactly why the method behind them needs the same scrutiny a claim gets: 'measured' is not a synonym for 'true'. THE CONCRETE RULES, now in issue142: discard the first timing after a build; never attribute cost by removing a dependency whose absence changes the code path; five samples minimum before quoting a delta; and measure the harness that matches the change. WELL: (1) the invalid experiment was caught by MY OWN follow-up measurement rather than by the human, and the bad numbers were corrected everywhere they had propagated, including into D0161's rationale; (2) the working change was reverted rather than kept on an undemonstrated benefit; (3) the knowledge redesign was reached by asking what the human wanted to DO, and it dissolved two invariant exceptions — the clearest signal available that the second answer is better than the first. Estimate 5 pts, delivered as a diagnosis plus a redesign, with no optimisation shipped."; }
    part pdRetroGateR1 : TestResult { :>> id = "0d80051e-0814-651e-9b3e-00000030051e"; :>> outcome = VerdictKind::pass; :>> judgedAgainst = "860cb10"; :>> judgedAt = "2026-08-18"; :>> judgedBy = "claudeOpus5"; }
}
