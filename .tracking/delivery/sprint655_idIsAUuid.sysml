// ProjectDeliveryS655 — Sprint 655: Deliver dcIdIsAUuid (issue454): a record written around the write API is caught on its id alone. Guard id-is-a-uuid fails any item dated on/after 2026-09-10 whose id is not an RFC 4122 v4 UUID and any non-v4 id on a line added in the working tree, and counts every earlier or undated failure once by class. D0430 (proposed, process-change) is the co-committed record of the enforcement-surface change.. EXECUTE. 3 pts.
package ProjectDeliveryS655 {
    private import EngineElement::*;
    private import EngineWork::*;
    private import EngineVerification::*;
    private import EngineRelationships::*;

    #CharteredBy dependency from idIsAUuidStory to d0430;

    part idIsAUuidStory : Story {
        :>> id = "52030377-50fc-49bf-bd49-898b3f63ed94";
        :>> title = "Sprint 655: Deliver dcIdIsAUuid (issue454): a record written around the write API is caught on its id alone. Guard id-is-a-uuid fails any item dated on/after 2026-09-10 whose id is not an RFC 4122 v4 UUID and any non-v4 id on a line added in the working tree, and counts every earlier or undated failure once by class. D0430 (proposed, process-change) is the co-committed record of the enforcement-surface change. (3 pts)";
        :>> createdAt = "2026-09-10"; :>> createdBy = "claudeOpus5"; :>> kind = WorkKind::code; :>> priority = WorkPriority::p0; :>> owner = "claudeOpus5"; :>> estimatedPoints = 3;
    }

    action def DeliveryRunS655 {
        action storyIdIsAUuid;
        verification storyIdIsAUuidDoD : Test { :>> id = "6385ff87-cd34-4975-b629-8a906a927fa8"; :>> method = VerificationMethod::test; :>> procedureText = "guards.rs gains is_v4_uuid / uuid_hex_shaped beside uuid_shaped, guard id_is_a_uuid, added_non_v4_ids and non_v4_ids_in; view::id_shape_census classes every model item's id as v4, forward violation (dated on/after the cutoff), history hex-not-v4 or history not-hex; GUARD_NAMES grows to include id-is-a-uuid with its dispatch arm; guards.md gains the row; control-map.sysml gains gIdIsAUuid anchored to ehz6; the backlog DoD's two unprobed clauses (validate refusing undated ids, a history count of roughly 94) are replaced by what the census established. VERIFY: cargo test --lib passes the fixture test (two forward, one history per class), the predicate test and the diff test; the guard PASSES on this tree with HISTORY 88 not-hex equal to the block-aware census; three probes FAIL it - a typed id dated today, an undated non-v4 id in an untracked file, an added typed id in a tracked file; validate, check-engine and guard --no-receipt green with the Decision staged; clippy clean."; }
        // RAN: verifier receipt 2026-09-10T15:27:02Z: cargo test --release -p keel-cli --lib 469 passed 0 failed (fixture, predicate and diff tests among them); keel guard id-is-a-uuid --no-receipt . PASS 15776 scanned, 1 counted-history line; keel validate . 746 clean; keel check-engine . clean; keel guard --no-receipt . exit 0; cargo clippy --release -p keel-cli --all-targets clean
        part storyIdIsAUuidDoDR1 : TestResult { :>> id = "a473ac76-6739-4640-9716-3fa64b94bde4"; :>> outcome = VerdictKind::pass; :>> judgedAgainst = "5f6701dc3b0ee31f8538e1146dade19cb537a1dc"; :>> judgedAt = "2026-09-10T15:27:02Z"; :>> judgedBy = "claudeOpus5"; }
    }

    verification idIsAUuidRefineGate : Test { :>> id = "b6b6cd5e-e749-4fdd-ab04-0a3742d897a4"; :>> title = "Sprint 655 refine gate (DoR)"; :>> createdAt = "2026-09-10"; :>> createdBy = "claudeOpus5"; :>> method = VerificationMethod::inspect; :>> procedureText = "One ready item, 3 points: a view function, a guard with two clauses, registration, a control-map constraint, doc-sync and a DoD correction. Ready: issue454 names the known positive and negative. PROBED BEFORE THE DESIGN: a block-aware census (idscan655.py, scratch) over .tracking and .engine found 0 ids dated on/after 2026-09-10 that fail v4 (216 dated today, all v4), 5,515 hex-shaped ids failing the version or variant nibble and 88 not-hex, 402 of them undated in .tracking - so the DoD's clause 'validate refuses the shape on any undated item' would have turned validate red over an honest tree (D0098), and its history-count claim (roughly 94) had not foreseen the v4 nibble class. Both clauses were replaced in the DoD before the sprint started, the item being open and mine. The replacement for the undated hole is git: an id on an added line of the working tree is new whatever it says."; }
    // RAN: verifier receipt 2026-09-10T15:27:02Z: keel validate . 746 clean; keel advance 655 . cursor at Refine; charter d0430, 3 points set by new sprint --fill
    part idIsAUuidRefineGateR1 : TestResult { :>> id = "7aca4604-245e-4593-9e7d-ebf6dcc8055d"; :>> outcome = VerdictKind::pass; :>> judgedAgainst = "5f6701dc3b0ee31f8538e1146dade19cb537a1dc"; :>> judgedAt = "2026-09-10T15:27:02Z"; :>> judgedBy = "claudeOpus5"; }
    verification idIsAUuidStandupGate : Test { :>> id = "b16a5a12-85c3-4409-aee3-5a34fbb4da5d"; :>> title = "Sprint 655 standup gate"; :>> createdAt = "2026-09-10"; :>> createdBy = "claudeOpus5"; :>> method = VerificationMethod::inspect; :>> procedureText = "No blocker. One finding from the first probe: the diff clause read git diff HEAD, which lists no UNTRACKED file, so an undated typed id in a new file - the exact shape of a fresh sprint record - was counted as history instead of failing. Fixed before any claim: untracked .sysml files under the model roots are scanned whole as added lines. A second finding on myself: the control-map constraint's id was typed by hand in the draft (v4-shaped, so the guard would have passed it - the stated residual); replaced by a generated uuid4 before it landed."; }
    // RAN: verifier receipt 2026-09-10T15:27:02Z: keel check-engine . clean; git status --short unchanged across the run; no blocker
    part idIsAUuidStandupGateR1 : TestResult { :>> id = "12e94646-6a29-4d6c-9a5a-156c133699c1"; :>> outcome = VerdictKind::pass; :>> judgedAgainst = "5f6701dc3b0ee31f8538e1146dade19cb537a1dc"; :>> judgedAt = "2026-09-10T15:27:02Z"; :>> judgedBy = "claudeOpus5"; }
    verification idIsAUuidImplementGate : Test { :>> id = "cb3ac309-666b-4858-94b2-4dccbf8713f8"; :>> title = "Sprint 655 implement gate"; :>> createdAt = "2026-09-10"; :>> createdBy = "claudeOpus5"; :>> method = VerificationMethod::test; :>> procedureText = "keel-cli/src/view/mod.rs: IdShapeCensus { scanned, forward: (item, file, id, date), history_not_hex, history_hex_not_v4 }; id_shape_census(root, cutoff) over Model::build; id_shape_census_of classes each item with an id attr by is_v4_uuid, then by the first present of judgedAt/createdAt/saidAt/acceptedAt against the cutoff. keel-cli/src/guards.rs: uuid_hex_shaped, is_v4_uuid (version nibble at byte 14 = 4, variant at byte 19 in 89ab); id_is_a_uuid reads the census, then git diff HEAD -U0 over .tracking and .engine plus every untracked .sysml there, dedupes by id, and emits one HISTORY line by class; added_non_v4_ids and non_v4_ids_in are pure over text. GUARD_NAMES 68 -> 69 with the dispatch arm. .engine/docs/guards.md: the row. .tracking/architecture/control-map.sysml: gIdIsAUuid (generated id) anchored to ehz6 beside gIdentityWellFormed, whose statement claimed v4 while its guard checked shape - that record is another actor's and is left as written. .tracking/backlog.sysml: dcIdIsAUuidDoD corrected. Tests: id_shape_census_fails_the_two_dated_on_or_after_the_cutoff_and_counts_the_rest (fixture through the real parse), is_v4_uuid_accepts_the_api_shape_and_refuses_shape_alone, added_non_v4_ids_reads_only_added_lines_of_the_diff (including the untracked-file scanner)."; }
    // RAN: verifier receipt 2026-09-10T15:27:02Z: cargo test --release -p keel-cli --lib -- id_shape_census is_v4_uuid added_non_v4_ids 3 passed 0 failed; cargo test --release -p keel-cli --lib 469 passed 0 failed; cargo clippy --release -p keel-cli --all-targets finished clean
    part idIsAUuidImplementGateR1 : TestResult { :>> id = "010cdfcc-c385-4bb7-8116-9cb4ccc2983e"; :>> outcome = VerdictKind::pass; :>> judgedAgainst = "5f6701dc3b0ee31f8538e1146dade19cb537a1dc"; :>> judgedAt = "2026-09-10T15:27:02Z"; :>> judgedBy = "claudeOpus5"; }
    verification idIsAUuidReviewGate : Test { :>> id = "c655b3a9-0637-45f2-8abb-a5ac040f0201"; :>> title = "Sprint 655 review gate — three passes per D0172"; :>> createdAt = "2026-09-10"; :>> createdBy = "claudeOpus5"; :>> method = VerificationMethod::inspect; :>> procedureText = "Probes, each run before the claim (D0388): known negative, the tree at HEAD plus this sprint's staged changes - PASS, 15,768 scanned, HISTORY 5,360 (5,272 hex-not-v4, 88 not-hex; the 88 equals the independent census, the hex figure differs from the census's 5,515 because the model keys items by name and excludes schema dirs, and that class is not the one the guard exists for). Known positives: probe655.sysml untracked with a typed id dated today and an undated hex-not-v4 id - FAIL, 2 violations, one per clause; the typed id a608di4d appended to control-map.sysml (tracked) - FAIL, 1 violation naming the file; probes removed - PASS. guard --no-receipt over the whole set exits 0 with D0430 staged (process-change satisfied); validate 745 clean; check-engine clean; show controls lists gIdIsAUuid anchored. Residual noted: an undated non-v4 id that is also on an added line is counted in the HISTORY figure as well as reported - the count describes the tree, the violation describes the change."; }
    // RAN: verifier receipt 2026-09-10T15:27:02Z: keel guard --no-receipt . exit 0; keel guard id-is-a-uuid --no-receipt . PASS 15776 scanned 0 violations 1 counted-history line; grep id-is-a-uuid in guards.md 1 guards.rs 4 control-map.sysml 1; gIdIsAUuid at control-map.sysml:49 anchored to ehz6 at :124
    part idIsAUuidReviewGateR1 : TestResult { :>> id = "29a6ea26-37d1-4240-8546-588ebeb11dbb"; :>> outcome = VerdictKind::pass; :>> judgedAgainst = "5f6701dc3b0ee31f8538e1146dade19cb537a1dc"; :>> judgedAt = "2026-09-10T15:27:02Z"; :>> judgedBy = "claudeOpus5"; }
    verification idIsAUuidCloseOutGate : Test { :>> id = "e8fab980-b4d0-494b-9883-e987a2830398"; :>> title = "Sprint 655 closeOut gate (autonomous, D0049)"; :>> createdAt = "2026-09-10"; :>> createdBy = "claudeOpus5"; :>> method = VerificationMethod::inspect; :>> procedureText = "Delivered: the guard, its census view, the registration, the row, the constraint, the DoD correction and three unit tests. D0430 stays proposed for the human (D0337); the code lands with it because the enforcement lock reads the marker's presence. Not delivered: validate is unchanged by design, and the guard is a fingerprint, not a proof of authorship - the write ledger (D0424) is the proof."; }
    // RAN: verifier receipt 2026-09-10T15:27:02Z: all twelve verifier steps PASS; keel validate . 746 clean; keel check-engine . clean; keel guard --no-receipt . exit 0
    part idIsAUuidCloseOutGateR1 : TestResult { :>> id = "a9e94025-b128-4130-8b98-e8dba1c33888"; :>> outcome = VerdictKind::pass; :>> judgedAgainst = "5f6701dc3b0ee31f8538e1146dade19cb537a1dc"; :>> judgedAt = "2026-09-10T15:27:02Z"; :>> judgedBy = "claudeOpus5"; }
    verification idIsAUuidRetroGate : Test { :>> id = "92767e13-f322-45d7-9a78-1beb9710be33"; :>> title = "Sprint 655 retro gate (autonomous, D0049)"; :>> createdAt = "2026-09-10"; :>> createdBy = "claudeOpus5"; :>> method = VerificationMethod::analyze; :>> procedureText = "Autonomous retro (D0049). AVOIDABLE-ISSUE SCAN: one avoidable issue, already tracked. Finding 1, avoidable and a recurrence: the DoD of this very item promised a validate clause and a history count from an unprobed hypothesis about the tree - the class issue455 recorded one sprint ago (a DoD figure promised before measurement), now seen twice; its resolver dcGuardPoolDispatchesLongestFirst carries the probe-first rule for the wall clock only, so the recurrence is recorded here for the priority lens (D0311) and no new item is added because D0388 already states the rule the DoD broke and the guard for it would be a DoD-text linter that cannot know what was probed. Finding 2, not avoidable: git diff HEAD omits untracked files; found by the probe, fixed before the claim - the probe-first rule worked as designed. Finding 3, on the agent's own act: a hand-typed id in a draft, caught by reading, not by a control - the guard's stated residual, and the ledger (D0424) is the control that covers it. Finding 4, caught by the control D0425 put there: the primary's tree did not compile - the two guard tests were inserted at an anchor inside parallel_tests, a module that imports nothing, and displaced that module's doc comment - and the primary had run validate, check-engine and every guard against a binary built BEFORE the tests existed, so every check it ran was green over code cargo had never seen. The VERIFIER subagent ran cargo test and reported eleven E0425 errors by line before any result was written; the fix (the module's use line, the doc comment moved back) is in this commit. The primary's own receipt would have said green; the split is what made the red visible. Finding 5, the same receipt on its second pass: the guard had four registration sites in the primary's head and the tree has five - constraint def in .engine/rules/guard-constraints.sysml (D0195 clause 1) was missing, and the catalogue test every_guard_has_a_constraint_def_identity is the control that already existed for exactly that; two deny-level lints on the guard fn went with it. Both found by the verifier running the full lib suite and clippy, neither by the primary."; }
    // RAN: verifier receipt 2026-09-10T15:27:02Z: retro text in F names the AVOIDABLE-ISSUE SCAN and five findings; keel validate . 746 clean after the text landed
    part idIsAUuidRetroGateR1 : TestResult { :>> id = "6be1a7a1-7192-43c1-aead-c524f81b3459"; :>> outcome = VerdictKind::pass; :>> judgedAgainst = "5f6701dc3b0ee31f8538e1146dade19cb537a1dc"; :>> judgedAt = "2026-09-10T15:27:02Z"; :>> judgedBy = "claudeOpus5"; }
}
