// ProjectDeliveryS632 — Sprint 632: Sprint 632: A gesture citation in an acceptance record is written by the surface that observed the gesture and re-verifiable from the record, never typed into a note (dcGestureCitationsAreWrittenByTheCommand, issue426, D0411). EXECUTE under the Change Request route: the substance rule and the command's channel arm are controls. 3 pts.. EXECUTE. 3 pts.
package ProjectDeliveryS632 {
    private import EngineElement::*;
    private import EngineWork::*;
    private import EngineVerification::*;
    private import EngineRelationships::*;

    #CharteredBy dependency from gestureCitationsAreTheCommandsStory to d0411;

    part gestureCitationsAreTheCommandsStory : Story {
        :>> id = "aabb1e07-1c15-4cbc-a702-bbd2db793aab";
        :>> title = "Sprint 632: Sprint 632: A gesture citation in an acceptance record is written by the surface that observed the gesture and re-verifiable from the record, never typed into a note (dcGestureCitationsAreWrittenByTheCommand, issue426, D0411). EXECUTE under the Change Request route: the substance rule and the command's channel arm are controls. 3 pts. (3 pts)";
        :>> createdAt = "2026-09-09"; :>> createdBy = "claudeOpus5"; :>> kind = WorkKind::code; :>> priority = WorkPriority::p0; :>> owner = "claudeOpus5"; :>> estimatedPoints = 3;
    }

    action def DeliveryRunS632 {
        action storyGestureCitationsAreTheCommands;
        verification storyGestureCitationsAreTheCommandsDoD : Test { :>> id = "aa5f2d5c-6c8e-47e1-82a5-78d86339c2e5"; :>> method = VerificationMethod::test; :>> procedureText = "DELIVERED (dcGestureCitationsAreWrittenByTheCommand, resolves issue426 through that item): the console's device receipt is written by the server as [device <full id> hmac=<hex> HMAC-verified] at all five tap sites and on every console acceptance, and device::reverify recomputes it from the record's own fields against the machine-local store (device.rs: CONSOLE_GESTURE, receipt_tag, parse_receipt, reverify, reverify_against; a unit test covers the accept and gate forms, typed words, an altered record, a changed field and an unpaired device); in an agent-marked session with no terminal, verdict_channel_refusal classifies the note (view/mod.rs NoteReceipt, note_receipt) and refuses a gesture word with no quoted span before the write, naming the mechanism and --words; acceptQuotesDelegatedWords carries a second date, 2026-09-09, from which a DELEGATED record evidences its channel only by a quoted span or the observed-TTY citation (checks.rs quotes_delegated_words_strict; raise_cutoffs raises every date a term carries; rules.sysml carries the date); keel-cli/tests/gesture_citation_is_the_commands.rs shows --note 'approved at the console', a typed TTY phrase, a deck word and a GitHub URL refused on accept and reject with nothing written, and --words recording with the declared pair; device_bound_taps.rs re-verifies a live console tap's record from the store and shows the altered record refused; tty_accept_cites_the_gesture.rs and accept_honours_delegation.rs unchanged and green. D0411 records the change (process-change, proposed for the human); CLAUDE.md and guards.md say the rule in the same words."; }
        // RAN: cargo test --release -p keel-cli --lib -> 435 passed; cargo test --release -p keel-cli --test gesture_citation_is_the_commands -> 2 passed; --test device_bound_taps -> 1 passed (step 6 reverify Ok(browser-test01), altered -> does not match); --test accept_honours_delegation -> 3; --test tty_accept_cites_the_gesture -> 2; --test forward_only_cutoff_is_the_projects_own -> 2; keel guard confirmation-authenticity . -> PASS 398 scanned 0 violations; keel validate . -> 717 clean
        part storyGestureCitationsAreTheCommandsDoDR1 : TestResult { :>> id = "34389df4-036b-4569-99db-62ef64184313"; :>> outcome = VerdictKind::pass; :>> judgedAgainst = "7c5d6e5"; :>> judgedAt = "2026-09-09"; :>> judgedBy = "claudeOpus5"; }
    }

    verification gestureCitationsAreTheCommandsRefineGate : Test { :>> id = "962e9ae8-c591-4860-8577-e8a45482496d"; :>> title = "Sprint 632 refine gate (DoR)"; :>> createdAt = "2026-09-09"; :>> createdBy = "claudeOpus5"; :>> method = VerificationMethod::inspect; :>> procedureText = "Definition of Ready: dcGestureCitationsAreWrittenByTheCommand at the head of keel whats-next . after 7c5d6e5 (High, driven by issue426's severity); its DoD names the property, the three surfaces (console receipt, terminal citation, agent arm) and four verifications; the design question - what can an agent session record - has one answer given by the delegation itself (the human's quoted words, D0289), so no fork; 3 points - five source files, a rule text change with a second cutoff, two new integration properties and a Decision."; }
    // RAN: sprint632 Refine: see the record's refine section; cargo test --release -p keel-cli --lib -> 435 passed; five channel integration tests -> 10 passed; cargo clippy --workspace --all-targets -- -D warnings -> Finished; keel guard confirmation-authenticity . -> PASS 398 scanned
    part gestureCitationsAreTheCommandsRefineGateR1 : TestResult { :>> id = "65bd337d-a41b-49aa-903d-61a72e0e84ef"; :>> outcome = VerdictKind::pass; :>> judgedAgainst = "7c5d6e5"; :>> judgedAt = "2026-09-09"; :>> judgedBy = "claudeOpus5"; }
    verification gestureCitationsAreTheCommandsStandupGate : Test { :>> id = "24c9502d-fdfe-4c5f-b0e8-d8334026a53f"; :>> title = "Sprint 632 standup gate"; :>> createdAt = "2026-09-09"; :>> createdBy = "claudeOpus5"; :>> method = VerificationMethod::inspect; :>> procedureText = "No blocker. The one dependency noticed: tty_accept_cites_the_gesture.rs sets CLAUDECODE=1 with the KEEL_TTY_GESTURE stand-in, so the stand-in stays accepted at the command (the TTY arm runs before the agent arm) and is refused only by the substance rule from the strict date - its own record is dated 2026-09-05 and stays green."; }
    // RAN: sprint632 Standup: see the record's standup section; cargo test --release -p keel-cli --lib -> 435 passed; five channel integration tests -> 10 passed; cargo clippy --workspace --all-targets -- -D warnings -> Finished; keel guard confirmation-authenticity . -> PASS 398 scanned
    part gestureCitationsAreTheCommandsStandupGateR1 : TestResult { :>> id = "33ccc990-ebbd-4364-a350-5ee8e04ec8f0"; :>> outcome = VerdictKind::pass; :>> judgedAgainst = "7c5d6e5"; :>> judgedAt = "2026-09-09"; :>> judgedBy = "claudeOpus5"; }
    verification gestureCitationsAreTheCommandsImplementGate : Test { :>> id = "f28d4f48-47ea-4a94-bef2-9d9ed5a2c0be"; :>> title = "Sprint 632 implement gate"; :>> createdAt = "2026-09-09"; :>> createdBy = "claudeOpus5"; :>> method = VerificationMethod::test; :>> procedureText = "device.rs receipt and reverify written through textpatch; serve.rs five device_tag sites take the tap's hmac; checks.rs strict predicate extracted into accept_quotes_delegated_words after clippy's too-many-lines; mod.rs NoteReceipt; main.rs arm; rules.sysml second date; cargo test --release -p keel-cli --lib -> 435 passed; the five channel integration tests -> 10 passed; cargo clippy --workspace --all-targets -- -D warnings -> Finished; keel guard confirmation-authenticity . -> PASS 398 scanned 0 violations on this tree with the strict date in force; keel validate . 717 clean; keel check-engine . clean; keel record decision D0411 --process-change -> proposed, OUTSIDE standing consent."; }
    // RAN: sprint632 Implement: see the record's implement section; cargo test --release -p keel-cli --lib -> 435 passed; five channel integration tests -> 10 passed; cargo clippy --workspace --all-targets -- -D warnings -> Finished; keel guard confirmation-authenticity . -> PASS 398 scanned
    part gestureCitationsAreTheCommandsImplementGateR1 : TestResult { :>> id = "12532b83-b0fc-4b9c-8092-cf4b95507a3c"; :>> outcome = VerdictKind::pass; :>> judgedAgainst = "7c5d6e5"; :>> judgedAt = "2026-09-09"; :>> judgedBy = "claudeOpus5"; }
    verification gestureCitationsAreTheCommandsReviewGate : Test { :>> id = "1a5b2acd-c567-4175-998f-0ed5179bffe7"; :>> title = "Sprint 632 review gate — three passes per D0172"; :>> createdAt = "2026-09-09"; :>> createdBy = "claudeOpus5"; :>> method = VerificationMethod::inspect; :>> procedureText = "Three passes per D0172: (1) the receipt is verified from the record's fields alone - kind, target, judgedAt, judgedBy, signed note - and the test changes each of a field, the text and the store to show each is load-bearing; (2) the refusal message names what was typed, who writes the real citation, and the exact remedy, and the test asserts on the mechanism words and the remedy, not on the exit code alone; (3) the rule's second date is read raised to adoption like the first (two raise_cutoffs cases), so a downstream project adopting after 2026-09-09 is not retro-failed on the day it adopts."; }
    // RAN: sprint632 Review: see the record's review section; cargo test --release -p keel-cli --lib -> 435 passed; five channel integration tests -> 10 passed; cargo clippy --workspace --all-targets -- -D warnings -> Finished; keel guard confirmation-authenticity . -> PASS 398 scanned
    part gestureCitationsAreTheCommandsReviewGateR1 : TestResult { :>> id = "73e62158-4964-4564-8070-b267e1bd3911"; :>> outcome = VerdictKind::pass; :>> judgedAgainst = "7c5d6e5"; :>> judgedAt = "2026-09-09"; :>> judgedBy = "claudeOpus5"; }
    verification gestureCitationsAreTheCommandsCloseOutGate : Test { :>> id = "c1a37642-72fc-4902-afe3-0120a0785be5"; :>> title = "Sprint 632 closeOut gate (autonomous, D0049)"; :>> createdAt = "2026-09-09"; :>> createdBy = "claudeOpus5"; :>> method = VerificationMethod::inspect; :>> procedureText = "keel validate . clean (717 files), keel check-engine . clean, keel gate --fast clean; keel guard . carries the pre-existing warning classes and, for this sprint, the D0064 coverage it supplies; dcGestureCitationsAreWrittenByTheCommand DoD stamped at 7c5d6e5 with the ten integration and five unit assertions named."; }
    // RAN: sprint632 CloseOut: see the record's closeOut section; cargo test --release -p keel-cli --lib -> 435 passed; five channel integration tests -> 10 passed; cargo clippy --workspace --all-targets -- -D warnings -> Finished; keel guard confirmation-authenticity . -> PASS 398 scanned
    part gestureCitationsAreTheCommandsCloseOutGateR1 : TestResult { :>> id = "afda044e-7dce-4371-a807-557bcae9348b"; :>> outcome = VerdictKind::pass; :>> judgedAgainst = "7c5d6e5"; :>> judgedAt = "2026-09-09"; :>> judgedBy = "claudeOpus5"; }
    verification gestureCitationsAreTheCommandsRetroGate : Test { :>> id = "f0cceaab-466e-480c-a8ff-2210ba453156"; :>> title = "Sprint 632 retro gate (autonomous, D0049)"; :>> createdAt = "2026-09-09"; :>> createdBy = "claudeOpus5"; :>> method = VerificationMethod::analyze; :>> procedureText = "Avoidable-issue scan: the gap existed because two surfaces wrote a citation as text and one gate read the text as the citation; the server had the signature in hand and threw it away. The class - a control that verifies a fact and records only the word verified - is what stpa-self run 2 was walking, and issue427 (an override target is a substring) and issue428 (a direction is rendered, not recorded) are the same class on the other two edges; both are tracked with resolvers, so this sprint adds no further item: no new item is needed beyond issue427 and issue428, which the run already tracks."; }
    // RAN: sprint632 Retro: see the record's retro section; cargo test --release -p keel-cli --lib -> 435 passed; five channel integration tests -> 10 passed; cargo clippy --workspace --all-targets -- -D warnings -> Finished; keel guard confirmation-authenticity . -> PASS 398 scanned
    part gestureCitationsAreTheCommandsRetroGateR1 : TestResult { :>> id = "9ff7dd45-ed07-4d3a-8077-49b575b27e60"; :>> outcome = VerdictKind::pass; :>> judgedAgainst = "7c5d6e5"; :>> judgedAt = "2026-09-09"; :>> judgedBy = "claudeOpus5"; }
}
