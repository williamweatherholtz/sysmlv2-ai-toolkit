// ProjectDeliveryS442 — Sprint 442: close the channel-bypass - every accepted decision gets a GitHub override thread regardless of acceptance path (issue238). EXECUTE. 1 pts.
package ProjectDeliveryS442 {
    private import EngineElement::*;
    private import EngineWork::*;
    private import EngineVerification::*;
    private import EngineRelationships::*;

    #CharteredBy dependency from overrideThreadEveryAcceptStory to d0205;

    part overrideThreadEveryAcceptStory : Story {
        :>> id = "633c3dd8-4229-440d-89a8-831b39f608df";
        :>> title = "Sprint 442: the human override surface exists for every decision, not just proposed ones (1 pts)";
        :>> createdAt = "2026-08-24"; :>> createdBy = "claudeFable5"; :>> kind = WorkKind::code; :>> priority = WorkPriority::p0; :>> owner = "claudeFable5"; :>> estimatedPoints = 1;
    }

    action def DeliveryRunS442 {
        action storyOverrideThreadEveryAccept;
        verification storyOverrideThreadEveryAcceptDoD : Test { :>> id = "dd70b1b5-5599-47c9-adbf-22b21a43b180"; :>> method = VerificationMethod::test; :>> procedureText = "DELIVERED: dcOverrideThreadEveryAccept (resolves issue238, D0047 corrections-become-controls). THE DEFECT, caught by the human: I claimed D0209 was overridable on its GitHub issue but no issue existed. D0205 opener (open_decision_issues.py) creates an override-thread issue only for PROPOSED decisions; a decision accepted locally (serve API / keel accept) before its push is already accepted when the workflow runs, so the proposed-only opener skips it - d0207 and d0209 (the two I had pre-accepted) had zero override threads. The standing-override surface the channel exists to give the human could be silently bypassed by my own acceptance path. FIX: ensure_override_threads() runs on every workflow fire and, for EVERY accepted decision numbered >= 205 (the channel birth) with no thread in any state, opens-and-closes an override-thread issue - regardless of acceptance path. Because an acceptance TestResult lands inside the decision own .sysml file, every accept mutates .engine/decisions/*.sysml and fires the workflow, so the sweep runs on every acceptance path, not just new decisions. A true decision is matched by name d + four digits, so acceptance-record cards (d0205AcceptR1) are excluded. VERIFIED: three mocked-gh dry-runs against the real decision-card set - none-exist targets exactly d0205..d0209 (5); all-exist targets 0; only d0207/d0209 missing targets exactly those two (the exact real bypass). END-TO-END: the decision-issue workflow dispatched in production printed no backfill (all five channel-era decisions already have threads), confirming idempotency. Immediate remediation opened #4 (D0207) and #5 (D0209) by hand before the durable control landed."; }
        part storyOverrideThreadEveryAcceptDoDR1 : TestResult { :>> id = "21f2e0c6-f40a-47c2-bb42-72708265c4c1"; :>> outcome = VerdictKind::pass; :>> judgedAgainst = "bc70bcb4c02cff97420c55aa535108b622e5b942"; :>> judgedAt = "2026-08-23"; :>> judgedBy = "claudeFable5"; }
    }

    verification overrideThreadEveryAcceptRefineGate : Test { :>> id = "b8968353-1ab2-4fe1-a792-cdd2df9dbd38"; :>> title = "Sprint 442 refine gate (DoR)"; :>> createdAt = "2026-08-24"; :>> createdBy = "claudeFable5"; :>> method = VerificationMethod::inspect; :>> procedureText = "DoR. Resolves issue238 (channel-bypass, caught by the human). D0047 makes the manual remediation (#4/#5) insufficient - a correction that could recur must become an automated control. Scope: extend open_decision_issues.py so every accepted-post-D0205 decision gets an override thread regardless of acceptance path; verify by dry-run + a production dispatch. 1 point."; }
    part overrideThreadEveryAcceptRefineGateR1 : TestResult { :>> id = "ac8a25c3-5e0a-4a68-b598-1b10e48fe5b9"; :>> outcome = VerdictKind::pass; :>> judgedAgainst = "bc70bcb4c02cff97420c55aa535108b622e5b942"; :>> judgedAt = "2026-08-23"; :>> judgedBy = "claudeFable5"; }
    verification overrideThreadEveryAcceptStandupGate : Test { :>> id = "3fd036d8-432b-4be0-bb07-77af73af61b7"; :>> title = "Sprint 442 standup gate"; :>> createdAt = "2026-08-24"; :>> createdBy = "claudeFable5"; :>> method = VerificationMethod::inspect; :>> procedureText = "Approach: the root cause is that the opener keys on PROPOSED status, but acceptance can precede push. Rather than forbid pre-accept (legitimate under D0207 standing consent), make the guarantee status-agnostic: sweep all accepted decisions >= the channel birth number and backfill any missing thread, idempotently. No blockers - acceptances mutate the decision file, so the existing push trigger already fires on every accept."; }
    part overrideThreadEveryAcceptStandupGateR1 : TestResult { :>> id = "9abbf1bf-a77e-4574-a5f5-027504db2351"; :>> outcome = VerdictKind::pass; :>> judgedAgainst = "bc70bcb4c02cff97420c55aa535108b622e5b942"; :>> judgedAt = "2026-08-23"; :>> judgedBy = "claudeFable5"; }
    verification overrideThreadEveryAcceptImplementGate : Test { :>> id = "79e2104f-1d13-49ac-ae53-ed6098853e4c"; :>> title = "Sprint 442 implement gate"; :>> createdAt = "2026-08-24"; :>> createdBy = "claudeFable5"; :>> method = VerificationMethod::test; :>> procedureText = "Verified by running: three mocked-gh dry-runs against the REAL decision-card set (none-exist -> exactly d0205..d0209; all-exist -> 0; only d0207/d0209 missing -> exactly those two, the exact bypass); the true-decision name filter (d + four digits) excludes acceptance-record cards, a bug caught in the FIRST dry-run which wrongly matched 191 cards before the fix; validate 492 clean; all 48 guards green (after this covering sprint); the decision-issue workflow dispatched in production succeeded and printed no backfill line (correct: all five threads exist)."; }
    part overrideThreadEveryAcceptImplementGateR1 : TestResult { :>> id = "82140b5d-c49b-4e21-9f9a-97ca0b3bc5c6"; :>> outcome = VerdictKind::pass; :>> judgedAgainst = "bc70bcb4c02cff97420c55aa535108b622e5b942"; :>> judgedAt = "2026-08-23"; :>> judgedBy = "claudeFable5"; }
    verification overrideThreadEveryAcceptReviewGate : Test { :>> id = "5b2b5f6e-e0a6-45d5-a111-17df8964192c"; :>> title = "Sprint 442 review gate — three passes per D0172"; :>> createdAt = "2026-08-24"; :>> createdBy = "claudeFable5"; :>> method = VerificationMethod::inspect; :>> procedureText = "PASS 1, CLAIMS: the three dry-run counts and the production-dispatch proposed-decisions-0 with no backfill line are quoted read-backs. PASS 2, BOUNDARY: the sweep fires on .engine/decisions/*.sysml pushes; an accept-only push also touches that path (the AcceptR1 result lands in the decision file), so coverage is every acceptance path - but a decision accepted and NEVER re-pushed after the channel birth would wait until the next decision-file push to get its thread (eventual, idempotent, not instant); stated. Also: the control opens-and-CLOSES the thread (an override surface, not an open ask) - a reject reply still reverses via the recorder. PASS 3, OWN DIFF: the first dry-run exposed my own bug - digit-extracting d0021AcceptR1 yielded 211 and matched 191 non-decisions; running the dry-run BEFORE shipping is what caught it, the lesson being that a control positive test must run against the real card set, not a toy one. WHAT A REVIEWER SHOULD ATTACK: CHANNEL_FROM=205 is a magic number - if the channel birth decision is ever renumbered the floor drifts; it is commented to D0205 but not computed from it."; }
    part overrideThreadEveryAcceptReviewGateR1 : TestResult { :>> id = "4a3526eb-7e46-41bc-893e-5c87cbc99248"; :>> outcome = VerdictKind::pass; :>> judgedAgainst = "bc70bcb4c02cff97420c55aa535108b622e5b942"; :>> judgedAt = "2026-08-23"; :>> judgedBy = "claudeFable5"; }
    verification overrideThreadEveryAcceptCloseOutGate : Test { :>> id = "305b47a1-f4c3-431e-a591-c3252811a74b"; :>> title = "Sprint 442 closeOut gate (autonomous, D0049)"; :>> createdAt = "2026-08-24"; :>> createdBy = "claudeFable5"; :>> method = VerificationMethod::inspect; :>> procedureText = "Autonomous closeOut (D0049). issue238 resolved (open-issues: 0 open / 235 resolved); the control landed at 3b6570f and verified in production by dispatch; validate + all 48 guards green after this covering sprint; #4 and #5 stand as the human override surfaces for D0207/D0209."; }
    part overrideThreadEveryAcceptCloseOutGateR1 : TestResult { :>> id = "ee0c3b5a-dfac-4d81-b241-24fd9ebb228c"; :>> outcome = VerdictKind::pass; :>> judgedAgainst = "bc70bcb4c02cff97420c55aa535108b622e5b942"; :>> judgedAt = "2026-08-23"; :>> judgedBy = "claudeFable5"; }
    verification overrideThreadEveryAcceptRetroGate : Test { :>> id = "4a415af2-3ee9-4163-90f2-130ec5768934"; :>> title = "Sprint 442 retro gate (autonomous, D0049)"; :>> createdAt = "2026-08-24"; :>> createdBy = "claudeFable5"; :>> method = VerificationMethod::analyze; :>> procedureText = "Autonomous retro (D0049). AVOIDABLE-ISSUE SCAN under rcRecurrence: (1) the channel-bypass itself - I recorded acceptances locally before push, outside the surface the channel builds; the durable fix is now the control, not my vigilance. (2) A NEW recurrence of an old class: I shipped a done backlog action without a covering sprint and CI sprint-coverage caught it - I had run validate+guard BEFORE stamping the DoD result, then only re-ran validate, so the regression was invisible locally until CI. Durable lesson: re-run the FULL guard suite after append-result, not just validate, because a passing DoD is exactly what flips sprint-coverage. WELL: the human one-line catch (I don't see a url) surfaced a real hole in the channel and it became a tested control the same session. Estimate 1 pt, delivered 1."; }
    part overrideThreadEveryAcceptRetroGateR1 : TestResult { :>> id = "45fbb51c-e9b6-4eb0-ad5f-afa6cc8beb2b"; :>> outcome = VerdictKind::pass; :>> judgedAgainst = "bc70bcb4c02cff97420c55aa535108b622e5b942"; :>> judgedAt = "2026-08-23"; :>> judgedBy = "claudeFable5"; }
}
