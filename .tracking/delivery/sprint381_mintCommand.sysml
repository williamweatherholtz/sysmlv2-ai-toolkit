// ProjectDeliveryS381 — Sprint 381: `keel mint` — the engine mints identity, and this file's own
// ids are its first real output. EXECUTE. 2 pts.
package ProjectDeliveryS381 {
    private import EngineElement::*;
    private import EngineWork::*;
    private import EngineVerification::*;
    private import EngineRelationships::*;

    #CharteredBy dependency from mintCommandStory to d0173;

    part mintCommandStory : Story {
        :>> id = "58f70a62-176d-4328-b22f-47090496dd96";
        :>> title = "Sprint 381: keel mint [N] - identity is never hand-authored (2 pts)";
        :>> createdAt = "2026-08-21"; :>> createdBy = "claudeOpus5"; :>> kind = WorkKind::code; :>> priority = WorkPriority::p0; :>> owner = "claudeOpus5"; :>> estimatedPoints = 2;
    }

    action def DeliveryRunS381 {
        action storyMintCommand;
        verification storyMintCommandDoD : Test { :>> id = "e568b3a9-591f-424c-8564-2b26e43b2a35"; :>> method = VerificationMethod::test; :>> procedureText = "DELIVERED BACKLOG ITEMS: dcMintCommand. Their instruction (st013): we should be programatically creating UUIDs, not via AI diligence. DONE AS SPECIFIED IN THE DoD: `keel mint [N]` prints N (default 1) engine-minted v4 UUIDs via the same gen_uuid the write API uses (OS CSPRNG, loud abort if unavailable), lowercase, one per line, nothing else on stdout; leading-dash, zero, non-numeric, and extra args are refused with usage at exit 2 per the positional_arg convention; advertised in the help catalogue under its coverage test. Tests: minted ids checked against GUARD 38'S OWN uuid_shaped predicate (one truth, not a re-derivation) with 10000-mint uniqueness; every refusal branch also RUN live against the built binary. 213 unit tests; clippy 0. THIS FILE'S OWN SIXTEEN IDS ARE `keel mint 16` OUTPUT - the first sprint record with no hand-authored identity. Doc-sync rode along: the bridged-session oversight advisory still told sessions to run the DELETED python generator (a Rust string literal, outside guard 39's doc-surface scope - residual noted in the retro); it now names `keel deck`."; }
        part storyMintCommandDoDR1 : TestResult { :>> id = "e54f73ac-b802-4ff2-9dec-c64ec9e3d2f2"; :>> outcome = VerdictKind::pass; :>> judgedAgainst = "36f226e"; :>> judgedAt = "2026-08-21"; :>> judgedBy = "claudeOpus5"; }
    }

    verification mcRefineGate : Test { :>> id = "db11c035-4ea9-4f41-ab2b-ace76f5f888f"; :>> title = "Sprint 381 refine gate (DoR)"; :>> createdAt = "2026-08-21"; :>> createdBy = "claudeOpus5"; :>> method = VerificationMethod::inspect; :>> procedureText = "DoR. Top of the ready frontier (D0052 auto-follow), fully specified by dcMintCommandDoD, no human gate: the DoD names the flag semantics, the refusal behaviour, the catalogue line, and the exact tests. estimatedPoints=2."; }
    part mcRefineGateR1 : TestResult { :>> id = "0a3ba166-17e4-4da5-bf26-f7f70abe6c4e"; :>> outcome = VerdictKind::pass; :>> judgedAgainst = "36f226e"; :>> judgedAt = "2026-08-21"; :>> judgedBy = "claudeOpus5"; }

    verification mcStandupGate : Test { :>> id = "4ea8bf6b-d397-49ac-9199-b7938ec21138"; :>> title = "Sprint 381 standup gate"; :>> createdAt = "2026-08-21"; :>> createdBy = "claudeOpus5"; :>> method = VerificationMethod::inspect; :>> procedureText = "Approach: expose, do not reinvent - gen_uuid already exists, is CSPRNG-backed, and is what the write API mints with; the command is a thin printer over it, and the test asserts against guard 38's own predicate so the minter and the checker cannot drift apart. The bigger consumer (sprint scaffolding) is dcSprintScaffold, next on the frontier. No blockers."; }
    part mcStandupGateR1 : TestResult { :>> id = "f3120478-5dc9-4a49-b10b-b0cfc64e2680"; :>> outcome = VerdictKind::pass; :>> judgedAgainst = "36f226e"; :>> judgedAt = "2026-08-21"; :>> judgedBy = "claudeOpus5"; }

    verification mcImplementGate : Test { :>> id = "05f2e334-cbad-4698-a83c-fa2703f7be8a"; :>> title = "Sprint 381 implement gate"; :>> createdAt = "2026-08-21"; :>> createdBy = "claudeOpus5"; :>> method = VerificationMethod::test; :>> procedureText = "Every claim from a run: `keel mint` prints one, `keel mint 3` prints three, `keel mint 0` / `abc` / `-3` / extra args each refuse with usage at exit 2 - all executed against the built binary, not read from the source (the dcAuthorViaWriteTool rule). uuid_shaped opened to pub(crate) so the test uses the guard's predicate itself. The stale python-generator reference in the oversight advisory was found by GREPPING THE PLACEMENT SITE before adding the catalogue line - the doc-sync habit applied to code strings."; }
    part mcImplementGateR1 : TestResult { :>> id = "0a1966ce-161f-4b45-a9fd-3505b7c16333"; :>> outcome = VerdictKind::pass; :>> judgedAgainst = "36f226e"; :>> judgedAt = "2026-08-21"; :>> judgedBy = "claudeOpus5"; }

    verification mcReviewGate : Test { :>> id = "b92c7225-5912-4f58-b977-54867ed91ce9"; :>> title = "Sprint 381 review gate — three passes per D0172"; :>> createdAt = "2026-08-21"; :>> createdBy = "claudeOpus5"; :>> method = VerificationMethod::inspect; :>> procedureText = "PASS 1, CLAIMS vs emitted/computed: 213 tests, clippy 0, live runs of all six argument shapes, help line present in the built binary's --help output. PASS 2, BOUNDARY: N has deliberately no upper cap because the DoD names none - a runaway `keel mint 999999999` prints for a while and stops, which is composable-tool behaviour, and inventing a cap would be authoring a constraint the item does not carry. PASS 3, OWN DIFF: the catalogue line first shipped without the leading two-space indent its siblings carry - caught by reading the emitted --help, not the source. WHAT A REVIEWER SHOULD ATTACK: guard 39 does not scan Rust string literals, which is where this sprint found its stale reference; noted in the retro as a scoped residual rather than silently absorbed."; }
    part mcReviewGateR1 : TestResult { :>> id = "3d725636-91ce-4fd7-b8a3-cb6af7c57145"; :>> outcome = VerdictKind::pass; :>> judgedAgainst = "36f226e"; :>> judgedAt = "2026-08-21"; :>> judgedBy = "claudeOpus5"; }

    verification mcCloseOutGate : Test { :>> id = "ded28118-8cd4-4922-ad79-e7a50d188e91"; :>> title = "Sprint 381 closeOut gate (autonomous, D0049)"; :>> createdAt = "2026-08-21"; :>> createdBy = "claudeOpus5"; :>> method = VerificationMethod::inspect; :>> procedureText = "Autonomous closeOut (D0049). dcMintCommand's DoD result flipped to pass at the judging HEAD; this record's sixteen ids are the command's first real output; the oversight advisory doc-synced. validate clean; 39 guards ALL PASS; 213 tests; clippy 0."; }
    part mcCloseOutGateR1 : TestResult { :>> id = "8b806c04-6d60-469c-b915-697432b26393"; :>> outcome = VerdictKind::pass; :>> judgedAgainst = "36f226e"; :>> judgedAt = "2026-08-21"; :>> judgedBy = "claudeOpus5"; }

    verification mcRetroGate : Test { :>> id = "7bd1fd74-5662-45dd-9945-79f08ccbd690"; :>> title = "Sprint 381 retro gate (autonomous, D0049)"; :>> createdAt = "2026-08-21"; :>> createdBy = "claudeOpus5"; :>> method = VerificationMethod::analyze; :>> procedureText = "Autonomous retro (D0049). AVOIDABLE-ISSUE SCAN under rcRecurrence: the stale tool reference in a Rust STRING LITERAL is the issue196 family's residual - guard 39 scans the doc surface and deliberately not source comments (historical references there are truthful), but user-facing advisory STRINGS are doc surface that happens to live in code. FIRST occurrence in this location; if a second string-literal staleness appears, the guard grows a strings-in-advisories scope per D0172's second-occurrence rule. WELL: (1) the frontier item was executed exactly to its DoD with nothing invented beyond it - the no-cap choice cites the DoD's silence rather than my preference; (2) the sprint record itself consumed the deliverable, which is the cheapest possible field test; (3) the mint-vs-guard one-truth coupling (test uses the guard's predicate) prevents the drift class where a generator and its checker disagree. Estimate 2 pts, delivered."; }
    part mcRetroGateR1 : TestResult { :>> id = "dc8a7d28-3ffb-4eb6-bf1a-79a51ce24cda"; :>> outcome = VerdictKind::pass; :>> judgedAgainst = "36f226e"; :>> judgedAt = "2026-08-21"; :>> judgedBy = "claudeOpus5"; }
}
