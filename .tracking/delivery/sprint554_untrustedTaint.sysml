// ProjectDeliveryS554 — Sprint 554: the untrusted label travels with the derivation - guard 63 computes the taint closure and only a human's acceptance takes it off. EXECUTE. 5 pts.
package ProjectDeliveryS554 {
    private import EngineElement::*;
    private import EngineWork::*;
    private import EngineVerification::*;
    private import EngineRelationships::*;

    #CharteredBy dependency from untrustedTaintStory to d0314;

    part untrustedTaintStory : Story {
        :>> id = "023b54d4-b5cb-46ed-9072-6be08b3ee1d0";
        :>> title = "Sprint 554: the untrusted label travels with the derivation - guard 63 computes the taint closure and only a human's acceptance takes it off (5 pts)";
        :>> createdAt = "2026-09-05"; :>> createdBy = "claudeOpus5"; :>> kind = WorkKind::code; :>> priority = WorkPriority::p0; :>> owner = "claudeOpus5"; :>> estimatedPoints = 5;
    }

    action def DeliveryRunS554 {
        action storyUntrustedTaint;
        verification storyUntrustedTaintDoD : Test { :>> id = "191c2cc7-aa36-4099-9cb6-9c055afa4da4"; :>> method = VerificationMethod::test; :>> procedureText = "DELIVERED BACKLOG ITEMS: dcUntrustedTaintClosure (D0314; resolves issue347). DONE: guard 63 untrusted-taint - from every SourceTrust::untrusted utterance, breadth-first over #DerivedFrom, #Implicates, #CharteredBy and #Resolves, a violation naming the whole path when the label reaches an AUTO-accepted Decision or a DONE task; a HUMAN-accepted Decision on the path stops the walk; a saidBy login mapped to a declared decider is the human speaking and is not a source. Constraint def, guards.md row, control-map anchor gUntrustedTaint (ehz2, ehz3), CLAUDE.md §4. Arming on the binary: keel-cli/tests/untrusted_taint.rs - the DoD's exact chain red naming the path, green with a human acceptance, green with the decider as speaker."; }
        // RAN: same suite receipt: 498/0 exit 0; gate --workspace at commit
        part storyUntrustedTaintDoDR1 : TestResult { :>> id = "1ea6f882-6ef7-4dec-b179-86993161c4ef"; :>> outcome = VerdictKind::pass; :>> judgedAgainst = "95493091e898d6c1257c5c4097b86c26428965a0"; :>> judgedAt = "2026-09-05"; :>> judgedBy = "claudeOpus5"; }
    }

    verification untrustedTaintRefineGate : Test { :>> id = "c5217916-9c12-424c-aa80-65b1aaa15785"; :>> title = "Sprint 554 refine gate (DoR)"; :>> createdAt = "2026-09-05"; :>> createdBy = "claudeOpus5"; :>> method = VerificationMethod::inspect; :>> procedureText = "READY: issue347 named the laundering precisely (D0291 auto-accept after an untrusted story) and guard 56 already had the untrusted population and the first-hop edge parse. The design question was where trust is conferred: a Decision a human accepted - the DoD's answer - and, found by the first live run, the speaker themself when the login is a declared decider."; }
    verification untrustedTaintStandupGate : Test { :>> id = "56d584d6-ac94-4ce2-8f3e-e86dd5f51245"; :>> title = "Sprint 554 standup gate"; :>> createdAt = "2026-09-05"; :>> createdBy = "claudeOpus5"; :>> method = VerificationMethod::inspect; :>> procedureText = "THE LIVE RUN DECIDED THE RULE: measured before the decider rule, the closure found three violations - d0268 and d0292 auto-accepted, dcUnknownFlagIsRefused done - and every one descended from an issue williamweatherholtz filed on their own public repository (st052, st076, st058), which the human had already said were essentially from them (st089). Refusing them would police the human, which governance never does; github-actors.toml is the committed login-to-human table the decision channel already trusts, so a mapped login confers trust at the source while the untrusted label on the record stays exactly as written (D0264). After the rule: 26 utterances, 0 violations. A proposed Decision is never a violation - planning is the tier untrusted input is allowed."; }
    verification untrustedTaintImplementGate : Test { :>> id = "91a1ff38-c100-4b6e-b542-1351385fde44"; :>> title = "Sprint 554 implement gate"; :>> createdAt = "2026-09-05"; :>> createdBy = "claudeOpus5"; :>> method = VerificationMethod::test; :>> procedureText = "RAN: cargo clippy -D warnings clean; cargo test --test untrusted_taint 2 passed; lib taint tests 4 passed (edges, closure, acceptance kind, decider source); keel validate . 632 clean; check-engine clean; keel guard . ALL PASS with untrusted-taint 26 scanned 0 violations; the full suite in the background to completion (receipt on the DoD result)."; }
    verification untrustedTaintReviewGate : Test { :>> id = "530aea81-5095-4788-8cb9-4c831338ce9e"; :>> title = "Sprint 554 review gate — three passes per D0172"; :>> createdAt = "2026-09-05"; :>> createdBy = "claudeOpus5"; :>> method = VerificationMethod::inspect; :>> procedureText = "THREE PASSES. (1) DOES THE DECIDER RULE REOPEN THE HOLE: only for logins the project itself committed to github-actors.toml, which GitHub authenticated on the issue - the same trust the acceptance channel already extends; a stranger cannot claim one. (2) IS AUTO-ACCEPTED THE RIGHT SINK: yes - the failure issue347 names is an acceptance nobody gave, and the guard keeps walking below it so the built task is named too. (3) THE RESIDUAL: a guard, contract or hook edit carries no edge and is caught only as a done task; the keystone lock is its Decision - stated in the guard doc and D0314."; }
    verification untrustedTaintCloseOutGate : Test { :>> id = "bcbe040f-7138-42ad-97bd-64ab36c1d57f"; :>> title = "Sprint 554 closeOut gate (autonomous, D0049)"; :>> createdAt = "2026-09-05"; :>> createdBy = "claudeOpus5"; :>> method = VerificationMethod::inspect; :>> procedureText = "CLOSED. D0314 accepted under standing consent; GUARD_NAMES 63; issue347 resolved by computation."; }
    verification untrustedTaintRetroGate : Test { :>> id = "0f974aa3-752b-419e-b658-9ca92fd7564f"; :>> title = "Sprint 554 retro gate (autonomous, D0049)"; :>> createdAt = "2026-09-05"; :>> createdBy = "claudeOpus5"; :>> method = VerificationMethod::analyze; :>> procedureText = "no new item - already tracked: the record-time auto-accept still cannot see taint at record time because the #DerivedFrom edge is authored after the Decision exists; dcRecordDecisionDeclaresSupersedes carries the --derived-from flag that would let record decision refuse on the spot, and the guard catches it at the commit either way. The lesson: measure the live tree BEFORE fixing the rule - the three false positives were the human's own words, and the DoD had not anticipated that the decider files public issues too."; }
}
