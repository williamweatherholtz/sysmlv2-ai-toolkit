// ProjectDeliveryS422 — Sprint 422: CI-red hotfix at the root: the parser proptest generator could emit reserved words; it now filters through the lexer's own predicate (issue225). EXECUTE. 1 pts.
package ProjectDeliveryS422 {
    private import EngineElement::*;
    private import EngineWork::*;
    private import EngineVerification::*;
    private import EngineRelationships::*;

    #CharteredBy dependency from proptestReservedWordsStory to d0047;

    part proptestReservedWordsStory : Story {
        :>> id = "dc9f907b-31fb-4901-a690-48f427fa4a99";
        :>> title = "Sprint 422: the generator learns the grammar (1 pts)";
        :>> createdAt = "2026-08-22"; :>> createdBy = "claudeFable5"; :>> kind = WorkKind::code; :>> priority = WorkPriority::p0; :>> owner = "claudeFable5"; :>> estimatedPoints = 1;
    }

    action def DeliveryRunS422 {
        action storyProptestReservedWords;
        verification storyProptestReservedWordsDoD : Test { :>> id = "0714648b-cee0-4496-9555-5809e74d4a8e"; :>> method = VerificationMethod::test; :>> procedureText = "DELIVERED: dcProptestReservedWords (resolves issue225). THE DEFECT: the sprint-421 push went CI-red on prop_part_string_attr - the identifier strategy [a-zA-Z_][a-zA-Z0-9_]{0,31} generated the reserved word 'doc' and the parser CORRECTLY refused it as a bare name; nothing in the push touched the parser, the random seed simply found a latent generator defect that could redden any future push. THE ROOT FIX: the lexer exposes is_reserved_word - implemented as a query against keyword_or_ident itself, never a copied list, so the predicate cannot drift from the grammar - and the proptest strategy filters through it; a deterministic regression pins both halves (reserved words are recognized; 'part doc' is a parse error). VERIFIED: keel-parser suite green including the new regression; full workspace suite 10/10 result-ok; clippy pedantic+nursery clean."; }
        part storyProptestReservedWordsDoDR1 : TestResult { :>> id = "d4c5784f-dacd-4f38-abc7-52b27b78f438"; :>> outcome = VerdictKind::pass; :>> judgedAgainst = "90e38d6c1e7c3d87fd92dd6b13a0d14888b60562"; :>> judgedAt = "2026-08-22"; :>> judgedBy = "claudeFable5"; }
    }

    verification proptestReservedWordsRefineGate : Test { :>> id = "e1c53e72-7da2-4ecf-a6d2-6040a2a211fc"; :>> title = "Sprint 422 refine gate (DoR)"; :>> createdAt = "2026-08-22"; :>> createdBy = "claudeFable5"; :>> method = VerificationMethod::inspect; :>> procedureText = "DoR. D0047 correction: CI red on the prior push must clear at the root, not by re-running until the seed misses. 1 point."; }
    part proptestReservedWordsRefineGateR1 : TestResult { :>> id = "99f39bb0-319a-4eb9-a0fe-40be1a363bcd"; :>> outcome = VerdictKind::pass; :>> judgedAgainst = "90e38d6c1e7c3d87fd92dd6b13a0d14888b60562"; :>> judgedAt = "2026-08-22"; :>> judgedBy = "claudeFable5"; }
    verification proptestReservedWordsStandupGate : Test { :>> id = "13d51d8c-4719-4b85-bb43-33f45fc1ecef"; :>> title = "Sprint 422 standup gate"; :>> createdAt = "2026-08-22"; :>> createdBy = "claudeFable5"; :>> method = VerificationMethod::inspect; :>> procedureText = "Approach: fix the GENERATOR, not the parser - a reserved bare name is correctly an error (kernel semantics), so the property under test ('any valid identifier parses') needed its input domain corrected to match the grammar. Single-source: the filter asks the lexer, the lexer asks its own keyword match. No blockers."; }
    part proptestReservedWordsStandupGateR1 : TestResult { :>> id = "964cb12d-0ca6-4278-b9e6-4343952d436b"; :>> outcome = VerdictKind::pass; :>> judgedAgainst = "90e38d6c1e7c3d87fd92dd6b13a0d14888b60562"; :>> judgedAt = "2026-08-22"; :>> judgedBy = "claudeFable5"; }
    verification proptestReservedWordsImplementGate : Test { :>> id = "ecf93b23-d6bd-4c13-85e6-fc8b45f1bf41"; :>> title = "Sprint 422 implement gate"; :>> createdAt = "2026-08-22"; :>> createdBy = "claudeFable5"; :>> method = VerificationMethod::test; :>> procedureText = "Verified by running: cargo test -p keel-parser (proptest suites + the new reserved_word_is_not_a_bare_identifier regression, all green); full workspace suite 10 result-ok lines, zero failures; clippy clean after one doc-paragraph lint. The failing case is now IMPOSSIBLE by construction rather than improbable by seed."; }
    part proptestReservedWordsImplementGateR1 : TestResult { :>> id = "3c988e91-afbb-4bc5-9151-d9bcccd965b3"; :>> outcome = VerdictKind::pass; :>> judgedAgainst = "90e38d6c1e7c3d87fd92dd6b13a0d14888b60562"; :>> judgedAt = "2026-08-22"; :>> judgedBy = "claudeFable5"; }
    verification proptestReservedWordsReviewGate : Test { :>> id = "1c5550b9-5a7c-434f-86bc-30f02ffb2d4d"; :>> title = "Sprint 422 review gate — three passes per D0172"; :>> createdAt = "2026-08-22"; :>> createdBy = "claudeFable5"; :>> method = VerificationMethod::inspect; :>> procedureText = "PASS 1, CLAIMS: the CI failure text ('expected identifier, got Doc', keel-parser/tests/parser_proptest.rs:39) is quoted from the run 's log; the fix cites it. PASS 2, BOUNDARY: prop_filter discards ~23 strings out of the strategy's space - statistically negligible, and proptest reports filter rejection rates if they ever mattered. PASS 3, OWN DIFF: first doc comment tripped the too-long-first-paragraph lint - machine-caught, split. WHAT A REVIEWER SHOULD ATTACK: quoted-name support ('doc' as a QUOTED identifier is legal SysML v2) is absent from the parser entirely - out of this sprint's scope, visible in parser-coverage's skipped census if it ever bites an instance file."; }
    part proptestReservedWordsReviewGateR1 : TestResult { :>> id = "fbe178a3-677e-4f65-810d-06c771842fe0"; :>> outcome = VerdictKind::pass; :>> judgedAgainst = "90e38d6c1e7c3d87fd92dd6b13a0d14888b60562"; :>> judgedAt = "2026-08-22"; :>> judgedBy = "claudeFable5"; }
    verification proptestReservedWordsCloseOutGate : Test { :>> id = "8ffbbd87-6ebb-4434-bdff-a3f637bceb9a"; :>> title = "Sprint 422 closeOut gate (autonomous, D0049)"; :>> createdAt = "2026-08-22"; :>> createdBy = "claudeFable5"; :>> method = VerificationMethod::inspect; :>> procedureText = "Autonomous closeOut (D0049). issue225 resolves; DoD flipped on the suite read-backs; validate + all 45 guards green; the redden-any-push flake class is closed by construction."; }
    part proptestReservedWordsCloseOutGateR1 : TestResult { :>> id = "738b6370-cd02-47b3-876e-06ced6b9a51d"; :>> outcome = VerdictKind::pass; :>> judgedAgainst = "90e38d6c1e7c3d87fd92dd6b13a0d14888b60562"; :>> judgedAt = "2026-08-22"; :>> judgedBy = "claudeFable5"; }
    verification proptestReservedWordsRetroGate : Test { :>> id = "8c503d47-ebae-4922-b09a-4cb665c67efc"; :>> title = "Sprint 422 retro gate (autonomous, D0049)"; :>> createdAt = "2026-08-22"; :>> createdBy = "claudeFable5"; :>> method = VerificationMethod::analyze; :>> procedureText = "Autonomous retro (D0049). AVOIDABLE-ISSUE SCAN under rcRecurrence: the class is 'a generator whose input domain is wider than the grammar' - the surviving instance to watch is arb_simple_string (attribute values), which is SAFE today because string literals admit any of its output; noted here so a future literal-syntax tightening re-checks it. WELL: the CI-red-check-after-every-push habit caught this within minutes of the push, and the fix landed the same hour - the ci-and-staging-hygiene loop working as intended. Estimate 1 pt, delivered 1."; }
    part proptestReservedWordsRetroGateR1 : TestResult { :>> id = "77898ddf-62dd-4829-aba9-b1bd4d29fc12"; :>> outcome = VerdictKind::pass; :>> judgedAgainst = "90e38d6c1e7c3d87fd92dd6b13a0d14888b60562"; :>> judgedAt = "2026-08-22"; :>> judgedBy = "claudeFable5"; }
}
