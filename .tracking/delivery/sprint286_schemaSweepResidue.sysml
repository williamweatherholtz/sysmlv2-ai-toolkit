// ProjectDeliveryS286 — Sprint 286: complete D0142's sweep; the frozen-core deletion D0145 signs off
// (dcSchemaSweepResidue, issue108). CHANGE. 3 pts.
package ProjectDeliveryS286 {
    private import EngineElement::*;
    private import EngineWork::*;
    private import EngineVerification::*;
    private import EngineRelationships::*;

    #CharteredBy dependency from sweepResidueStory to d0145;

    part sweepResidueStory : Story {
        :>> id = "0d80018c-0814-618c-9b3e-00000030018c";
        :>> title = "Sprint 286: delete the dead risk schema, and contribute its migration step (3 pts)";
        :>> createdAt = "2026-08-15"; :>> createdBy = "claudeOpus5"; :>> kind = WorkKind::modeling; :>> priority = WorkPriority::p0; :>> owner = "claudeOpus5"; :>> estimatedPoints = 3;
    }

    action def DeliveryRunS286 {
        action storySweepResidue;
        verification storySweepResidueDoD : Test { :>> id = "0d80018d-0814-618d-9b3e-00000030018d"; :>> method = VerificationMethod::inspect; :>> procedureText = "Delivers dcSchemaSweepResidue; resolves issue108; governed by D0145 with the human's frozen-core sign-off recorded on that specific change. D0142's sweep removed `Risk`, `Mitigation` and `DesignElement` and left `risk.sysml` HOLLOW — its header and doc string still describing all three, its only content an unreferenced `enum def RiskStatus` — plus an orphaned `RiskLevel` in element.sysml and two docs naming deleted types. DELETED: `risk.sysml` and `RiskLevel`. CORRECTED: architecture.sysml's header (no longer names DesignElement), sysmlv2-syntax-notes.md (no longer lists EngineRisk as importable), and all THREE python schema preload lists, since a list naming a deleted file fails loudly. VERIFIED BEFORE deleting rather than after: zero references to RiskLevel, RiskStatus or EngineRisk anywhere in `.tracking` or `.engine` outside the historical records describing the residue itself. THE KERNEL WAS RUN, non-negotiably — the last two schema deletions in this pass each broke a reference the Rust validator accepted (the `#View item def ICD` removal and the `Release` retarget) — and returned 15/15 files passed; the conformance lane returned 473/473 with no construct rejected. THE MIGRATION STEP IS CONTRIBUTED BY THIS SPRINT, the first to honour that rule: `keel migrate` gains a `REMOVED_ENUMS` blocker for `RiskLevel` and deliberately NOT for `RiskStatus`, an asymmetry no later reconstruction could recover — RiskLevel lived in `element.sysml`, which the engine SHIPS and resync OVERWRITES, so a downstream project assigning `RiskLevel::high` breaks on migrating; RiskStatus lived in `risk.sysml`, which the engine no longer ships, and resync never deletes a file it does not ship, so the project keeps its own copy and blocking would refuse a migration over a type it still owns. Both encoded as tests. clippy clean; 176 tests; validate 308 clean; check-engine clean; 29 guards green."; }
        part storySweepResidueDoDR1 : TestResult { :>> id = "0d80018e-0814-618e-9b3e-00000030018e"; :>> outcome = VerdictKind::pass; :>> judgedAgainst = "b745cc2"; :>> judgedAt = "2026-08-15"; :>> judgedBy = "claudeOpus5"; }
    }

    verification srRefineGate : Test { :>> id = "0d80018f-0814-618f-9b3e-00000030018f"; :>> title = "Sprint 286 refine gate (DoR)"; :>> createdAt = "2026-08-15"; :>> createdBy = "claudeOpus5"; :>> method = VerificationMethod::inspect; :>> procedureText = "DoR. This is the CHANGE route, not EXECUTE: a `schema/core` deletion needs explicit human sign-off (§1.5), which is why it was held at the top of the ready frontier across five sprints rather than auto-followed. The human was asked with the alternatives inline — keep the enums and fix only the docs, or restore Risk/Mitigation with a real instance — and chose deletion. CONSUMER CHECK (dorConsumer, D0144), and it produced the sprint's most interesting output: the consumer of a schema deletion is a downstream project, which surfaced that the two enums have OPPOSITE downstream consequences depending on whether their file is still shipped. estimatedPoints=3. DoR met."; }
    part srRefineGateR1 : TestResult { :>> id = "0d800190-0814-6190-9b3e-000000300190"; :>> outcome = VerdictKind::pass; :>> judgedAgainst = "b745cc2"; :>> judgedAt = "2026-08-15"; :>> judgedBy = "claudeOpus5"; }

    verification srStandupGate : Test { :>> id = "0d800191-0814-6191-9b3e-000000300191"; :>> title = "Sprint 286 standup gate"; :>> createdAt = "2026-08-15"; :>> createdBy = "claudeOpus5"; :>> method = VerificationMethod::inspect; :>> procedureText = "Approach: grep for every reference BEFORE deleting anything, run the kernel on the result, and write the migration step in the same commit. The first two are what the last two schema deletions in this pass skipped and paid for; the third is a rule this project wrote in sprint 281 and has not yet had occasion to follow. No blockers."; }
    part srStandupGateR1 : TestResult { :>> id = "0d800192-0814-6192-9b3e-000000300192"; :>> outcome = VerdictKind::pass; :>> judgedAgainst = "b745cc2"; :>> judgedAt = "2026-08-15"; :>> judgedBy = "claudeOpus5"; }

    verification srImplementGate : Test { :>> id = "0d800193-0814-6193-9b3e-000000300193"; :>> title = "Sprint 286 implement gate"; :>> createdAt = "2026-08-15"; :>> createdBy = "claudeOpus5"; :>> method = VerificationMethod::test; :>> procedureText = "The migration step is the part worth reading. From outside, `RiskLevel` and `RiskStatus` look identically deleted, and a later author reconstructing this change would naturally block on both — which would refuse a downstream migration over a type that project still legitimately owns. The difference is which FILE each lived in and whether the engine still ships it, and that is knowable only while making the change. This is precisely the argument dcProjectMigrationTool's DoD made for the rule that each conversion sprint writes its own step 'when they still know what it changed, not reconstructed later', and it is the first change where following the rule produced something reconstruction would have got wrong."; }
    part srImplementGateR1 : TestResult { :>> id = "0d800194-0814-6194-9b3e-000000300194"; :>> outcome = VerdictKind::pass; :>> judgedAgainst = "b745cc2"; :>> judgedAt = "2026-08-15"; :>> judgedBy = "claudeOpus5"; }

    verification srReviewGate : Test { :>> id = "0d800195-0814-6195-9b3e-000000300195"; :>> title = "Sprint 286 review gate"; :>> createdAt = "2026-08-15"; :>> createdBy = "claudeOpus5"; :>> method = VerificationMethod::inspect; :>> procedureText = "Reviewed. The three python preload lists are the doc-sync catch that mattered: `_schema_files.py`, `validate_all.py` and `validate_workflows.py` each named `risk.sysml` independently, so deleting the file without delisting it would have broken the kernel validators — the tools that gate every future schema change. Three copies of one list is itself the dual-truth smell this engine exists to remove, and it is worth noting as standing debt rather than fixing opportunistically inside a frozen-core sprint. The historical records in `.tracking/issues.sysml` and `.tracking/panel-critiques.sysml` that DESCRIBE the residue keep their references intact, correctly: they are the record of what was found, not live references to a live type."; }
    part srReviewGateR1 : TestResult { :>> id = "0d800196-0814-6196-9b3e-000000300196"; :>> outcome = VerdictKind::pass; :>> judgedAgainst = "b745cc2"; :>> judgedAt = "2026-08-15"; :>> judgedBy = "claudeOpus5"; }

    verification srCloseOutGate : Test { :>> id = "0d800197-0814-6197-9b3e-000000300197"; :>> title = "Sprint 286 closeOut gate (autonomous, D0049)"; :>> createdAt = "2026-08-15"; :>> createdBy = "claudeOpus5"; :>> method = VerificationMethod::inspect; :>> procedureText = "Autonomous closeOut (D0049) — note that closeOut is autonomous while the CHANGE itself was not: D0145 carries the human's explicit frozen-core sign-off on this specific deletion, given with the alternatives stated, never inferred from a standing instruction to proceed. dcSchemaSweepResidue carries a passing DoD TestResult; issue108 resolves. validate_schema.py 15/15; conformance lane 473/473; validate 308 clean; check-engine clean; 29 guards green; JVMs swept. No gate bypassed."; }
    part srCloseOutGateR1 : TestResult { :>> id = "0d800198-0814-6198-9b3e-000000300198"; :>> outcome = VerdictKind::pass; :>> judgedAgainst = "b745cc2"; :>> judgedAt = "2026-08-15"; :>> judgedBy = "claudeOpus5"; }

    verification srRetroGate : Test { :>> id = "0d800199-0814-6199-9b3e-000000300199"; :>> title = "Sprint 286 retro gate (autonomous, D0049)"; :>> createdAt = "2026-08-15"; :>> createdBy = "claudeOpus5"; :>> method = VerificationMethod::analyze; :>> procedureText = "Autonomous retro (D0049) under D0131's retroTrack. WELL: (1) the item was HELD at the top of the ready frontier across five sprints rather than auto-followed, because §1.5 reserves a pause for exactly this and a standing 'proceed without sign-off' does not extend to frozen core — and holding it cost nothing, since the frontier had other work; (2) the human was given the real alternatives inline, including one (restore Risk with an instance) that would have reversed the recommendation, rather than a yes/no framed to be agreed with; (3) the migration step was written in the same commit and immediately produced an asymmetry — RiskLevel blocks, RiskStatus must not — that a later reconstruction would have got wrong in the more expensive direction, refusing a valid migration. AVOIDABLE-ISSUE 1: three separate python files each declare their own copy of the schema preload list, and all three had to be edited to delete one file. Nothing broke, because I grepped for every reference before deleting rather than after, but a single missed copy would have broken the kernel validators that gate every future schema change. NO NEW ITEM, reason stated: it is one-place-per-fact debt in the engine-dev toolchain rather than in the model, and opportunistically refactoring three validator scripts inside a frozen-core sprint is exactly the unexamined ride-along this sprint was split out to avoid. Recorded in this sprint's review gate so it is findable when the toolchain is next touched. Estimate 3 pts, delivered."; }
    part srRetroGateR1 : TestResult { :>> id = "0d80019a-0814-619a-9b3e-00000030019a"; :>> outcome = VerdictKind::pass; :>> judgedAgainst = "b745cc2"; :>> judgedAt = "2026-08-15"; :>> judgedBy = "claudeOpus5"; }
}
