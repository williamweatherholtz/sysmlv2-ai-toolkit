// ProjectDeliveryS503 — Sprint 503: the unattended-distribution plan, and the rollback the rest of it rests on. EXECUTE. 8 pts.
package ProjectDeliveryS503 {
    private import EngineElement::*;
    private import EngineWork::*;
    private import EngineVerification::*;
    private import EngineRelationships::*;

    #CharteredBy dependency from migrationRollsBackStory to d0267;

    part migrationRollsBackStory : Story {
        :>> id = "24aaefbb-c1d1-40d8-ae9e-8f76797820f9";
        :>> title = "Sprint 503: two Needs, seven use cases, five contracts, and a rollback that runs (8 pts)";
        :>> createdAt = "2026-08-31"; :>> createdBy = "claudeOpus5"; :>> kind = WorkKind::code; :>> priority = WorkPriority::p0; :>> owner = "claudeOpus5"; :>> estimatedPoints = 8;
    }

    action def DeliveryRunS503 {
        action storyMigrationRollsBack;
        verification storyMigrationRollsBackDoD : Test { :>> id = "b54b3e46-672d-4837-974f-b4be6de670b4"; :>> method = VerificationMethod::test; :>> procedureText = "DELIVERED (D0267, from st047/st048/st049). THE PLAN: nUnattendedCurrency and nAutonomyBoundedByProof - two Needs from three statements, consolidated by the human's own keyboard principle - seven UseCases of which THREE are failure paths, and five SystemRequirements with thresholds a run either meets or does not. Four tasks in dependency order, each with a #Verify edge to the contract it discharges. THE FIRST INCREMENT, resolving dcMigrationRollsBack and verifying srMigrationIsReversible: migrate records the pre-migration commit, arms a machine-local marker BEFORE the first byte, and restores .engine and .tracking on any detected failure OR on the next run after an interruption. The unverified-re-plan path rolls back too - 'migrated but NOT verified, inspect git diff' was exactly the state reversibility exists to refuse. VERIFY: migration_rolls_back.rs 3/3 with real fault injection (a read-only target so a write fails mid-apply with files already written; the case PANICS if the platform allowed the write, rather than passing on a fault never injected); after a failed or interrupted run git status --porcelain over .engine and .tracking is EMPTY; clippy -D warnings clean; federation 11/11 unaffected.: DELIVERED BACKLOG ITEMS: <items>. <what done means, verified how>."; }
        // RAN: // RAN: migration_rolls_back 3/3 fault-injected; git status --porcelain EMPTY after failure and after interruption; clippy -D warnings clean; federation 11/11
        part storyMigrationRollsBackDoDR1 : TestResult { :>> id = "bfbae439-8b7d-4f03-bd11-ee69af6de9ea"; :>> outcome = VerdictKind::pass; :>> judgedAgainst = "7c12f13"; :>> judgedAt = "2026-08-30"; :>> judgedBy = "claudeOpus5"; }
    }

    verification migrationRollsBackRefineGate : Test { :>> id = "6ea5a1c1-2309-4114-8e4b-9f1b61625854"; :>> title = "Sprint 503 refine gate (DoR)"; :>> createdAt = "2026-08-31"; :>> createdBy = "claudeOpus5"; :>> method = VerificationMethod::inspect; :>> procedureText = "READY: the human asked for the plan first and the plan came from THREE RECORDED UTTERANCES, so no Need here rests on my judgment alone. One scope decision is recorded in the business file rather than hidden: 'see installed versus upstream at a glance' is a gap I proposed and they never asked for, so it is folded into nUnattendedCurrency instead of made its own Need - inventing a Need to hold my own idea would dress my proposal as their demand (D0216)."; }
    verification migrationRollsBackStandupGate : Test { :>> id = "dbf36240-782f-44bb-bc53-a5a496ec66e4"; :>> title = "Sprint 503 standup gate"; :>> createdAt = "2026-08-31"; :>> createdBy = "claudeOpus5"; :>> method = VerificationMethod::inspect; :>> procedureText = "No blocker. The dependency that shaped everything: their chosen gate was CONDITIONAL - 'if you really can guarantee correctness' - so it was tested before being built, and it failed. An empty plan makes migrate return before it re-stamps the pin, so auto-applying one achieves nothing; and an empty plan says nothing about safety anyway, since a new engine can ship guards the existing tree violates. The replacement gate (reversible-and-verified) is a STRONGER guarantee than the one asked for, and it is buildable because migrate already refuses a dirty tree and requires git - so the pre-state is always a commit."; }
    verification migrationRollsBackImplementGate : Test { :>> id = "935005af-599c-4d40-ae38-baa4280910b4"; :>> title = "Sprint 503 implement gate"; :>> createdAt = "2026-08-31"; :>> createdBy = "claudeOpus5"; :>> method = VerificationMethod::test; :>> procedureText = "RAN: cargo test --test migration_rolls_back -> 3/3. The interruption case injects exactly what a killed run leaves - a modified file, a created file, and the marker still on disk - and asserts all three are undone. The write-failure case makes a planned target read-only so the apply genuinely fails partway. clippy -D warnings clean: three lints fixed by EXTRACTING functions (apply_files, arm_marker) and by replacing a set_readonly(false) teardown with attrib, never by suppression. cargo test --test federation -> 11/11 unaffected. THE ASSERTION THAT FAILED AND TAUGHT SOMETHING: the interruption case failed first because recovery ran AFTER check_preconditions - and an interrupted migration leaves the tree dirty, so the dirty-tree precondition refused and a genuine interruption could never be recovered by the command that recovers it. The ordering is the fix; inspection had not found it."; }
    verification migrationRollsBackReviewGate : Test { :>> id = "06c18619-e8a3-4f87-87eb-94e3a013a1ee"; :>> title = "Sprint 503 review gate — three passes per D0172"; :>> createdAt = "2026-08-31"; :>> createdBy = "claudeOpus5"; :>> method = VerificationMethod::inspect; :>> procedureText = "THREE PASSES. (1) IS THE ROLLBACK REAL OR NARRATED: fault-injected, and the injection is itself checked - the read-only case PANICS if the write succeeded anyway, so it cannot pass on a fault that never happened. (2) CAN THE ROLLBACK BECOME THE DEFECT: yes, if a marker outlived a completed run, which would restore a good tree on the next invocation - so a dedicated case asserts a completed migration clears its marker AND that a second run does not 'recover' a finished tree. (3) IS THE GUARANTEE STATED HONESTLY: the two failure classes are separated in the source, because only one is addressable in-process. A killed process runs no code; claiming otherwise would be the overclaiming this project has convicted itself of before."; }
    verification migrationRollsBackCloseOutGate : Test { :>> id = "66d9f48f-4476-4c54-9f38-eaa0e98f255c"; :>> title = "Sprint 503 closeOut gate (autonomous, D0049)"; :>> createdAt = "2026-08-31"; :>> createdBy = "claudeOpus5"; :>> method = VerificationMethod::inspect; :>> procedureText = "CLOSED. dcMigrationRollsBack resolves; srMigrationIsReversible is verified. The next three tasks (dcAutoUpdateVerifiedOrReverted, dcLibraryStatusShowsDrift, dcScheduledCurrency) are planned with their contracts and can now be built on a rollback that exists. NAMED DEBT: the two Needs are PROPOSED, not accepted - per D0157 the human is asked what is wider than they meant, and that gate is theirs."; }
    verification migrationRollsBackRetroGate : Test { :>> id = "f0edfda7-b5ae-43a7-9626-5ba534bb536d"; :>> title = "Sprint 503 retro gate (autonomous, D0049)"; :>> createdAt = "2026-08-31"; :>> createdBy = "claudeOpus5"; :>> method = VerificationMethod::analyze; :>> procedureText = "FINDING: the human's condition was the most valuable thing in the request. 'If you really can guarantee correctness' invited a no, and testing the gate they liked produced one - the empty-plan criterion is inert, and I would have shipped it as a safety feature had I taken the choice at face value. The lesson is not 'test more'; it is that a conditional instruction is an invitation to disagree, and answering it honestly produced a stronger design than the one requested. SECOND FINDING: the ordering bug (recovery after preconditions) was invisible to inspection and obvious to the test within seconds. I wrote the recovery, read it, believed it, and it could not have worked on the exact case it was built for - because the state it recovers from is the state the preconditions refuse."; }
}
