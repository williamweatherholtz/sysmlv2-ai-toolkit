// ProjectDeliveryS221 — Sprint 221: viewerInProgramEdit (INCREMENT) — POST /api/decision + advertised
// write surface. Exposes keel's `record decision` process over HTTP (a status=proposed Decision) and
// advertises KEEL_API_WRITE_ENDPOINTS in /api/version so a generated UI DISCOVERS write actions rather
// than hardcoding them (N-16 / D0117 write half). The backlog action viewerInProgramEdit stays OPEN:
// the remaining pieces (supersede-edge endpoint, inline guard-rejection surfacing, live conflict flag)
// are follow-ups largely realised in the viewer app (shape B). Honest partial. EXECUTE. 2 pts.
package ProjectDeliveryS221 {
    private import EngineElement::*;
    private import EngineWork::*;
    private import EngineVerification::*;
    private import EngineRequirements::*;
    private import EngineRelationships::*;

    #CharteredBy dependency from viewerInProgEditStory to d0117;

    part viewerInProgEditStory : Story {
        :>> id = "63940516-2c7d-4e8f-c221-51627384c001";
        :>> title = "Sprint 221: viewerInProgramEdit increment (2 pts) - POST /api/decision (record process) + advertised write surface (N-16/D0117)";
        :>> createdAt = "2026-07-15"; :>> createdBy = "wweatherholtz"; :>> kind = WorkKind::code; :>> priority = WorkPriority::p2; :>> owner = "claudeOpus"; :>> estimatedPoints = 2;
    }

    action def DeliveryRunS221 {
        action storyViewerInProgEdit;
        verification storyViewerInProgEditDoD : Test { :>> id = "63940516-2c7d-4e8f-c221-51627384c002"; :>> method = VerificationMethod::inspect; :>> procedureText = "INCREMENT toward srViewerInProgramEdit (N-16, human-clarified: modify via keel PROCESSES, not rogue edits). DELIVERED: serve::api_decision serves POST /api/decision, reusing write::record_decision to scaffold a status=proposed Decision (auto NNNN + UUID); acceptance stays a SEPARATE explicit human gate (D0106) — never fabricated, never auto-committed. Added KEEL_API_WRITE_ENDPOINTS (record-Decision + the pre-existing disposition/testresult/resolver) advertised in GET /api/version (bumped 1.5.0) so a generated UI DISCOVERS the write surface rather than hardcoding actions (D0117 generative UI, write half). Contract test extended (writeEndpoints present + /api/decision). VERIFY (inspect): clippy --workspace --all-targets -D warnings clean; cargo test green (api_version contract); live curl against a TEMP root -> POST /api/decision returns D0001 status=proposed, /api/version=1.5.0 reports writeEndpoints; no repo pollution. keel validate + guard + check-engine green. Code @662a109. HONEST SCOPE: the backlog action viewerInProgramEdit stays OPEN — supersede-edge authoring, inline guard-rejection surfacing, and live conflict-detection (D0108) are follow-ups, largely in the viewer app (shape B)."; }
        part storyViewerInProgEditDoDR1 : TestResult { :>> id = "63940516-2c7d-4e8f-c221-51627384c003"; :>> outcome = VerdictKind::pass; :>> judgedAgainst = "662a109"; :>> judgedAt = "2026-07-15"; :>> judgedBy = "claudeOpus"; }
    }

    verification vipRefineGate : Test { :>> id = "63940516-2c7d-4e8f-c221-51627384c004"; :>> title = "Sprint 221 refine gate (DoR)"; :>> createdAt = "2026-07-15"; :>> createdBy = "claudeOpus"; :>> method = VerificationMethod::inspect; :>> procedureText = "DoR: with /api/schema (read half, S220) in place, the generative UI needs a write half. The keel-side gap is record-Decision (disposition/testresult/resolver already exist as endpoints). Increment scoped: POST /api/decision + advertise writeEndpoints. estimatedPoints=2. #CharteredBy d0117. DoR met."; }
    part vipRefineGateR1 : TestResult { :>> id = "63940516-2c7d-4e8f-c221-51627384c005"; :>> outcome = VerdictKind::pass; :>> judgedAgainst = "662a109"; :>> judgedAt = "2026-07-15"; :>> judgedBy = "claudeOpus"; }
    verification vipStandupGate : Test { :>> id = "63940516-2c7d-4e8f-c221-51627384c006"; :>> title = "Sprint 221 standup gate"; :>> createdAt = "2026-07-15"; :>> createdBy = "claudeOpus"; :>> method = VerificationMethod::inspect; :>> procedureText = "Approach: reuse write::record_decision (the CLI `keel record decision` path) behind a thin POST handler; add KEEL_API_WRITE_ENDPOINTS + report it in /api/version; no auto-commit, proposed-only. No blockers."; }
    part vipStandupGateR1 : TestResult { :>> id = "63940516-2c7d-4e8f-c221-51627384c007"; :>> outcome = VerdictKind::pass; :>> judgedAgainst = "662a109"; :>> judgedAt = "2026-07-15"; :>> judgedBy = "claudeOpus"; }
    verification vipImplementGate : Test { :>> id = "63940516-2c7d-4e8f-c221-51627384c008"; :>> title = "Sprint 221 implement gate"; :>> createdAt = "2026-07-15"; :>> createdBy = "claudeOpus"; :>> method = VerificationMethod::inspect; :>> procedureText = "api_decision + DecisionReq + route + KEEL_API_WRITE_ENDPOINTS + /api/version writeEndpoints + contract test implemented. clippy -D warnings clean; cargo test green; live-verified (temp root: D0001 proposed; writeEndpoints reported). keel validate + guard + check-engine green."; }
    part vipImplementGateR1 : TestResult { :>> id = "63940516-2c7d-4e8f-c221-51627384c009"; :>> outcome = VerdictKind::pass; :>> judgedAgainst = "662a109"; :>> judgedAt = "2026-07-15"; :>> judgedBy = "claudeOpus"; }
    verification vipReviewGate : Test { :>> id = "63940516-2c7d-4e8f-c221-51627384c00a"; :>> title = "Sprint 221 review gate"; :>> createdAt = "2026-07-15"; :>> createdBy = "claudeOpus"; :>> method = VerificationMethod::inspect; :>> procedureText = "Reviewed. The write half now mirrors the read half: /api/version advertises BOTH readEndpoints + writeEndpoints, so a generated UI discovers actions from the API (D0117) instead of hardcoding them. record-Decision is the right first write op — it routes change THROUGH the keel process (proposed Decision), keeping acceptance a separate human gate (D0106, the user's 'not going rogue'). Scope kept HONEST: viewerInProgramEdit stays open; inline guard-rejection + conflict-detection deferred, not silently claimed. Clean."; }
    part vipReviewGateR1 : TestResult { :>> id = "63940516-2c7d-4e8f-c221-51627384c00b"; :>> outcome = VerdictKind::pass; :>> judgedAgainst = "662a109"; :>> judgedAt = "2026-07-15"; :>> judgedBy = "claudeOpus"; }
    verification vipCloseOutGate : Test { :>> id = "63940516-2c7d-4e8f-c221-51627384c00c"; :>> title = "Sprint 221 closeOut gate (autonomous, D0049)"; :>> createdAt = "2026-07-15"; :>> createdBy = "claudeOpus"; :>> method = VerificationMethod::inspect; :>> procedureText = "Autonomous closeOut (D0049): story DoD pass; POST /api/decision + advertised write surface delivered + live-verified. Self-evidencing (D0051). viewerInProgramEdit remains OPEN (honest partial). NEXT keel-side viewer bricks: viewerChangeImpact (distance-grouped slice), viewerExportShare (N-12), viewerBaselineCompare (N-13); the generative UI itself is the viewer app (shape B)."; }
    part vipCloseOutGateR1 : TestResult { :>> id = "63940516-2c7d-4e8f-c221-51627384c00d"; :>> outcome = VerdictKind::pass; :>> judgedAgainst = "662a109"; :>> judgedAt = "2026-07-15"; :>> judgedBy = "claudeOpus"; }
    verification vipRetroGate : Test { :>> id = "63940516-2c7d-4e8f-c221-51627384c00e"; :>> title = "Sprint 221 retro gate (autonomous, D0049)"; :>> createdAt = "2026-07-15"; :>> createdBy = "claudeOpus"; :>> method = VerificationMethod::analyze; :>> procedureText = "Autonomous retro (D0049). WELL: kept scope HONEST — a broad DoD (record/supersede/apply-review/append/add-task + inline-reject + conflict) was NOT force-closed on a single-endpoint increment; delivered record-Decision + write-surface discovery and left the action open with the remaining pieces named. Also verified the write live against a TEMP root, so the record process was exercised for real WITHOUT polluting the repo (a reusable pattern for testing write endpoints). AVOIDABLE-ISSUE SCAN: none new. LESSON: test model-mutating endpoints against a throwaway root, not '.'; advertise write ops in /api/version so the UI discovers them (generativity applies to writes too). Estimate 2 pts held. NEXT: viewerChangeImpact."; }
    part vipRetroGateR1 : TestResult { :>> id = "63940516-2c7d-4e8f-c221-51627384c00f"; :>> outcome = VerdictKind::pass; :>> judgedAgainst = "662a109"; :>> judgedAt = "2026-07-15"; :>> judgedBy = "claudeOpus"; }
}
