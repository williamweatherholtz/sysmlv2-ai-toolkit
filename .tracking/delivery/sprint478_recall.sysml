// ProjectDeliveryS478 - Sprint 478: recall becomes injectable - content-bearing, budgeted, and seeded from a PROMPT instead of a term the caller must already know. EXECUTE. 5 pts.
package ProjectDeliveryS478 {
    private import EngineElement::*;
    private import EngineWork::*;
    private import EngineVerification::*;
    private import EngineRelationships::*;

    #CharteredBy dependency from recallStory to d0242;
    #CharteredBy dependency from recallStory to d0243;

    part recallStory : Story {
        :>> id = "00e08a33-6968-4137-bda5-bea1d79ce1fc";
        :>> title = "Sprint 478: recall is content-bearing, budgeted, and seeds from a prompt - the two halves injection needs (5 pts)";
        :>> createdAt = "2026-08-27"; :>> createdBy = "claudeOpus5"; :>> kind = WorkKind::code; :>> priority = WorkPriority::p1; :>> owner = "claudeOpus5"; :>> estimatedPoints = 5;
    }

    action def DeliveryRunS478 {
        action storyRecall;
        verification storyRecallDoD : Test { :>> id = "fe6a034e-14bb-4829-9c82-229c60cc09a6"; :>> method = VerificationMethod::test; :>> procedureText = "DELIVERED: kgRecallIsContentBearing and kgRecallSeedsFromAPrompt (D0242 parts 1-2 under D0243's precision rules). `keel why --brief` emits ranked lines carrying type, name, title, hops, via and source file plus the substantive text of the nearest two, under a budget whose ONE stated exception is that the top row is always shown. `keel recall --prompt -` reads a prompt on STDIN - never an argument, because free-form text must not reach a shell - and seeds from the corpus itself: identifier tokens first, word SEGMENTS not substrings, rarity derived from the tree, English function words filtered as language, and the rarest three words only. Elements the prompt NAMED outrank everything. The JSON form is unchanged for existing callers."; }
    // RAN: cargo test --release => 14 suites 0 failures, incl three new precision tests (matching_is_on_word_segments_not_substrings, identifier_tokens_are_recognised_and_plain_words_are_not, a_tight_budget_still_shows_the_top_row) | cargo clippy --release --all-targets => 0 errors | PRECISION, before -> after on the same terms: a 11112 -> 431 seeds, decision 294 -> 236, change 96 -> 80, the 795 -> 746, gate 5736 (unchanged and CORRECT - `gate` is a real segment in ~2,800 sprint-gate names, which is why rarity acts at the PROMPT level not on an explicit why) | prompt recall: 'can you please change the gate so a decision is made' => 'no informative term in this prompt - nothing pushed' naming change(80), decision(236), gate(5736) as too common; 'why did we decide d0239 that way?' => d0239 FIRST with its decision text; 'how does the keystone lock interact with a workspace' => keystone(38), workspace(65) both survive | budgets 800/1500/4000 all FIT (571/1289/3859 chars); a 200-char budget still shows the top row with no contradictory 'nothing reached' | .knowledge/ DELETED => recall still works (corpus 13632 vs 13639: the store is 7 of 13,639 items) | latency 641-863ms | keel why JSON keys unchanged.
        part storyRecallDoDR1 : TestResult { :>> id = "72fd1a7b-d7e0-45a6-82c2-801e79fe8aee"; :>> outcome = VerdictKind::pass; :>> judgedAgainst = "2bec54d"; :>> judgedAt = "2026-08-27"; :>> judgedBy = "claudeOpus5"; }
    }

    verification recallRefineGate : Test { :>> id = "ebea0de4-2a09-44e3-9503-6facf9ec8a35"; :>> title = "Sprint 478 refine gate (DoR)"; :>> createdAt = "2026-08-27"; :>> createdBy = "claudeOpus5"; :>> method = VerificationMethod::inspect; :>> procedureText = "DoR: the human asked to ingest the knowledge graph's ideas into keel rather than maintain a parallel subsystem, and the measurement agreed - seeding was already model-driven (65 seeds for `workspace`, 57 by name match and 8 by title, none from the store), and the store's four lexicon terms are ALIASES, not a subject vocabulary. D0243 recorded that and made `.knowledge/` optional. Resolvers: kgRecallIsContentBearing, kgRecallSeedsFromAPrompt. estimatedPoints=5. #CharteredBy d0242, d0243."; }
    part recallRefineGateR1 : TestResult { :>> id = "f74cb5e1-5f9b-4c76-906c-495515206aa4"; :>> outcome = VerdictKind::pass; :>> judgedAgainst = "2bec54d"; :>> judgedAt = "2026-08-27"; :>> judgedBy = "claudeOpus5"; }
    verification recallStandupGate : Test { :>> id = "750b307e-d2ca-4feb-8fe3-6a50b161be70"; :>> title = "Sprint 478 standup gate"; :>> createdAt = "2026-08-27"; :>> createdBy = "claudeOpus5"; :>> method = VerificationMethod::inspect; :>> procedureText = "Approach: precision has to come from the corpus, not from authored vocabulary, or recall's usefulness stays proportional to authoring effort in every downstream project - and this project's own four-term lexicon after a week is the evidence for how that goes. Four rules in preference order: identifiers, segments, rarity, hub suppression. Rarity is the workhorse and acts at the PROMPT level only: `keel why gate` legitimately returns 5,736 seeds because the caller asked for it, while a prompt containing `gate` must drop it."; }
    part recallStandupGateR1 : TestResult { :>> id = "8e193780-db65-433e-a46b-22c2df2e820b"; :>> outcome = VerdictKind::pass; :>> judgedAgainst = "2bec54d"; :>> judgedAt = "2026-08-27"; :>> judgedBy = "claudeOpus5"; }
    verification recallImplementGate : Test { :>> id = "7e945b14-60c0-4c0d-b4db-67c3d021cb09"; :>> title = "Sprint 478 implement gate"; :>> createdAt = "2026-08-27"; :>> createdBy = "claudeOpus5"; :>> method = VerificationMethod::test; :>> procedureText = "Implemented, and every defect below was found by MEASURING the output rather than reading the code. Four in this sprint: a tight budget printed '41 more reached, not shown' AND '(nothing reached)' - two contradictory claims and zero facts, because the budget check ran before the first row was written; a prompt asking about d0239 ranked d0219 first, since both sat at 0 hops and the tie broke alphabetically, so the one element the reader NAMED lost to a neighbour; `made` (7 matches) seeded an unrelated Issue, proving frequency alone cannot separate a rare domain term from a rare filler word; and a 1,500-char budget produced 1,539 chars because the footer was appended after the check. All four fixed and pinned."; }
    // RAN: cargo test --release => 14 suites 0 failures, incl three new precision tests (matching_is_on_word_segments_not_substrings, identifier_tokens_are_recognised_and_plain_words_are_not, a_tight_budget_still_shows_the_top_row) | cargo clippy --release --all-targets => 0 errors | PRECISION, before -> after on the same terms: a 11112 -> 431 seeds, decision 294 -> 236, change 96 -> 80, the 795 -> 746, gate 5736 (unchanged and CORRECT - `gate` is a real segment in ~2,800 sprint-gate names, which is why rarity acts at the PROMPT level not on an explicit why) | prompt recall: 'can you please change the gate so a decision is made' => 'no informative term in this prompt - nothing pushed' naming change(80), decision(236), gate(5736) as too common; 'why did we decide d0239 that way?' => d0239 FIRST with its decision text; 'how does the keystone lock interact with a workspace' => keystone(38), workspace(65) both survive | budgets 800/1500/4000 all FIT (571/1289/3859 chars); a 200-char budget still shows the top row with no contradictory 'nothing reached' | .knowledge/ DELETED => recall still works (corpus 13632 vs 13639: the store is 7 of 13,639 items) | latency 641-863ms | keel why JSON keys unchanged.
    part recallImplementGateR1 : TestResult { :>> id = "f35c262c-3ee2-4749-b162-0f51b9c76e98"; :>> outcome = VerdictKind::pass; :>> judgedAgainst = "2bec54d"; :>> judgedAt = "2026-08-27"; :>> judgedBy = "claudeOpus5"; }
    verification recallReviewGate : Test { :>> id = "0b8d163d-182d-420b-b5e1-672fafbfa1ba"; :>> title = "Sprint 478 review gate"; :>> createdAt = "2026-08-27"; :>> createdBy = "claudeOpus5"; :>> method = VerificationMethod::inspect; :>> procedureText = "Diff reviewed. Two of my own rules turned out to CONTRADICT each other - 'the payload fits the budget' and 'a budget narrows the answer, never erases it' - and the resolution is a STATED exception in both the doc comment and the DoD rather than letting one quietly falsify the other. The English function-word list is deliberately called out as LANGUAGE, not domain vocabulary: domain stop-wording stays derived per D0243 because it differs per project and goes stale, while `would` is filler in every corpus forever. `gate` remaining at 5,736 seeds is recorded as CORRECT rather than quietly improved - it is a real word in ~2,800 element names."; }
    part recallReviewGateR1 : TestResult { :>> id = "fec9cb20-052e-4b34-adeb-37266ba0449b"; :>> outcome = VerdictKind::pass; :>> judgedAgainst = "2bec54d"; :>> judgedAt = "2026-08-27"; :>> judgedBy = "claudeOpus5"; }
    verification recallCloseOutGate : Test { :>> id = "214b7497-74d9-4e68-9b3f-87a1063156c0"; :>> title = "Sprint 478 closeOut gate (autonomous, D0049)"; :>> createdAt = "2026-08-27"; :>> createdBy = "claudeOpus5"; :>> method = VerificationMethod::inspect; :>> procedureText = "Autonomous closeOut (D0049): both DoDs recorded pass with their RAN receipt; the frontier was read back from keel whats-next. NOTHING IS INJECTED YET - this sprint built the payload and the seeding, and kgPromptPathInjects is the next item and the one that changes the human's every turn. Latency measured at 641-863ms, which is why that item carries a hard cap and fail-open. Self-evidencing (D0051): no human confirmation claimed, and no claim is made about answer quality - kgInjectionProvenOnTheTrap exists to measure it."; }
    part recallCloseOutGateR1 : TestResult { :>> id = "388926fd-addb-4b22-a267-63acdff121f6"; :>> outcome = VerdictKind::pass; :>> judgedAgainst = "2bec54d"; :>> judgedAt = "2026-08-27"; :>> judgedBy = "claudeOpus5"; }
    verification recallRetroGate : Test { :>> id = "c8c9fbbd-0e74-4d9d-a4c6-ac12dd010693"; :>> title = "Sprint 478 retro gate (autonomous, D0049)"; :>> createdAt = "2026-08-27"; :>> createdBy = "claudeOpus5"; :>> method = VerificationMethod::analyze; :>> procedureText = "Autonomous retro (D0049). WELL: measuring the OUTPUT after each change found four defects that reading the diff would not have - two of them contradictions between my own stated rules. The before/after numbers also killed a wrong assumption cheaply: segment matching alone was supposed to fix seeding, and it took `a` from 11,112 to 431 while leaving `gate` at 5,736, which is what showed rarity to be the actual workhorse. FINDING, third instance in one session: `root_arg` takes the first bare token as ROOT and cannot know which flags consume the token after them, so `github-decider --root X`, `recall --prompt -` and `why --budget 1500` each read a flag's VALUE as a root. The last two were only visible because the issue281 project precondition started refusing outright - before that they would have silently answered about the wrong tree. Now one helper, `without_flag_values`, with the class named in its doc. AVOIDABLE-ISSUE SCAN: that class deserves a guard rather than a helper - nothing stops the fourth instance. Candidate forward control, stated not built: a check that every command declaring a value-taking flag routes its positionals through the stripper. Estimate 5 pts held."; }
    part recallRetroGateR1 : TestResult { :>> id = "77635b55-8658-4e83-8f95-032cd72bd059"; :>> outcome = VerdictKind::pass; :>> judgedAgainst = "2bec54d"; :>> judgedAt = "2026-08-27"; :>> judgedBy = "claudeOpus5"; }
}
