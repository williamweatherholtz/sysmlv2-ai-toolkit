// ProjectDeliveryS347 — Sprint 347: the 483 spawns were MY guard from sprint 344, not D0084 staleness.
// One `git log` replaces 480 `git show -s`. assured ~21s -> 6.2s. EXECUTE. 3 pts.
package ProjectDeliveryS347 {
    private import EngineElement::*;
    private import EngineWork::*;
    private import EngineVerification::*;
    private import EngineRelationships::*;

    #CharteredBy dependency from batchCommitDatesStory to d0162;

    part batchCommitDatesStory : Story {
        :>> id = "0d800560-0814-6560-9b3e-000000300560";
        :>> title = "Sprint 347: one git log replaces 480 git show -s; my sprint-344 guard had tripled assured (issue148, 3 pts)";
        :>> createdAt = "2026-08-19"; :>> createdBy = "claudeOpus5"; :>> kind = WorkKind::code; :>> priority = WorkPriority::p0; :>> owner = "claudeOpus5"; :>> estimatedPoints = 3;
    }

    action def DeliveryRunS347 {
        action storyBatchCommitDates;
        verification storyBatchCommitDatesDoD : Test { :>> id = "0d800561-0814-6561-9b3e-000000300561"; :>> method = VerificationMethod::test; :>> procedureText = "THE 483 SPAWNS WERE MY OWN GUARD FROM SPRINT 344, NOT D0084 STALENESS AS issue147 ASSERTED. `keel assured` folds GUARD_NAMES into its invariant check (view.rs:4620), so `impossible-evidence-date` runs inside it, and its `commit_date` helper spawned `git show -s --format=%ad` once per DISTINCT judgedAgainst SHA: 480 of 484 spawns, 15,286ms of a ~21,000ms run. Sprint 342 had measured assured at 9.9s, so the guard I added the day before roughly TRIPLED it. FIXED with `commit_dates()` - the whole history in ONE `git log --all --format=%H %ad`, memoized for the process (safe under D0129, which forbids rewriting history, so a commit's author date is immutable) - and `commit_date` resolving an abbreviated SHA against that map: exact hit, then a UNIQUE prefix match, None on ambiguity because a date bound to the wrong commit is worse than no date when the caller uses it to decide whether a judgment was possible. MEASURED, five samples, warmed binary: spawns 484 to 5, git 15,286ms to 963ms, assured ~21s to 6.0-6.6s - now faster than the 9.9s the guard had regressed. GUARD BEHAVIOUR RE-VERIFIED BOTH WAYS, which is the only verification that means anything here: PASS on the clean tree at 3817 results, and FAIL naming srConsoleObligationActionableConfirmR1 when the original defect is reintroduced. validate 375 clean; check-engine clean; 36 guards ALL PASS; 188 tests; clippy clean."; }
        part storyBatchCommitDatesDoDR1 : TestResult { :>> id = "0d800562-0814-6562-9b3e-000000300562"; :>> outcome = VerdictKind::pass; :>> judgedAgainst = "a92e916"; :>> judgedAt = "2026-08-19"; :>> judgedBy = "claudeOpus5"; }
    }

    verification bcRefineGate : Test { :>> id = "0d800563-0814-6563-9b3e-000000300563"; :>> title = "Sprint 347 refine gate (DoR)"; :>> createdAt = "2026-08-19"; :>> createdBy = "claudeOpus5"; :>> method = VerificationMethod::inspect; :>> procedureText = "DoR. Followed the frontier to dcBatchGitReads, the 15-second finding sprint 346 recorded. Its own DoD said to finish the instrumentation FIRST and verify by spawn count rather than by clock - and following that instruction is the entire reason this sprint found the true cause instead of implementing the fix issue147 described for a caller that was not the problem. estimatedPoints=3."; }
    part bcRefineGateR1 : TestResult { :>> id = "0d800564-0814-6564-9b3e-000000300564"; :>> outcome = VerdictKind::pass; :>> judgedAgainst = "a92e916"; :>> judgedAt = "2026-08-19"; :>> judgedBy = "claudeOpus5"; }

    verification bcStandupGate : Test { :>> id = "0d800565-0814-6565-9b3e-000000300565"; :>> title = "Sprint 347 standup gate"; :>> createdAt = "2026-08-19"; :>> createdBy = "claudeOpus5"; :>> method = VerificationMethod::inspect; :>> procedureText = "Approach: add a PER-ARGV tally before touching any code, because a total says spawns are the cost while only a breakdown says which call to batch. That took five minutes and immediately showed `git show -s x480` against `git grep x2` and `git log x2`, which pointed at `commit_date` rather than at the staleness path issue147 had named. Then batch, then re-verify the guard's behaviour in BOTH directions rather than only re-timing it - a faster guard that no longer catches its defect would be a worse outcome than a slow one. No blockers."; }
    part bcStandupGateR1 : TestResult { :>> id = "0d800566-0814-6566-9b3e-000000300566"; :>> outcome = VerdictKind::pass; :>> judgedAgainst = "a92e916"; :>> judgedAt = "2026-08-19"; :>> judgedBy = "claudeOpus5"; }

    verification bcImplementGate : Test { :>> id = "0d800567-0814-6567-9b3e-000000300567"; :>> title = "Sprint 347 implement gate"; :>> createdAt = "2026-08-19"; :>> createdBy = "claudeOpus5"; :>> method = VerificationMethod::test; :>> procedureText = "THE PATTERN, STATED GENERALLY BECAUSE IT WILL RECUR: a per-item git call is fine at ten items and catastrophic at five hundred, and the whole history is available in one `git log`, so there is no reason to ever pay per item for a commit-graph fact. I wrote the per-SHA version in sprint 344 while thinking about correctness and never asked what it would cost at corpus scale - and the guard it powers scans 3817 results. TWO CORRECTNESS DETAILS THAT ARE NOT OPTIMISATIONS. (1) The memo is process-lifetime, which is only safe because D0129 forbids rewriting history; a commit created DURING a run postdates every judgment the run could be reading, which is the case the caller already treats as a violation. (2) `judgedAgainst` records ABBREVIATED SHAs, so lookup tries an exact hit and then a UNIQUE prefix match, returning None on an ambiguous prefix rather than an arbitrary winner - the previous `git show` resolved abbreviations itself and silently, and reproducing that behaviour was the part most likely to be got wrong. PREDICTION AND OUTCOME, recorded because the prediction was made BEFORE the fix: dcBatchGitReads's DoD, written yesterday, said 'assured from ~21s toward the ~6s that remains once 15s of spawn cost is removed'. Measured after: 6.0-6.6s over five samples. A prediction that lands is evidence the attribution was right, in a way a bare improvement is not."; }
    part bcImplementGateR1 : TestResult { :>> id = "0d800568-0814-6568-9b3e-000000300568"; :>> outcome = VerdictKind::pass; :>> judgedAgainst = "a92e916"; :>> judgedAt = "2026-08-19"; :>> judgedBy = "claudeOpus5"; }

    verification bcReviewGate : Test { :>> id = "0d800569-0814-6569-9b3e-000000300569"; :>> title = "Sprint 347 review gate"; :>> createdAt = "2026-08-19"; :>> createdBy = "claudeOpus5"; :>> method = VerificationMethod::inspect; :>> procedureText = "Reviewed, and this gate exists mainly to correct TWO CLAIMS I RECORDED YESTERDAY, both wrong, both mine. (1) SPRINT 346's REVIEW GATE said the 9.9s-to-21s jump in `assured` showed that 'a cross-day wall-clock comparison on this host is not evidence'. The sprint-342 figure was REAL and my own guard explains the whole difference. The general point about cross-day comparisons still holds, but I used it to dismiss a signal that was telling me something true - which is worse than the measurement error it was warning against, because a rule invoked to explain away evidence stops being a rule. (2) issue147 said the 483 spawns were 'one per element for D0084 staleness, and there are ~250 critiquable elements'. Plausible, order-of-magnitude right, and wrong: a guard, keyed by SHA. Both claims were made from a TOTAL without the breakdown that settles it, and the breakdown cost five minutes. THAT IS THREE WRONG COST ATTRIBUTIONS IN THIS SESSION and every one shares a shape - I explained a number instead of decomposing it. Both corrections are recorded in issue148 next to what they correct, not edited away. WHAT I LEFT UNDONE AND SPLIT OUT RATHER THAN CLAIMED: the spawn counter still covers 2 of ~25 sites, so `orient` reports git x0 while demonstrably shelling out and every total UNDERSTATES. That is dcInstrumentAllGitSites, carrying a failing result, with a STATIC check as its verification - a grep proving no a raw Command::new git spawn survives outside the counted helper - because a counter you must remember to call is the manual vigilance D0047 refuses."; }
    part bcReviewGateR1 : TestResult { :>> id = "0d80056a-0814-656a-9b3e-00000030056a"; :>> outcome = VerdictKind::pass; :>> judgedAgainst = "a92e916"; :>> judgedAt = "2026-08-19"; :>> judgedBy = "claudeOpus5"; }

    verification bcCloseOutGate : Test { :>> id = "0d80056b-0814-656b-9b3e-00000030056b"; :>> title = "Sprint 347 closeOut gate (autonomous, D0049)"; :>> createdAt = "2026-08-19"; :>> createdBy = "claudeOpus5"; :>> method = VerificationMethod::inspect; :>> procedureText = "Autonomous closeOut (D0049). issue148 recorded with both of yesterday's wrong attributions corrected in its own text; dcBatchGitReads now carries a PASSING second result for the half that is done, and the half that is not is dcInstrumentAllGitSites with a failing result. CUMULATIVE EFFECT OF SPRINTS 346 AND 347, all five-sample warmed measurements: assured ~21s to ~6.2s, console warm burst 7197ms to ~1.1s, cold burst 12066ms to ~5.3s, guard ~3.6s. The one number I will not put a before against is CLI orient and coverage - no baseline was taken before sprint 346's fingerprint change, so they read 1.45s and 2.45s with no honest delta. pendingAcceptances d0159, d0161, d0162 - unchanged; nothing here needed a Decision. validate 375 clean; check-engine clean; 36 guards ALL PASS; 188 tests; clippy clean."; }
    part bcCloseOutGateR1 : TestResult { :>> id = "0d80056c-0814-656c-9b3e-00000030056c"; :>> outcome = VerdictKind::pass; :>> judgedAgainst = "a92e916"; :>> judgedAt = "2026-08-19"; :>> judgedBy = "claudeOpus5"; }

    verification bcRetroGate : Test { :>> id = "0d80056d-0814-656d-9b3e-00000030056d"; :>> title = "Sprint 347 retro gate (autonomous, D0049)"; :>> createdAt = "2026-08-19"; :>> createdBy = "claudeOpus5"; :>> method = VerificationMethod::analyze; :>> procedureText = "Autonomous retro (D0049) under D0131's retroTrack. AVOIDABLE-ISSUE: I shipped a hard commit gate yesterday without measuring what it cost, and it tripled the slowest command in the tool. The guard is correct and I still defend it; what I skipped is that a check which scans 3817 results and calls git per distinct SHA has an obvious cost question, and I never asked it because I was thinking about whether the check was RIGHT. A CONTROL THAT MAKES THE TOOL PAINFUL TO RUN IS A CONTROL PEOPLE WILL BYPASS - which is D0132's whole lesson, where an all-or-nothing kernel validator got disabled and took every other layer with it. So cost is part of a control's correctness, not a separate concern, and the rule is: any new guard gets a KEEL_PERF reading before it lands. SECOND AVOIDABLE-ISSUE: three wrong cost attributions in one session, all made by explaining a total rather than decomposing it. The per-argv tally that settled this one took five minutes and I built it only after being wrong twice more. WELL: (1) following the DoD's own 'instrument first, verify by count not clock' instruction is what found the true cause, and the process caught its author for the second sprint running; (2) the guard was re-verified in both directions, not just re-timed; (3) a prediction made before the fix (~6s) matched the measurement after it, which is stronger evidence of correct attribution than the speedup itself; (4) both of yesterday's wrong claims are corrected in the record rather than quietly overwritten, including the one where I invoked a real methodological rule to dismiss a true signal; (5) the undone half was split out with a STATIC verification rather than folded into a 'done' item. Estimate 3 pts, delivered."; }
    part bcRetroGateR1 : TestResult { :>> id = "0d80056e-0814-656e-9b3e-00000030056e"; :>> outcome = VerdictKind::pass; :>> judgedAgainst = "a92e916"; :>> judgedAt = "2026-08-19"; :>> judgedBy = "claudeOpus5"; }
}
