// ProjectDeliveryS203 — Sprint 203: osAdaptiveCommandGuidance (issue065) — generalize the AI command
// guidance to "detect + adapt to the host OS/shell" (CLAUDE.md §6) and ship an OS-agnostic environment
// section in the downstream keel-init template. Retro finding. EXECUTE (guidance/doc). 1 pt. AUTONOMOUS (D0049).
package ProjectDeliveryS203 {
    private import EngineElement::*;
    private import EngineWork::*;
    private import EngineVerification::*;
    private import EngineRequirements::*;
    private import EngineRelationships::*;

    #CharteredBy dependency from osAdaptiveCommandGuidanceStory to issue065;

    part osAdaptiveCommandGuidanceStory : Story {
        :>> id = "63940516-2c7d-4e8f-c203-51627384c001";
        :>> title = "Sprint 203: osAdaptiveCommandGuidance (1 pt) - OS-adaptive command principle in CLAUDE.md §6 + downstream template (issue065)";
        :>> createdAt = "2026-07-14"; :>> createdBy = "wweatherholtz"; :>> kind = WorkKind::code; :>> priority = WorkPriority::p2; :>> owner = "claudeOpus"; :>> estimatedPoints = 1;
    }

    action def DeliveryRunS203 {
        action storyOsAdaptiveCommandGuidance;
        verification storyOsAdaptiveCommandGuidanceDoD : Test { :>> id = "63940516-2c7d-4e8f-c203-51627384c002"; :>> method = VerificationMethod::inspect; :>> procedureText = "Resolves issue065 (retro finding; generalizes issue013). (1) CLAUDE.md §6 now leads with an OS-agnostic PRINCIPLE — detect the host shell/OS before assuming syntax; command forms (path seps, env-var syntax, null device, call operator, substitution chars incl. the backtick-in-double-quoted-Bash bug this session hit) are host-specific; switch tools on error/hang — with the Windows/PowerShell/miniforge specifics reframed as THIS repo's host instance. (2) The downstream keel-init template (keel-cli/assets/claude-md-template.md) gains a §6 'Environment — adapt to your host OS/shell' section (OS-agnostic; prompts the new project to record its own host), so init'd projects on macOS/Linux inherit the principle instead of nothing. HONEST SCOPE: guidance is a 'linter, ignorable' (D0110) — this REDUCES, not eliminates, the mistake class; judged NOT to rise to a frozen-process Decision (operating-notes maintenance, like prior §6 accretion), so no Decision/acceptance. VERIFIED: `keel init` writes a template containing the §6 section (grep confirmed). VERIFY: §6 principle present in CLAUDE.md + template; doc-sync (only main.rs include_str references the template — no section-count claims); keel validate + guard green."; }
        part storyOsAdaptiveCommandGuidanceDoDR1 : TestResult { :>> id = "63940516-2c7d-4e8f-c203-51627384c003"; :>> outcome = VerdictKind::pass; :>> judgedAgainst = "b794280"; :>> judgedAt = "2026-07-14"; :>> judgedBy = "claudeOpus"; }
    }

    verification oacgRefineGate : Test { :>> id = "63940516-2c7d-4e8f-c203-51627384c004"; :>> title = "Sprint 203 refine gate (DoR)"; :>> createdAt = "2026-07-14"; :>> createdBy = "claudeOpus"; :>> method = VerificationMethod::inspect; :>> procedureText = "DoR: issue065 triaged (resolver osAdaptiveCommandGuidance). Scope = CLAUDE.md §6 generalization + downstream template §6; guidance/doc, not a frozen process -> EXECUTE, no Decision. estimatedPoints=1. #CharteredBy issue065. DoR met."; }
    part oacgRefineGateR1 : TestResult { :>> id = "63940516-2c7d-4e8f-c203-51627384c005"; :>> outcome = VerdictKind::pass; :>> judgedAgainst = "b794280"; :>> judgedAt = "2026-07-14"; :>> judgedBy = "claudeOpus"; }
    verification oacgStandupGate : Test { :>> id = "63940516-2c7d-4e8f-c203-51627384c006"; :>> title = "Sprint 203 standup gate"; :>> createdAt = "2026-07-14"; :>> createdBy = "claudeOpus"; :>> method = VerificationMethod::inspect; :>> procedureText = "Approach: add the OS-adaptive principle atop CLAUDE.md §6 (Windows specifics reframed as this repo's host); add an OS-agnostic §6 to the template; rebuild so the binary embeds it; verify via `keel init`. No blockers."; }
    part oacgStandupGateR1 : TestResult { :>> id = "63940516-2c7d-4e8f-c203-51627384c007"; :>> outcome = VerdictKind::pass; :>> judgedAgainst = "b794280"; :>> judgedAt = "2026-07-14"; :>> judgedBy = "claudeOpus"; }
    verification oacgImplementGate : Test { :>> id = "63940516-2c7d-4e8f-c203-51627384c008"; :>> title = "Sprint 203 implement gate"; :>> createdAt = "2026-07-14"; :>> createdBy = "claudeOpus"; :>> method = VerificationMethod::inspect; :>> procedureText = "CLAUDE.md §6 principle + template §6 landed; binary rebuilt; `keel init` template contains the §6 section (grep=1). keel validate + guard green; doc-sync clean."; }
    part oacgImplementGateR1 : TestResult { :>> id = "63940516-2c7d-4e8f-c203-51627384c009"; :>> outcome = VerdictKind::pass; :>> judgedAgainst = "b794280"; :>> judgedAt = "2026-07-14"; :>> judgedBy = "claudeOpus"; }
    verification oacgReviewGate : Test { :>> id = "63940516-2c7d-4e8f-c203-51627384c00a"; :>> title = "Sprint 203 review gate"; :>> createdAt = "2026-07-14"; :>> createdBy = "claudeOpus"; :>> method = VerificationMethod::inspect; :>> procedureText = "Reviewed. The fix does the honest, bounded thing: it lifts the OS lesson from a Windows-only note (issue013) to an OS-agnostic PRINCIPLE and, crucially, ships it downstream (the template had nothing). It correctly does NOT overclaim — the retro-recorded honest limit is that guidance can't gate behavior (D0110), so this reduces not eliminates the class. Not dressed up as a Decision it isn't. Clean."; }
    part oacgReviewGateR1 : TestResult { :>> id = "63940516-2c7d-4e8f-c203-51627384c00b"; :>> outcome = VerdictKind::pass; :>> judgedAgainst = "b794280"; :>> judgedAt = "2026-07-14"; :>> judgedBy = "claudeOpus"; }
    verification oacgCloseOutGate : Test { :>> id = "63940516-2c7d-4e8f-c203-51627384c00c"; :>> title = "Sprint 203 closeOut gate (autonomous, D0049)"; :>> createdAt = "2026-07-14"; :>> createdBy = "claudeOpus"; :>> method = VerificationMethod::inspect; :>> procedureText = "Autonomous closeOut (D0049): DoD pass; issue065 resolved (osAdaptiveCommandGuidance done). keel validate + guard green. Self-evidencing (D0051). NEXT: Sprint 204 = jvmRetirementSpike (issue066) — a research spike producing a design artifact + a PROPOSED Decision, checkpointed to the human before any implementation."; }
    part oacgCloseOutGateR1 : TestResult { :>> id = "63940516-2c7d-4e8f-c203-51627384c00d"; :>> outcome = VerdictKind::pass; :>> judgedAgainst = "b794280"; :>> judgedAt = "2026-07-14"; :>> judgedBy = "claudeOpus"; }
    verification oacgRetroGate : Test { :>> id = "63940516-2c7d-4e8f-c203-51627384c00e"; :>> title = "Sprint 203 retro gate (autonomous, D0049)"; :>> createdAt = "2026-07-14"; :>> createdBy = "claudeOpus"; :>> method = VerificationMethod::analyze; :>> procedureText = "Autonomous retro (D0049). WELL: a live retro finding (my own bash/PowerShell fumbling this session, incl. a backtick-in-double-quoted-Bash command-substitution bug) became durable, OS-agnostic guidance that ALSO ships to downstream projects — closing the gap that the template carried no OS section. AVOIDABLE-ISSUE SCAN: the mistakes themselves recurred DURING this session even while capturing the issue — reinforcing D0110's point that guidance is not a control; a structural OS-detection mechanism (harness-injected host specifics) would be the real fix, noted as a possible future item. Estimate 1 pt held. NEXT: the issue066 JVM-retirement research spike."; }
    part oacgRetroGateR1 : TestResult { :>> id = "63940516-2c7d-4e8f-c203-51627384c00f"; :>> outcome = VerdictKind::pass; :>> judgedAgainst = "b794280"; :>> judgedAt = "2026-07-14"; :>> judgedBy = "claudeOpus"; }
}
