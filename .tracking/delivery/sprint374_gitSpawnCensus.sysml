// ProjectDeliveryS374 — Sprint 374: every git spawn is counted. orient said git x0 while spawning 20.
// EXECUTE. 3 pts.
package ProjectDeliveryS374 {
    private import EngineElement::*;
    private import EngineWork::*;
    private import EngineVerification::*;
    private import EngineRelationships::*;

    #CharteredBy dependency from gitCensusStory to d0169;

    part gitCensusStory : Story {
        :>> id = "0d800710-0814-6710-9b3e-000000300710";
        :>> title = "Sprint 374: one counted constructor for git — the 8%-coverage counter becomes total (3 pts)";
        :>> createdAt = "2026-08-21"; :>> createdBy = "claudeOpus5"; :>> kind = WorkKind::code; :>> priority = WorkPriority::p0; :>> owner = "claudeOpus5"; :>> estimatedPoints = 3;
    }

    action def DeliveryRunS374 {
        action storyGitCensus;
        verification storyGitCensusDoD : Test { :>> id = "0d800711-0814-6711-9b3e-000000300711"; :>> method = VerificationMethod::test; :>> procedureText = "DELIVERED BACKLOG ITEMS: dcInstrumentAllGitSites; issue142Fix verified MOOT with its damaged DoD recorded (its fragment text -in original statement- is a live specimen of the shell-mangling class dcAuthorViaWriteTool tracks). The spawn counter covered TWO of 25 `git` sites - view::git_out and govern::git_lines - so every total UNDERSTATED and `orient` reported `git x0`. MEASURED AFTER: orient `git x20`, assured `git x52` (the old counter said 5), suspect `git x20`. THE SHAPE: `gitx::git()` is a drop-in COUNTED CONSTRUCTOR returning the same `Command`, so all eleven distinct builder chains across 11 files compiled unchanged - chosen because rewriting 25 sites to a common run signature is exactly the mechanical multi-site edit that has failed three times this session. All 25 sites routed; the two rich helpers keep argv/time detail and their own count was REMOVED so the layers never double-count. THE CONTROL: `no_git_spawn_bypasses_the_counted_constructor` fails the build naming file:line on any raw `Command::new(git)` outside gitx.rs - verified by reintroducing one in history.rs and watching it named. HONEST LIMIT stated in the module doc: GIT_NANOS/GIT_ARGV stay partial (rich helpers only), the COUNT is total - count-don't-time is the session's rule and the count is what settles arguments. validate clean; check-engine clean; 38 guards ALL PASS; 206 tests; clippy clean."; }
        part storyGitCensusDoDR1 : TestResult { :>> id = "0d800712-0814-6712-9b3e-000000300712"; :>> outcome = VerdictKind::pass; :>> judgedAgainst = "e0285ba"; :>> judgedAt = "2026-08-21"; :>> judgedBy = "claudeOpus5"; }
    }

    verification gcRefineGate : Test { :>> id = "0d800713-0814-6713-9b3e-000000300713"; :>> title = "Sprint 374 refine gate (DoR)"; :>> createdAt = "2026-08-21"; :>> createdBy = "claudeOpus5"; :>> method = VerificationMethod::inspect; :>> procedureText = "DoR. The last AI-workable frontier item; everything above it awaits their demo or their direction. The census came first: 25 sites across 11 files, all sharing the -C shape, eleven distinct builder chains. That census is what chose the design - a constructor swap over a signature rewrite. estimatedPoints=3."; }
    part gcRefineGateR1 : TestResult { :>> id = "0d800714-0814-6714-9b3e-000000300714"; :>> outcome = VerdictKind::pass; :>> judgedAgainst = "e0285ba"; :>> judgedAt = "2026-08-21"; :>> judgedBy = "claudeOpus5"; }

    verification gcStandupGate : Test { :>> id = "0d800715-0814-6715-9b3e-000000300715"; :>> title = "Sprint 374 standup gate"; :>> createdAt = "2026-08-21"; :>> createdBy = "claudeOpus5"; :>> method = VerificationMethod::inspect; :>> procedureText = "Approach: count at CONSTRUCTION, which equals spawns because every site runs the command it builds. The alternative - a run-wrapper - would have meant rewriting eleven different chain shapes, the exact class of edit sprint 373's retro flagged at occurrence three. A counter that covers 8% of sites is worse than no counter, because it gets believed: three investigations this session mis-attributed cost off that number. No blockers."; }
    part gcStandupGateR1 : TestResult { :>> id = "0d800716-0814-6716-9b3e-000000300716"; :>> outcome = VerdictKind::pass; :>> judgedAgainst = "e0285ba"; :>> judgedAt = "2026-08-21"; :>> judgedBy = "claudeOpus5"; }

    verification gcImplementGate : Test { :>> id = "0d800717-0814-6717-9b3e-000000300717"; :>> title = "Sprint 374 implement gate"; :>> createdAt = "2026-08-21"; :>> createdBy = "claudeOpus5"; :>> method = VerificationMethod::test; :>> procedureText = "THE NUMBER THAT JUSTIFIES THE SPRINT: `orient` - the command every session starts with - spawns git TWENTY times and reported zero. `assured` spawns 52 and reported 5. Nobody can reason about a hot path whose instrument hides 90% of it. FOUR SMALL BREAKS DURING ROUTING, all import-level and all caught by the compiler in one pass: three files whose only `Command` use was the replaced spawn (dead import), one grouped import needing `Command` dropped from the braces, and main.rs being the BIN crate where `crate::gitx` does not resolve - `keel_cli::gitx` does. The double-count trap was handled at design time rather than found later: the two rich helpers had their own GIT_CALLS increment removed in the same patch that routed their spawn through the constructor."; }
    part gcImplementGateR1 : TestResult { :>> id = "0d800718-0814-6718-9b3e-000000300718"; :>> outcome = VerdictKind::pass; :>> judgedAgainst = "e0285ba"; :>> judgedAt = "2026-08-21"; :>> judgedBy = "claudeOpus5"; }

    verification gcReviewGate : Test { :>> id = "0d800719-0814-6719-9b3e-000000300719"; :>> title = "Sprint 374 review gate — three passes per D0172"; :>> createdAt = "2026-08-21"; :>> createdBy = "claudeOpus5"; :>> method = VerificationMethod::inspect; :>> procedureText = "PASS 1, CLAIMS vs computed output: the counts (20/52/20) read from KEEL_PERF runs of the built binary, not inferred from the diff; 206 tests, clippy zero, 38 guards ALL PASS - all from the runs. PASS 2, BOUNDARY: the static check skips its own file and comment lines, probed with the needle built from char concatenation so the test's own source cannot self-match; the bin-vs-lib crate path boundary was hit and fixed. PASS 3, THE SPRINT'S OWN DIFF: the double-count risk was in MY change (constructor counts + helpers counted), removed in the same patch; checked the emitted counts are plausible rather than doubled - orient's 20 matches five orient sites times multiple calls, not 40. WHAT A REVIEWER SHOULD ATTACK: counting at construction assumes every built Command is run. True of all 25 sites today, unverifiable for tomorrow's - a site that builds and drops a Command would inflate the count. Accepted: the error is bounded, visible in KEEL_PERF=2's argv tally when it matters, and the alternative was the multi-site rewrite this session keeps fumbling."; }
    part gcReviewGateR1 : TestResult { :>> id = "0d80071a-0814-671a-9b3e-00000030071a"; :>> outcome = VerdictKind::pass; :>> judgedAgainst = "e0285ba"; :>> judgedAt = "2026-08-21"; :>> judgedBy = "claudeOpus5"; }

    verification gcCloseOutGate : Test { :>> id = "0d80071b-0814-671b-9b3e-00000030071b"; :>> title = "Sprint 374 closeOut gate (autonomous, D0049)"; :>> createdAt = "2026-08-21"; :>> createdBy = "claudeOpus5"; :>> method = VerificationMethod::inspect; :>> procedureText = "Autonomous closeOut (D0049). dcInstrumentAllGitSites judged; the frontier's AI-workable set is now EMPTY - every remaining ready item awaits their demo confirmation or their scoping direction. validate clean; check-engine clean; 38 guards ALL PASS; 206 tests; clippy clean."; }
    part gcCloseOutGateR1 : TestResult { :>> id = "0d80071c-0814-671c-9b3e-00000030071c"; :>> outcome = VerdictKind::pass; :>> judgedAgainst = "e0285ba"; :>> judgedAt = "2026-08-21"; :>> judgedBy = "claudeOpus5"; }

    verification gcRetroGate : Test { :>> id = "0d80071d-0814-671d-9b3e-00000030071d"; :>> title = "Sprint 374 retro gate (autonomous, D0049)"; :>> createdAt = "2026-08-21"; :>> createdBy = "claudeOpus5"; :>> method = VerificationMethod::analyze; :>> procedureText = "Autonomous retro (D0049). AVOIDABLE-ISSUE SCAN under rcRecurrence: the four import breaks are occurrence ONE of import-cleanup-after-mechanical-replace - watch for recurrence, no new item (the compiler catches it in one pass every time, which is a working control; recording an item for a compiler-caught class would be the warning-fatigue rcRecurrence exists to avoid). The bin-crate path confusion (crate:: vs keel_cli:: in main.rs) is occurrence ONE this session; same disposition. WELL: (1) the census preceded the design and CHOSE it - eleven chain shapes is why a constructor swap beat a signature rewrite; (2) the control was verified by reintroducing a raw spawn and reading its file:line in the failure; (3) the double-count was prevented in the same patch rather than discovered by a suspicious number later; (4) the honest limit - time attribution stays partial - is in the module doc, not buried; (5) authored via Write-tool patch files throughout, zero shell-mangling, second consecutive clean sprint. Estimate 3 pts, delivered."; }
    part gcRetroGateR1 : TestResult { :>> id = "0d80071e-0814-671e-9b3e-00000030071e"; :>> outcome = VerdictKind::pass; :>> judgedAgainst = "e0285ba"; :>> judgedAt = "2026-08-21"; :>> judgedBy = "claudeOpus5"; }
}
