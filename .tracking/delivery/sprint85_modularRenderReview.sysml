// =====================================================================
// ProjectDeliveryS85 — Sprint 85: modularRenderReview (D0086). Generalize the one-off diagram into a
// MODULAR `sysmlv2 render <view> --mode graph|table|review` artifact generator over the view layer,
// and add `sysmlv2 apply-review` — a human-review round-trip where review enters as NEW LINKED
// critique items that attest state + induce computed suspicion (critique_suspect). All at once.
// Total: 8 pts  Ceremony: AUTONOMOUS (D0049); the render+review CHANGE was human-accepted (D0086).
// =====================================================================
package ProjectDeliveryS85 {
    private import EngineElement::*;
    private import EngineWork::*;
    private import EngineVerification::*;
    private import EngineRelationships::*;

    #CharteredBy dependency from modularRenderReviewStory to d0086;

    part modularRenderReviewStory : Story {
        :>> id = "63940516-2c7d-4e8f-b085-51627384b601";
        :>> title = "Sprint 85: modularRenderReview (8 pts) — `sysmlv2 render <view> --mode graph|table|review` + `apply-review` round-trip (review = linked critique, attests state + induces suspicion); render process/skill/viewpoint (D0086)";
        :>> createdAt = "2026-06-21";
        :>> createdBy = "wweatherholtz";
        :>> kind = WorkKind::code;
        :>> priority = WorkPriority::p1;
        :>> owner = "claudeOpus";
        :>> estimatedPoints = 8;
    }

    action def DeliveryRunS85 {
        action storyModularRenderReview;
        verification storyModularRenderReviewDoD : Test { :>> id = "63940516-2c7d-4e8f-b085-51627384b602"; :>> method = VerificationMethod::test; :>> procedureText = "`sysmlv2 render <view> --mode graph|table|review` renders any declared view as self-contained interactive HTML: graph (cytoscape; model=whole-model diagram preset, else view-scoped subgraph; contains/resultof default-off, all node types + edge kinds toggleable), table (sortable/searchable rows via run_resolved), review (table + accept/finding + lens/severity/actionable/rationale + Export-JSON). `sysmlv2 apply-review --batch` writes each disposition via the write path (write.rs append_critique: UUID + append-only) as a NEW LINKED method=critique verification + TestResult + #Verify edge in .tracking/critiques.sysml (human = independent critic, D0080): accept->pass attests state; finding->fail + severity INDUCES computed suspicion (`sysmlv2 suspect` critique_suspect). render process-def (.engine/processes/render.sysml, generalizing diagram.sysml) + render skill + skills-registry + 'render' viewpoint; D0086 #ProspectiveChange keystone co-commit (D0070); doc-sync CLAUDE.md/usage.md; /*.html git-ignored. VERIFY: render emits valid HTML for all 3 modes (graph whole+view-scoped, table, review); apply-review smoke = parseable critiques (validate 97 clean) + critique_suspect picks up a finding; serde_json added; clippy --workspace --all-targets -D warnings + cargo test (35 lib, +critique_suspect +render-dispatch regressions) + guard all (9) green; d0086 Core-3 critiqued."; }
        part storyModularRenderReviewDoDR1 : TestResult { :>> id = "63940516-2c7d-4e8f-b085-51627384b603"; :>> outcome = VerdictKind::pass; :>> judgedAgainst = "fdaa84c"; :>> judgedAt = "2026-06-21"; :>> judgedBy = "claudeOpus"; }
    }

    verification modularRenderReviewRefineGate : Test { :>> id = "63940516-2c7d-4e8f-b085-51627384b604"; :>> title = "Sprint 85 refine gate (DoR)"; :>> createdAt = "2026-06-21"; :>> createdBy = "claudeOpus"; :>> method = VerificationMethod::inspect; :>> procedureText = "DoR: the human asked (1) more diagram toggles, (2) 'a process to create this kind of artifact from an arbitrary view, modular', and (3) a reviewing tool (accept/reject + rationale, export JSON sitewide), specifying the write-back: 'apply-review signifies a critique or downstream test result; user input enters as new linked items that attest item state and induce suspicion and new implementation if relevant'. Accepted scope 'All at once' + 'Round-trip to authored facts'. Recorded as D0086 (#ProspectiveChange; the directive is the acceptance). estimatedPoints=8. #CharteredBy d0086. DoD accepted."; }
    part modularRenderReviewRefineGateR1 : TestResult { :>> id = "63940516-2c7d-4e8f-b085-51627384b605"; :>> outcome = VerdictKind::pass; :>> judgedAgainst = "fdaa84c"; :>> judgedAt = "2026-06-21"; :>> judgedBy = "claudeOpus"; }

    verification modularRenderReviewStandupGate : Test { :>> id = "63940516-2c7d-4e8f-b085-51627384b606"; :>> title = "Sprint 85 standup gate"; :>> createdAt = "2026-06-21"; :>> createdBy = "claudeOpus"; :>> method = VerificationMethod::inspect; :>> procedureText = "Approach: (1) view.rs — expose run_resolved (shared by `view` JSON + render); factor graph_elements(model, only) so graph works whole-model or view-scoped; render_html(root, view, mode) + TABLE/REVIEW templates (plain-JS, self-contained) + table_or_review_html + view_columns; render mode error. (2) write.rs — append_critique(path, Critique{...}): next-free <element>HRev<n>, UUID + append-only, sanitized procedureText, verification+result+#Verify before the package brace. (3) main.rs — cmd_render + cmd_apply_review (serde_json batch) + dispatch + help. (4) critique_suspect (pure critique_suspect_set) surfaced in `suspect`. (5) D0086 + render.sysml + render skill + registries + viewpoint + doc-sync + critiques for d0086. Scope cuts (documented): findings write the critique + suspicion only — no auto Issue/action (would trip issues/sprint-coverage guards); 'new implementation' rides the suspect->frontier flow. No blockers."; }
    part modularRenderReviewStandupGateR1 : TestResult { :>> id = "63940516-2c7d-4e8f-b085-51627384b607"; :>> outcome = VerdictKind::pass; :>> judgedAgainst = "fdaa84c"; :>> judgedAt = "2026-06-21"; :>> judgedBy = "claudeOpus"; }

    verification modularRenderReviewImplementGate : Test { :>> id = "63940516-2c7d-4e8f-b085-51627384b608"; :>> title = "Sprint 85 implement gate"; :>> createdAt = "2026-06-21"; :>> createdBy = "claudeOpus"; :>> method = VerificationMethod::test; :>> procedureText = "Implemented render (graph/table/review) + apply-review + append_critique + critique_suspect + render process/skill/viewpoint + serde_json dep + doc-sync + d0086 Core-3 critiques. VERIFY (live): render decisions --mode table -> sortable table HTML (style+rows injected, 0 placeholders); render issues --mode review -> exportJSON + capture; render model --mode graph -> inlined-cytoscape HTML; render <view> --mode graph -> view-scoped subgraph; unknown mode -> error exit 1. apply-review smoke (2 dispositions) -> appended parseable critiques; `sysmlv2 validate .` = 97 clean; `sysmlv2 suspect` critique_suspect flagged the finding; restore clean. clippy --workspace --all-targets -D warnings green; cargo test 35 lib pass (incl critique_suspect_flags_unresolved_failing_critique + render_dispatches_modes_and_rejects_unknown); guard all (9) PASS (critique 0 gaps after d0086 critiques; process-change keystone via D0086 #ProspectiveChange + render.sysml)."; }
    part modularRenderReviewImplementGateR1 : TestResult { :>> id = "63940516-2c7d-4e8f-b085-51627384b609"; :>> outcome = VerdictKind::pass; :>> judgedAgainst = "fdaa84c"; :>> judgedAt = "2026-06-21"; :>> judgedBy = "claudeOpus"; }

    verification modularRenderReviewReviewGate : Test { :>> id = "63940516-2c7d-4e8f-b085-51627384b60a"; :>> title = "Sprint 85 review gate"; :>> createdAt = "2026-06-21"; :>> createdBy = "claudeOpus"; :>> method = VerificationMethod::inspect; :>> procedureText = "Diff reviewed. render is a pure computed #View over the same view engine as `view` (run_resolved) — the diagram is now one preset (D0085 subsumed, not retired), so 'modular from an arbitrary view' is real, not diagram-special-cased. apply-review honors text-as-truth: the exported JSON is transport, the durable record is the linked critiques append_critique writes via the sanctioned write path (UUID + append-only); a human review is an INDEPENDENT critique (D0080), recorded as a #Verify-linked verification — never a mutation of the element, never a parallel store. Findings induce COMPUTED suspicion (critique_suspect) — nothing stored. Blast radius checked: serde_json is the only new dep; new edge kinds + critique_suspect are inert to coverage/guards (coverage 110/0, guard all 9 PASS). Honest scope (documented in D0086 + critiques): v1 writes critiques + suspicion, not auto Issue/action (those would trip issues/sprint-coverage); structural fixes machine-verified; the in-browser render + the actual human review are the human's confirmation (the Sprint 83 lesson). doc-sync: CLAUDE.md + usage.md + registries."; }
    part modularRenderReviewReviewGateR1 : TestResult { :>> id = "63940516-2c7d-4e8f-b085-51627384b60b"; :>> outcome = VerdictKind::pass; :>> judgedAgainst = "fdaa84c"; :>> judgedAt = "2026-06-21"; :>> judgedBy = "claudeOpus"; }

    verification modularRenderReviewCloseOutGate : Test { :>> id = "63940516-2c7d-4e8f-b085-51627384b60c"; :>> title = "Sprint 85 closeOut gate (autonomous, D0049)"; :>> createdAt = "2026-06-21"; :>> createdBy = "claudeOpus"; :>> method = VerificationMethod::inspect; :>> procedureText = "Autonomous closeOut (D0049): storyModularRenderReview DoD recorded pass; render (graph/table/review) + apply-review + critique_suspect live; render process/skill/viewpoint registered; D0086 accepted + Core-3 critiqued; doc-sync done; clippy + cargo test (35) + rust validate (97) + guard all (9) green. Self-evidencing (D0051); the in-browser render + the actual human review are the human's confirmation. The modular interactive-artifact renderer + review round-trip are operational."; }
    part modularRenderReviewCloseOutGateR1 : TestResult { :>> id = "63940516-2c7d-4e8f-b085-51627384b60d"; :>> outcome = VerdictKind::pass; :>> judgedAgainst = "fdaa84c"; :>> judgedAt = "2026-06-21"; :>> judgedBy = "claudeOpus"; }

    verification modularRenderReviewRetroGate : Test { :>> id = "63940516-2c7d-4e8f-b085-51627384b60e"; :>> title = "Sprint 85 retro gate (autonomous, D0049)"; :>> createdAt = "2026-06-21"; :>> createdBy = "claudeOpus"; :>> method = VerificationMethod::analyze; :>> procedureText = "Autonomous retro (D0049). WELL: the human's three asks (more toggles / modular-from-arbitrary-view / a reviewing tool) collapsed into ONE capability — render over the view layer + a critique-shaped review round-trip — and the human's own directive ('review = independent critique that attests state + induces suspicion + induces implementation') mapped cleanly onto the existing D0080 critique mechanism + the suspect machinery, so almost nothing new in the data model was needed (reuse over invention). Grounding the design in an explore of the disposition + write-API mechanisms BEFORE coding avoided writing the wrong authored fact. CAUGHT (avoidable-issue candidate): I initially scoped apply-review to auto-create Issues/actions per the first D0086 draft, then found that would trip guard issues (untriaged) + sprint-coverage (sprint-less action) — an avoidable collision I should have predicted from the guard set; corrected to critique+suspicion only, with 'new implementation' riding the normal suspect->frontier flow, and recorded the scope cut honestly in D0086 + the d0086 critiques rather than shipping a guard-breaking write. Lesson: when a new write path creates tracked items, check it against EVERY enforced guard (issues, sprint-coverage) before designing the write, not after. Estimate 8 pts held. The engine now renders any view interactively and round-trips human review as defensible linked critiques that induce suspicion."; }
    part modularRenderReviewRetroGateR1 : TestResult { :>> id = "63940516-2c7d-4e8f-b085-51627384b60f"; :>> outcome = VerdictKind::pass; :>> judgedAgainst = "fdaa84c"; :>> judgedAt = "2026-06-21"; :>> judgedBy = "claudeOpus"; }
}
