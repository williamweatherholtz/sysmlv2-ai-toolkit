// ProjectDeliveryS182 — Sprint 182: declarativeScopeSubLanguage (D0105 migration, MIGRATE step 3).
// Add the non-git SCOPE sub-language (whereStatus) + a sibling-result predicate (hasPassingResult), and
// migrate guard:acceptance-events to a declared ElementRule at PARITY. Also threads model access into the
// predicate engine (sets up relational predicates). Guards still run. EXECUTE. 2 pt. AUTONOMOUS (D0049).
package ProjectDeliveryS182 {
    private import EngineElement::*;
    private import EngineWork::*;
    private import EngineVerification::*;
    private import EngineRelationships::*;

    #CharteredBy dependency from declScopeStory to d0105;

    part declScopeStory : Story {
        :>> id = "63940516-2c7d-4e8f-c182-51627384c001";
        :>> title = "Sprint 182: declarativeScopeSubLanguage (2 pt) - whereStatus scope + hasPassingResult + acceptance-events rule at parity (D0105 MIGRATE)";
        :>> createdAt = "2026-07-03"; :>> createdBy = "wweatherholtz"; :>> kind = WorkKind::code; :>> priority = WorkPriority::p1; :>> owner = "claudeOpus"; :>> estimatedPoints = 2;
    }

    action def DeliveryRunS182 {
        action storyDeclScope;
        verification storyDeclScopeDoD : Test { :>> id = "63940516-2c7d-4e8f-c182-51627384c002"; :>> method = VerificationMethod::test; :>> procedureText = "D0105 MIGRATE step 3 (the SCOPE sub-language, non-git half). (1) subject_in_scope: appliesWhen supports `all` + `whereStatus(v)` (item's status attr == v); unsupported scope (e.g. git-temporal newlyAdded) -> None -> rule reports evaluated=false (never a false pass). (2) predicate engine gains model access (eval_predicate_term now takes model+name) + a new closed-vocab term hasPassingResult(suffix) (sibling item <name><suffix>R1 has outcome=pass) — this also sets up relational predicates for critic-independence. (3) New rule .engine/rules/rules.sysml acceptanceEventRule (subject Decision, appliesWhen whereStatus(accepted), predicate hasPassingResult(Accept)), #JustifiedBy d0066 — mirrors guard:acceptance-events (D0066). (4) PARITY proven: unit test element_rule_scope_and_result_reach_parity_with_acceptance_events (== compute_attestation) + LIVE: `keel rules` acceptanceEventRule (scope whereStatus(accepted), evaluated=true) 0 violations == `keel guard acceptance-events` 0 (102 scanned). NOTHING retired. VERIFY: clippy -D warnings clean; cargo test (4 rule parity tests pass) green; keel validate + guard all (14) green; rule instance rust-validated (D0048). NOTE: git-temporal newlyAdded (charter/sprint-coverage) is the next scope sub-step."; }
        part storyDeclScopeDoDR1 : TestResult { :>> id = "63940516-2c7d-4e8f-c182-51627384c003"; :>> outcome = VerdictKind::pass; :>> judgedAgainst = "8f3a968"; :>> judgedAt = "2026-07-03"; :>> judgedBy = "claudeOpus"; }
    }

    verification declScopeRefineGate : Test { :>> id = "63940516-2c7d-4e8f-c182-51627384c004"; :>> title = "Sprint 182 refine gate (DoR)"; :>> createdAt = "2026-07-03"; :>> createdBy = "claudeOpus"; :>> method = VerificationMethod::inspect; :>> procedureText = "DoR: human chose the scope sub-language next. Non-git half (whereStatus) is the clean start; acceptance-events is its parity target. estimatedPoints=2. #CharteredBy d0105. DoR met."; }
    part declScopeRefineGateR1 : TestResult { :>> id = "63940516-2c7d-4e8f-c182-51627384c005"; :>> outcome = VerdictKind::pass; :>> judgedAgainst = "8f3a968"; :>> judgedAt = "2026-07-03"; :>> judgedBy = "claudeOpus"; }
    verification declScopeStandupGate : Test { :>> id = "63940516-2c7d-4e8f-c182-51627384c006"; :>> title = "Sprint 182 standup gate"; :>> createdAt = "2026-07-03"; :>> createdBy = "claudeOpus"; :>> method = VerificationMethod::inspect; :>> procedureText = "Approach: subject_in_scope (all/whereStatus); thread model+name into predicate eval; add hasPassingResult; author acceptanceEventRule; parity vs guard:acceptance-events (unit + live). Defer git-temporal newlyAdded. No guard retired."; }
    part declScopeStandupGateR1 : TestResult { :>> id = "63940516-2c7d-4e8f-c182-51627384c007"; :>> outcome = VerdictKind::pass; :>> judgedAgainst = "8f3a968"; :>> judgedAt = "2026-07-03"; :>> judgedBy = "claudeOpus"; }
    verification declScopeImplementGate : Test { :>> id = "63940516-2c7d-4e8f-c182-51627384c008"; :>> title = "Sprint 182 implement gate"; :>> createdAt = "2026-07-03"; :>> createdBy = "claudeOpus"; :>> method = VerificationMethod::test; :>> procedureText = "whereStatus scope + hasPassingResult predicate + acceptanceEventRule landed. LIVE: keel rules acceptanceEventRule (whereStatus(accepted), evaluated=true) 0 == guard acceptance-events 0 (102). clippy -D clean; cargo test element_rule_scope_and_result_reach_parity + all rule tests pass; keel validate + guard green."; }
    part declScopeImplementGateR1 : TestResult { :>> id = "63940516-2c7d-4e8f-c182-51627384c009"; :>> outcome = VerdictKind::pass; :>> judgedAgainst = "8f3a968"; :>> judgedAt = "2026-07-03"; :>> judgedBy = "claudeOpus"; }
    verification declScopeReviewGate : Test { :>> id = "63940516-2c7d-4e8f-c182-51627384c00a"; :>> title = "Sprint 182 review gate"; :>> createdAt = "2026-07-03"; :>> createdBy = "claudeOpus"; :>> method = VerificationMethod::inspect; :>> procedureText = "Reviewed. The scope sub-language starts fail-closed (unsupported scope -> evaluated=false), the same honest default as the predicate engine — critical for the inner-platform-risk zone D0105 flagged. Threading model access into predicates was the right investment (enables hasPassingResult now + relational critic-independence later) and stayed bounded. 4th guard at parity. Clean."; }
    part declScopeReviewGateR1 : TestResult { :>> id = "63940516-2c7d-4e8f-c182-51627384c00b"; :>> outcome = VerdictKind::pass; :>> judgedAgainst = "8f3a968"; :>> judgedAt = "2026-07-03"; :>> judgedBy = "claudeOpus"; }
    verification declScopeCloseOutGate : Test { :>> id = "63940516-2c7d-4e8f-c182-51627384c00c"; :>> title = "Sprint 182 closeOut gate (autonomous, D0049)"; :>> createdAt = "2026-07-03"; :>> createdBy = "claudeOpus"; :>> method = VerificationMethod::inspect; :>> procedureText = "Autonomous closeOut (D0049): DoD pass; the non-git scope sub-language works + 4 guards now have parity rules (rootedness, issues, decision-rationale, acceptance-events). clippy + cargo test + keel validate + guard green. Self-evidencing (D0051)."; }
    part declScopeCloseOutGateR1 : TestResult { :>> id = "63940516-2c7d-4e8f-c182-51627384c00d"; :>> outcome = VerdictKind::pass; :>> judgedAgainst = "8f3a968"; :>> judgedAt = "2026-07-03"; :>> judgedBy = "claudeOpus"; }
    verification declScopeRetroGate : Test { :>> id = "63940516-2c7d-4e8f-c182-51627384c00e"; :>> title = "Sprint 182 retro gate (autonomous, D0049)"; :>> createdAt = "2026-07-03"; :>> createdBy = "claudeOpus"; :>> method = VerificationMethod::analyze; :>> procedureText = "Autonomous retro (D0049). WELL: the scope sub-language landed fail-closed + parity-gated; threading model access into the predicate engine paid double (hasPassingResult now, relational critic-independence next). AVOIDABLE-ISSUE SCAN: none new this sprint. LESSON: the whereStatus/sibling-result combo shows most 'structural' guards are really scope+predicate compositions — the bounded-vocabulary bet (D0105) is holding. Estimate 2 pt held. PROGRESS: 4 of ~14 guards at parity (spanning EdgeRule + ElementRule + the whereStatus scope). REMAINING: git-temporal newlyAdded (charter/sprint-coverage) — the genuinely hard scope predicate + the flagged inner-platform risk; relational distinct (critic-independence); external-file guards (manifest-coverage/viewpoint-renderer); OrderingRule (ceremony); then CONTRACT + the `keel check` name reconciliation."; }
    part declScopeRetroGateR1 : TestResult { :>> id = "63940516-2c7d-4e8f-c182-51627384c00f"; :>> outcome = VerdictKind::pass; :>> judgedAgainst = "8f3a968"; :>> judgedAt = "2026-07-03"; :>> judgedBy = "claudeOpus"; }
}
