// ProjectDeliveryS629 — Sprint 629: The decision brief carries each ask as its own tab, states no implementation duration, and names every member of any set it counts - the three defects the human read off the standing page on 2026-09-09 become checker clauses, not a rewrite (D0404, D0405, D0406; D0407 proposed). EXECUTE. 3 pts.
package ProjectDeliveryS629 {
    private import EngineElement::*;
    private import EngineWork::*;
    private import EngineVerification::*;
    private import EngineRelationships::*;

    #CharteredBy dependency from briefTabsNoDurationsNamedMembersStory to d0404;

    part briefTabsNoDurationsNamedMembersStory : Story {
        :>> id = "232e2f96-73b1-4a55-8242-dfe369a374a4";
        :>> title = "Sprint 629: The decision brief carries each ask as its own tab, states no implementation duration, and names every member of any set it counts - the three defects the human read off the standing page on 2026-09-09 become checker clauses, not a rewrite (issue425; D0404, D0405, D0406; D0407 proposed) (3 pts)";
        :>> createdAt = "2026-09-09"; :>> createdBy = "claudeOpus5"; :>> kind = WorkKind::code; :>> priority = WorkPriority::p0; :>> owner = "claudeOpus5"; :>> estimatedPoints = 3;
    }

    action def DeliveryRunS629 {
        action storyBriefTabsNoDurationsNamedMembers;
        verification storyBriefTabsNoDurationsNamedMembersDoD : Test { :>> id = "34b6efe5-78b7-426f-97f2-0f987e4ffaec"; :>> method = VerificationMethod::test; :>> procedureText = "DELIVERED (resolves issue425): scripts/check_templates.py check_brief gains four clauses - tabs, panels and asks are one count with exactly one tab selected (D0404); a duration phrase in reader prose is refused, a date is not one (D0405); an aggregate verb on a counted set requires a data-members table whose named members reconcile with its count (D0406); the ceiling is measured per tab when D0407 is accepted and summed until then - each with known-positive and known-negative cases in --self-test. scripts/exec_brief/facts.py emits cliLiveTopLevelByFamily (every live verb with its family and effect, or null if the groups do not sum), fitProbeCases, briefBuilders and briefBuildersEndingInFit. scripts/exec_brief/build_2026_09_09_five_asks_tabbed.py renders five asks as five tabs, computes the members table and the remainder (34 of 67 fold, 34 remain) from the fact under D0399 option A's own mapping, states this page's frame, largest-tab and summed word counts by the checker's reading, and ends in assert_fits. asi-templates SKILL.md 2.1-2.2 state the tabbed shape, the no-duration rule and the members rule. VERIFIED: --self-test 18 of 18 including the new cases; the built page passes every clause per tab and fails exactly the summed ceiling, which is D0407's question; every tab screenshotted and read; fit_check clean on both font passes."; }
        // RAN: python scripts/check_templates.py --self-test -> pass, 18 of 18 (tabs, duration, members and per-tab cases named in the sprint); python scripts/exec_brief/build_2026_09_09_five_asks_tabbed.py facts.json prev.html out.html -> frame 144 words, largest tab 236, members table names 67 verbs, 34 fold, 34 remain, fit_check fits (4 probe cases first); check_templates --brief out.html -> 1 violation, the summed 927-word ceiling (D0407 proposed), and clean with per_tab=True; every tab screenshotted and read
        part storyBriefTabsNoDurationsNamedMembersDoDR1 : TestResult { :>> id = "407b8ec9-e71f-4e06-aaef-044ccc1a6164"; :>> outcome = VerdictKind::pass; :>> judgedAgainst = "0d5be97"; :>> judgedAt = "2026-09-09"; :>> judgedBy = "claudeOpus5"; }
    }

    verification briefTabsNoDurationsNamedMembersRefineGate : Test { :>> id = "55e205f9-8091-470f-9283-229e09ace194"; :>> title = "Sprint 629 refine gate (DoR)"; :>> createdAt = "2026-09-09"; :>> createdBy = "claudeOpus5"; :>> method = VerificationMethod::inspect; :>> procedureText = "READY. The human's words of 2026-09-09 are three Decisions accepted on their quoted text (D0404-D0406); D0407 is the clause they force and waits for their word. 3 points: checker clauses with cases, a members fact, a tabbed builder, skill text."; }
    // RAN: the human's message of 2026-09-09 quoted into D0404-D0406 and accepted on those words (keel accept --words); D0407 recorded proposed; 3 points sized against sprint 628's shape
    part briefTabsNoDurationsNamedMembersRefineGateR1 : TestResult { :>> id = "a24dcf9e-d11c-41d9-b5ac-a3ce20b6e846"; :>> outcome = VerdictKind::pass; :>> judgedAgainst = "0d5be97"; :>> judgedAt = "2026-09-09"; :>> judgedBy = "claudeOpus5"; }
    verification briefTabsNoDurationsNamedMembersStandupGate : Test { :>> id = "68accae7-f54c-4ae9-97fb-3d9603665ac5"; :>> title = "Sprint 629 standup gate"; :>> createdAt = "2026-09-09"; :>> createdBy = "claudeOpus5"; :>> method = VerificationMethod::inspect; :>> procedureText = "Blockers: the built page cannot be published while D0407 is proposed - the checker measures summed and refuses 927 words; the standing page stays up with the defects until the human answers. No other blocker."; }
    // RAN: blocker stated: check_templates --brief measures summed while D0407 is proposed and refuses the 927-word tabbed page, so the standing page stays published until the human answers
    part briefTabsNoDurationsNamedMembersStandupGateR1 : TestResult { :>> id = "1421ef7a-1e0e-4d2a-9043-a6112ef00d27"; :>> outcome = VerdictKind::pass; :>> judgedAgainst = "0d5be97"; :>> judgedAt = "2026-09-09"; :>> judgedBy = "claudeOpus5"; }
    verification briefTabsNoDurationsNamedMembersImplementGate : Test { :>> id = "90690e9b-8b4e-46ad-acd3-c7f7c0995667"; :>> title = "Sprint 629 implement gate"; :>> createdAt = "2026-09-09"; :>> createdBy = "claudeOpus5"; :>> method = VerificationMethod::test; :>> procedureText = "Checker first, with its cases named before the page was read: 'A five collapses, a day each.' refused, 'Waiting since 2026-09-01.' passes; 'Collapse five families.' refused without a table, passes with five named members, refused with four named against five declared; two asks under one tab refused; two 300-word tabs pass per tab and fail summed. Then the fact, then the builder. The builder's own word count first disagreed with the checker by 164 words (it counted the charts' inline CSS) and then by 5 (the document title) and then by 1 (a stub token) - each time the checker's reading was adopted, so the number the page states about itself is the checker's."; }
    // RAN: check_templates --self-test 18/18; facts.py -> cliLiveTopLevelByFamily sums to 67 = cliLiveTopLevel, fitProbeCases 4, briefBuilders 10, briefBuildersEndingInFit 1; builder self-count matched the checker (927) after adopting markup_only and the whole-document reading; shots.py: 5 tabs, 5 panels, 1 visible, arrow keys and click switch, digest lists all 5 h2
    part briefTabsNoDurationsNamedMembersImplementGateR1 : TestResult { :>> id = "8ee61e7b-626f-409c-8014-d31435c2a049"; :>> outcome = VerdictKind::pass; :>> judgedAgainst = "0d5be97"; :>> judgedAt = "2026-09-09"; :>> judgedBy = "claudeOpus5"; }
    verification briefTabsNoDurationsNamedMembersReviewGate : Test { :>> id = "b14ef57a-6a24-4011-9030-de5d58528391"; :>> title = "Sprint 629 review gate — three passes per D0172"; :>> createdAt = "2026-09-09"; :>> createdBy = "claudeOpus5"; :>> method = VerificationMethod::inspect; :>> procedureText = "Pass 1 (intent): each of the human's three sentences maps to one clause with a refusing case that reproduces the defect they named. Pass 2 (defects): the members table names all 67 live verbs and the builder refuses when that count differs from cliLiveTopLevel; D0399's text estimated the remainder at about 20 and the members give 34, which the page says rather than hides. Pass 3 (docs): SKILL.md 2.1-2.2, D0404-D0407 and the checker's clause comments say the same rules."; }
    // RAN: three passes: each of the human's three sentences has a refusing case reproducing its defect; members table count asserted equal to cliLiveTopLevel in the builder; SKILL.md 2.1-2.2, D0404-D0407 and the checker comments state the same rules; D0407 context corrected to the measured 927/144/236
    part briefTabsNoDurationsNamedMembersReviewGateR1 : TestResult { :>> id = "e4451d34-ce10-4c97-b81e-10f4ae3d0efe"; :>> outcome = VerdictKind::pass; :>> judgedAgainst = "0d5be97"; :>> judgedAt = "2026-09-09"; :>> judgedBy = "claudeOpus5"; }
    verification briefTabsNoDurationsNamedMembersCloseOutGate : Test { :>> id = "7df7e5ff-a734-4574-9a15-0ff64447dd11"; :>> title = "Sprint 629 closeOut gate (autonomous, D0049)"; :>> createdAt = "2026-09-09"; :>> createdBy = "claudeOpus5"; :>> method = VerificationMethod::inspect; :>> procedureText = "A brief now shows one ask at a time, never says how long, and names what it counts. The page that says so is built and measured but waits on the ceiling Decision to be published."; }
    // RAN: keel validate . and keel guard . --no-receipt at 0d5be97 before commit (output in the commit's gate run); issue425 recorded with #Resolves from this Story
    part briefTabsNoDurationsNamedMembersCloseOutGateR1 : TestResult { :>> id = "0b118816-3176-40f2-b4da-20c3460c44ef"; :>> outcome = VerdictKind::pass; :>> judgedAgainst = "0d5be97"; :>> judgedAt = "2026-09-09"; :>> judgedBy = "claudeOpus5"; }
    verification briefTabsNoDurationsNamedMembersRetroGate : Test { :>> id = "8387c05a-0875-4385-b5a0-a11a6660d25b"; :>> title = "Sprint 629 retro gate (autonomous, D0049)"; :>> createdAt = "2026-09-09"; :>> createdBy = "claudeOpus5"; :>> method = VerificationMethod::analyze; :>> procedureText = "Retro held; avoidable-issue scan: three defects were published on one page under a checker that had a clause for none of them - the manual-vigilance class, tracked as issue425 and resolved here by clauses with cases. One recurrence noted: the builder's self-count disagreed with the checker three times before matching; a page that states a number about itself should call the checker's function, which it now does. No new item."; }
    // RAN: avoidable-issue scan: three published defects under a checker with no clause for them - tracked as issue425, resolved by clauses with cases; the builder's self-count disagreed with the checker three times before it called the checker's own functions; no new item
    part briefTabsNoDurationsNamedMembersRetroGateR1 : TestResult { :>> id = "035cc0ac-49f1-45fd-bfe7-d53dd74676e7"; :>> outcome = VerdictKind::pass; :>> judgedAgainst = "0d5be97"; :>> judgedAt = "2026-09-09"; :>> judgedBy = "claudeOpus5"; }
}
