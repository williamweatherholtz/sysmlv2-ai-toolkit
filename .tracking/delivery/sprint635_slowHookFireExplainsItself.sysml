// ProjectDeliveryS635 — Sprint 635: Sprint 635: a slow hook fire explains itself from the ledger - a fire at or past 3 000 ms carries a phases field naming its serial steps longest first, the guard runner's critical path and the unattributed remainder; enforcement-report lists the slow fires by phase; the guard receipt records the critical path (dcSlowHookFireExplainsItself, issue429, D0414). EXECUTE under the Change Request route: hook and guard source are the enforcement surface. 3 pts.. EXECUTE. 3 pts.
package ProjectDeliveryS635 {
    private import EngineElement::*;
    private import EngineWork::*;
    private import EngineVerification::*;
    private import EngineRelationships::*;

    #CharteredBy dependency from slowHookFireExplainsItselfStory to d0414;

    part slowHookFireExplainsItselfStory : Story {
        :>> id = "73257770-1462-4ada-8e1a-9d0828fc3f41";
        :>> title = "Sprint 635: Sprint 635: a slow hook fire explains itself from the ledger - a fire at or past 3 000 ms carries a phases field naming its serial steps longest first, the guard runner's critical path and the unattributed remainder; enforcement-report lists the slow fires by phase; the guard receipt records the critical path (dcSlowHookFireExplainsItself, issue429, D0414). EXECUTE under the Change Request route: hook and guard source are the enforcement surface. 3 pts. (3 pts)";
        :>> createdAt = "2026-09-09"; :>> createdBy = "claudeOpus5"; :>> kind = WorkKind::code; :>> priority = WorkPriority::p0; :>> owner = "claudeOpus5"; :>> estimatedPoints = 3;
    }

    action def DeliveryRunS635 {
        action storySlowHookFireExplainsItself;
        verification storySlowHookFireExplainsItselfDoD : Test { :>> id = "845f2cf7-f723-4a4b-a1c0-ca8eadd8d039"; :>> method = VerificationMethod::test; :>> procedureText = "DELIVERED (dcSlowHookFireExplainsItself, resolves issue429 through that item): perf.rs collect_phases turns phase collection on without KEEL_PERF, attribute is the pure attribution (hook:* serial steps and the longest guard:* labelled critical path longest first, unattributed = total minus the serial sum, then git xN summed and parse which never lead); pm.rs SLOW_FIRE_MS = 3000, slow_fire_phases returns None under it, LEDGER_ADDITIVE_FIELDS names bin/build/phases beside the frozen core, enforcement-report gains slowFires (threshold, count, last 25 rows by phase, a pre-D0414 line stated as unattributed); main.rs names hook:receipt-key, hook:validate, hook:guards, hook:rules, hook:recall, hook:fast-guards, hook:advisory, hook:fingerprint and ledger_emit attaches phases past the threshold; guards.rs times every guard and keeps the run's critical path, which the receipt stores as critical_path and KEEL_PERF=1 keel guard prints. PROBED (D0388) before the live ledger was read: known-positive attribute over hook:validate 5000 + hook:guards 700 of a 6000 total names hook:validate first and unattributed 300, with git x44 summed at 14 114 placed after the steps; known-negative attribute over no hook phase yields only unattributed = total, and slow_fire_phases(2999) is None; both named in the_longest_step_leads_and_the_uncovered_remainder_is_named and a_fast_fire_carries_no_phases_and_a_slow_one_always_carries_the_remainder; the report's row test writes a 217 ms line, a 28 000 ms line with phases and a 35 000 ms line without and reads back one row per slow line with the hook's first phase first. LIVE: keel hook stop after keel guard (receipt covered guards only) -> ms 8337 with phases git x46 summed 12778 / hook:guards 7269 / guard:priority-inversion (critical path) 7160 / parse 1234 / hook:validate 578 / hook:rules 267 / hook:receipt-key 144 / unattributed 79 (this line predates the reorder that moves summed counters after the steps); the next stop, a receipt hit -> ms 205, no phases field; keel enforcement-report . slowFires threshold 3000 count 993, the newest row by phase and the 992 before it stated as recorded before D0414; guard-receipt.toml critical_path = priority-inversion 7160 ms; KEEL_PERF=1 keel guard --no-receipt . prints critical path: priority-inversion 6070 ms. D0414 records the field (process-change, proposed for the human); CLAUDE.md section 5 states it."; }
        // RAN: probe pair the_longest_step_leads_and_the_uncovered_remainder_is_named + a_fast_fire_carries_no_phases_and_a_slow_one_always_carries_the_remainder (cargo test --release -p keel-cli --lib -> 445 passed); live: hook stop -> ms 8337 with phases hook:guards 7269 / guard:priority-inversion (critical path) 7160; receipt-hit stop -> ms 205 no phases; enforcement-report slowFires count 993 newest row by phase; guard-receipt critical_path = priority-inversion 7160 ms
        part storySlowHookFireExplainsItselfDoDR1 : TestResult { :>> id = "0471ae6d-56bb-4a71-98b4-dba8e8c758d2"; :>> outcome = VerdictKind::pass; :>> judgedAgainst = "df7a54e8780090a9c721525e3d573e270a863f9a"; :>> judgedAt = "2026-09-09"; :>> judgedBy = "claudeOpus5"; }
    }

    verification slowHookFireExplainsItselfRefineGate : Test { :>> id = "a86203b2-e605-46fe-aaa2-c71b4d4868b5"; :>> title = "Sprint 635 refine gate (DoR)"; :>> createdAt = "2026-09-09"; :>> createdBy = "claudeOpus5"; :>> method = VerificationMethod::inspect; :>> procedureText = "Definition of Ready: dcSlowHookFireExplainsItself at the head of keel whats-next . after df7a54e, placed there by the backlog reorder that answered the human's 'kind of seems like keel is still crazy slow'; its DoD names the property (a slow fire explains itself from the ledger), the DO (phases past a threshold, the critical path in the receipt and runner output, a slow row per fire in enforcement-report, unattributed ms rather than omission) and the forbidden adjacent changes (shortening priority-inversion, moving guards off the stop hook); no fork; 3 points - five source files, five tests, a CLAUDE.md paragraph and a Decision."; }
    // RAN: sprint 635 Refine step: see the sprint record's Refine text; cargo test --release -p keel-cli --lib -> 445 passed; keel guard . -> ALL PASS
    part slowHookFireExplainsItselfRefineGateR1 : TestResult { :>> id = "884cf494-b0ec-4e5b-8939-2c6fff06ea37"; :>> outcome = VerdictKind::pass; :>> judgedAgainst = "df7a54e8780090a9c721525e3d573e270a863f9a"; :>> judgedAt = "2026-09-09"; :>> judgedBy = "claudeOpus5"; }
    verification slowHookFireExplainsItselfStandupGate : Test { :>> id = "d6147f5a-868f-43ae-8823-7deae334aeb9"; :>> title = "Sprint 635 standup gate"; :>> createdAt = "2026-09-09"; :>> createdBy = "claudeOpus5"; :>> method = VerificationMethod::inspect; :>> procedureText = "No blocker. One design point settled by the first live line: the summed git wait across twenty threads (12 778 ms) sorted above the fire's own total (8 337 ms), so a reader's first entry exceeded the line's total; the attribution was split into wall-clock steps longest first and summed counters after, and the probe test now asserts a 14 s summed counter never leads a 6 s fire."; }
    // RAN: sprint 635 Standup step: see the sprint record's Standup text; cargo test --release -p keel-cli --lib -> 445 passed; keel guard . -> ALL PASS
    part slowHookFireExplainsItselfStandupGateR1 : TestResult { :>> id = "64946832-ae28-442f-803a-8baf472ec18c"; :>> outcome = VerdictKind::pass; :>> judgedAgainst = "df7a54e8780090a9c721525e3d573e270a863f9a"; :>> judgedAt = "2026-09-09"; :>> judgedBy = "claudeOpus5"; }
    verification slowHookFireExplainsItselfImplementGate : Test { :>> id = "59782c3f-409a-4fd9-a59a-189bae2721c6"; :>> title = "Sprint 635 implement gate"; :>> createdAt = "2026-09-09"; :>> createdBy = "claudeOpus5"; :>> method = VerificationMethod::test; :>> procedureText = "perf.rs, pm.rs, guards.rs, receipt.rs and main.rs patched through textpatch (patch635.py, patch635b.py, clippy635.py, order635.py); one helper-script defect on the way: a 16-space anchor matched inside its 20-space twin and the guards.rs block was re-anchored on the newline before a second run; a Python literal wrote a backslash-n tail into pm.rs that rustc refused (unknown start of token) and was repaired before the build. cargo build --release green; cargo clippy --workspace --all-targets -- -D warnings green after four pedantic findings (too_long_first_doc_paragraph x2, map_or_else, too_many_lines on enforcement_report allowed with its reason); cargo test --release -p keel-cli --lib -> 445 passed; keel record decision D0414 --process-change -> proposed, OUTSIDE standing consent."; }
    // RAN: sprint 635 Implement step: see the sprint record's Implement text; cargo test --release -p keel-cli --lib -> 445 passed; keel guard . -> ALL PASS
    part slowHookFireExplainsItselfImplementGateR1 : TestResult { :>> id = "02422832-4ade-4036-ac28-473096560ced"; :>> outcome = VerdictKind::pass; :>> judgedAgainst = "df7a54e8780090a9c721525e3d573e270a863f9a"; :>> judgedAt = "2026-09-09"; :>> judgedBy = "claudeOpus5"; }
    verification slowHookFireExplainsItselfReviewGate : Test { :>> id = "51d4f835-18bf-4748-960d-4ee38f2e633b"; :>> title = "Sprint 635 review gate — three passes per D0172"; :>> createdAt = "2026-09-09"; :>> createdBy = "claudeOpus5"; :>> method = VerificationMethod::inspect; :>> procedureText = "Three passes per D0172: (1) the pure attribution is tested on both sides of the probe pair and on the over-attributed case, where the remainder saturates at zero rather than wrapping; (2) the reader is tested with a fast line, a slow line with phases and a slow line without, so a row exists per slow fire and a pre-D0414 line is stated rather than read as empty; (3) the emitter's threshold is asserted at SLOW_FIRE_MS - 1 and SLOW_FIRE_MS, and the live ledger's next slow fire was read back from the report by phase."; }
    // RAN: sprint 635 Review step: see the sprint record's Review text; cargo test --release -p keel-cli --lib -> 445 passed; keel guard . -> ALL PASS
    part slowHookFireExplainsItselfReviewGateR1 : TestResult { :>> id = "7748b365-be77-4e7b-a335-0608360d03d4"; :>> outcome = VerdictKind::pass; :>> judgedAgainst = "df7a54e8780090a9c721525e3d573e270a863f9a"; :>> judgedAt = "2026-09-09"; :>> judgedBy = "claudeOpus5"; }
    verification slowHookFireExplainsItselfCloseOutGate : Test { :>> id = "9b4be291-9ad5-4472-8612-a883b319cba1"; :>> title = "Sprint 635 closeOut gate (autonomous, D0049)"; :>> createdAt = "2026-09-09"; :>> createdBy = "claudeOpus5"; :>> method = VerificationMethod::inspect; :>> procedureText = "keel validate . clean, keel check-engine . clean, keel gate --fast clean; dcSlowHookFireExplainsItself DoD stamped with the probe pair and the live line named."; }
    // RAN: sprint 635 CloseOut step: see the sprint record's CloseOut text; cargo test --release -p keel-cli --lib -> 445 passed; keel guard . -> ALL PASS
    part slowHookFireExplainsItselfCloseOutGateR1 : TestResult { :>> id = "d910f43f-1561-49ad-8e3d-d09302a32973"; :>> outcome = VerdictKind::pass; :>> judgedAgainst = "df7a54e8780090a9c721525e3d573e270a863f9a"; :>> judgedAt = "2026-09-09"; :>> judgedBy = "claudeOpus5"; }
    verification slowHookFireExplainsItselfRetroGate : Test { :>> id = "ef84307b-ba38-4815-bb77-190b3b8119f0"; :>> title = "Sprint 635 retro gate (autonomous, D0049)"; :>> createdAt = "2026-09-09"; :>> createdBy = "claudeOpus5"; :>> method = VerificationMethod::analyze; :>> procedureText = "Avoidable-issue scan: the first live attribution put a summed counter above the total, a reading defect the pure test had not covered because its git sum was smaller than the total - the case is now the test. Two textpatch misfires (a prefix-substring anchor, a literal backslash-n) cost one build each; textpatch refused neither because both were legal single matches, so no control is proposed - the anchors were mine. Observed and NOT concluded: priority-inversion measured 2 102 ms idle on a clean tree at issue429's opening and 6 070-7 160 ms on this dirty tree; whether the dirty tree is the cause is checked after this commit lands, against the clean tree, and recorded as an Issue only if it holds. No new item: the one finding this sprint tracked is issue429, already tracked and resolved through this sprint."; }
    // RAN: sprint 635 Retro step: see the sprint record's Retro text; cargo test --release -p keel-cli --lib -> 445 passed; keel guard . -> ALL PASS
    part slowHookFireExplainsItselfRetroGateR1 : TestResult { :>> id = "2c0734e0-4c5e-4598-9321-af6dd9bdbb50"; :>> outcome = VerdictKind::pass; :>> judgedAgainst = "df7a54e8780090a9c721525e3d573e270a863f9a"; :>> judgedAt = "2026-09-09"; :>> judgedBy = "claudeOpus5"; }
}
