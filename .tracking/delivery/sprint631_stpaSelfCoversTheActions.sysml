// ProjectDeliveryS631 — Sprint 631: Sprint 631: The hazard analysis covers the human's authority reaching the model, and the currency warning names the next tranche instead of standing on a number (dcStpaSelfCoversTheActions, issue403, D0410). EXECUTE via the stpa-self skill. 3 pts.. EXECUTE. 3 pts.
package ProjectDeliveryS631 {
    private import EngineElement::*;
    private import EngineWork::*;
    private import EngineVerification::*;
    private import EngineRelationships::*;

    #CharteredBy dependency from stpaSelfCoversTheActionsStory to d0410;

    part stpaSelfCoversTheActionsStory : Story {
        :>> id = "8978efc3-4e29-40f2-bac9-4ed753ac2fa2";
        :>> title = "Sprint 631: Sprint 631: The hazard analysis covers the human's authority reaching the model, and the currency warning names the next tranche instead of standing on a number (dcStpaSelfCoversTheActions, issue403, D0410). EXECUTE via the stpa-self skill. 3 pts. (3 pts)";
        :>> createdAt = "2026-09-09"; :>> createdBy = "claudeOpus5"; :>> kind = WorkKind::code; :>> priority = WorkPriority::p0; :>> owner = "claudeOpus5"; :>> estimatedPoints = 3;
    }

    action def DeliveryRunS631 {
        action storyStpaSelfCoversTheActions;
        verification storyStpaSelfCoversTheActionsDoD : Test { :>> id = "48caadfd-ce46-48d5-98d6-725f3a2f4d3f"; :>> method = VerificationMethod::test; :>> procedureText = "DELIVERED (dcStpaSelfCoversTheActions, resolves issue403 through that item): stpa-self run 2 walks the six actions of the human->model, human->work and console->model edges - cmdAccept, cmdReject, cmdOverride, humanDecidesOnChannel, consoleApprovesWrite, humanDirects - through all four UCA types against the code (main.rs verdict_channel_refusal / tty_gesture / consume_override, checks.rs quotes_conversational_words, mod.rs read_back_names, write.rs reject_decision_locked, serve.rs device tag and plan-bound approval, control_structure.rs channel_wired); four UCAs whose contexts name the action and the state it runs in, four constraints - one bound to gAcceptanceBindsToText, three to new Issues with resolvers: issue426 a gesture citation is typed text (dcGestureCitationsAreWrittenByTheCommand, High), issue427 an override target is a substring (dcOverrideBindsToOneFile, Medium), issue428 direction is rendered not recorded (dcDirectionDecisionsLinkTheirStatement, Medium); the run record stpaRun2 with its ANALYSED list and passing result. The stpa-currency guard's message is regrouped (D0410 proposed, process-change): count kept, TARGET stated, OPEN EDGES with k-of-n form, NEXT TRANCHE named with its copy-out ANALYSED list; control_structure.rs gains LocalAction and local_actions; six unit tests. The uncovered count read back from the guard falls 45 -> 39 and the remainder is named by edge: hooks->agent-turn 7, commit-gate->main-ref 4, ci->main-ref 3, agent->model 15 of 19, agent->work 1, agent->enforcement-surface 6, agent->main-ref 2 of 3, agent->deliverable 1; next tranche agent->deliverable. guards.md, the stpa5 process text and the stpa-self skill state the edge-as-tranche rule."; }
        // RAN: keel guard stpa-currency . read back: 39 of 48 open, eight edges named, NEXT TRANCHE agent->deliverable; cargo test -p keel-cli --lib stpa_currency 6 passed; keel validate . 716 clean
        part storyStpaSelfCoversTheActionsDoDR1 : TestResult { :>> id = "cb0df8e4-8d09-4d54-ab07-9b59a9220850"; :>> outcome = VerdictKind::pass; :>> judgedAgainst = "e9c5a83f27566cdc0a2a78aa9d9e85c52847019e"; :>> judgedAt = "2026-09-09"; :>> judgedBy = "claudeOpus5"; }
    }

    verification stpaSelfCoversTheActionsRefineGate : Test { :>> id = "c6e34260-d6b7-4e67-91cb-d5b6e02fec0d"; :>> title = "Sprint 631 refine gate (DoR)"; :>> createdAt = "2026-09-09"; :>> createdBy = "claudeOpus5"; :>> method = VerificationMethod::inspect; :>> procedureText = "Definition of Ready: dcStpaSelfCoversTheActions at the head of keel whats-next . after e9c5a83; its DoD names three verifications (the count falls and the remainder is named, contexts are states not beliefs, the warning is actionable); the tranche is chosen as the three edges that carry the human's authority into the model, because they are the edges the founding hazard EHZ3 sits on and the second run should cover the part of the system where a misrecorded judgment does the most; 3 points - a six-action analysis with code reads, a guard message change with tests, a Decision and doc-sync."; }
    // RAN: sprint 631 Refine: see the sprint record's section; keel validate . 716 clean, keel check-engine . clean
    part stpaSelfCoversTheActionsRefineGateR1 : TestResult { :>> id = "730632f8-5c8c-4e41-8341-4c65031c9814"; :>> outcome = VerdictKind::pass; :>> judgedAgainst = "e9c5a83f27566cdc0a2a78aa9d9e85c52847019e"; :>> judgedAt = "2026-09-09"; :>> judgedBy = "claudeOpus5"; }
    verification stpaSelfCoversTheActionsStandupGate : Test { :>> id = "fa1c8f80-b754-41a0-abbe-8caaff6da2e1"; :>> title = "Sprint 631 standup gate"; :>> createdAt = "2026-09-09"; :>> createdBy = "claudeOpus5"; :>> method = VerificationMethod::inspect; :>> procedureText = "No blocker. One judgment the DoD asked for - what the warning should say - is settled by the structure's own shape and recorded in D0410 as NOT A FORK; D0410 stays proposed for the human because it changes guard text (D0337)."; }
    // RAN: sprint 631 Standup: see the sprint record's section; keel validate . 716 clean, keel check-engine . clean
    part stpaSelfCoversTheActionsStandupGateR1 : TestResult { :>> id = "ebed5afa-46d2-49f9-b59b-cadfb92d2289"; :>> outcome = VerdictKind::pass; :>> judgedAgainst = "e9c5a83f27566cdc0a2a78aa9d9e85c52847019e"; :>> judgedAt = "2026-09-09"; :>> judgedBy = "claudeOpus5"; }
    verification stpaSelfCoversTheActionsImplementGate : Test { :>> id = "8ec4694d-85f9-4f4b-988d-1e926f0b3ac7"; :>> title = "Sprint 631 implement gate"; :>> createdAt = "2026-09-09"; :>> createdBy = "claudeOpus5"; :>> method = VerificationMethod::test; :>> procedureText = "keel show control-structure . read (48 local actions); six actions walked; keel add-task x3, keel record issue x3 (triaged on arrival), the run-2 block inserted through textpatch insert_after; cargo test --release -p keel-cli --lib stpa_currency -> 6 passed; cargo build --release; keel guard stpa-currency . read back with the grouped message; keel record decision D0410 --process-change (OUTSIDE standing consent, proposed); keel sync-claude . 46/46; keel check-engine . clean; keel validate . 716 clean."; }
    // RAN: sprint 631 Implement: see the sprint record's section; keel validate . 716 clean, keel check-engine . clean
    part stpaSelfCoversTheActionsImplementGateR1 : TestResult { :>> id = "f9c2bb24-9208-45dc-b6e2-24ca1f9f395d"; :>> outcome = VerdictKind::pass; :>> judgedAgainst = "e9c5a83f27566cdc0a2a78aa9d9e85c52847019e"; :>> judgedAt = "2026-09-09"; :>> judgedBy = "claudeOpus5"; }
    verification stpaSelfCoversTheActionsReviewGate : Test { :>> id = "698209b7-11dc-46b0-b097-d3708805b32d"; :>> title = "Sprint 631 review gate — three passes per D0172"; :>> createdAt = "2026-09-09"; :>> createdBy = "claudeOpus5"; :>> method = VerificationMethod::inspect; :>> procedureText = "Three passes per D0172: (1) every UCA context names the action verbatim and a state - a session marker, an edit at a later commit, a target string, a chat direction - not a belief or an outcome, and every statement cites the function it read; (2) the CONSIDERED SAFE lines name the code that makes each safe (read_back_names, reject_decision_locked, ctlOverrideObligation, srServeApproveGateHuman, channel_wired), so a later reader can re-check each rather than trust the word safe; (3) the guard's tests fix the k-of-n form, the tie-break and the copy-out list, and the doc surface says the rule in the same words as the message."; }
    // RAN: sprint 631 Review: see the sprint record's section; keel validate . 716 clean, keel check-engine . clean
    part stpaSelfCoversTheActionsReviewGateR1 : TestResult { :>> id = "49b0d083-4ced-4136-a05d-70ddd91f9177"; :>> outcome = VerdictKind::pass; :>> judgedAgainst = "e9c5a83f27566cdc0a2a78aa9d9e85c52847019e"; :>> judgedAt = "2026-09-09"; :>> judgedBy = "claudeOpus5"; }
    verification stpaSelfCoversTheActionsCloseOutGate : Test { :>> id = "249e5f05-26e4-4bcd-90b4-e7c37ac52a88"; :>> title = "Sprint 631 closeOut gate (autonomous, D0049)"; :>> createdAt = "2026-09-09"; :>> createdBy = "claudeOpus5"; :>> method = VerificationMethod::inspect; :>> procedureText = "keel validate . clean (716 files), keel check-engine . clean, keel gate --fast clean; keel guard . carries the pre-existing warning classes and, for this sprint, the D0064 coverage it supplies; dcStpaSelfCoversTheActions DoD stamped at e9c5a83 with the remainder count and its edges named."; }
    // RAN: sprint 631 CloseOut: see the sprint record's section; keel validate . 716 clean, keel check-engine . clean
    part stpaSelfCoversTheActionsCloseOutGateR1 : TestResult { :>> id = "a881fdd2-746f-45a0-964c-5e4715447993"; :>> outcome = VerdictKind::pass; :>> judgedAgainst = "e9c5a83f27566cdc0a2a78aa9d9e85c52847019e"; :>> judgedAt = "2026-09-09"; :>> judgedBy = "claudeOpus5"; }
    verification stpaSelfCoversTheActionsRetroGate : Test { :>> id = "9ed29bd9-75a6-42b0-90a1-f23817dc48f9"; :>> title = "Sprint 631 retro gate (autonomous, D0049)"; :>> createdAt = "2026-09-09"; :>> createdBy = "claudeOpus5"; :>> method = VerificationMethod::analyze; :>> procedureText = "Avoidable-issue scan: the second run found three open channels for the founding hazard - a gesture that is text, a target that is a substring, a direction that is a rendering - none of which a test had asked about, because the first run chose its actions by hand and the guard's flat list gave the second no reason to start where the authority enters. The fix that closes that class is the guard naming the next tranche; the three gaps are tracked as issue426, issue427 and issue428 with resolvers, and this sprint adds no further item beyond those: no new item is needed for the guard change itself, which D0410 records."; }
    // RAN: sprint 631 Retro: see the sprint record's section; keel validate . 716 clean, keel check-engine . clean
    part stpaSelfCoversTheActionsRetroGateR1 : TestResult { :>> id = "e7bda55a-cbd9-4127-b5bb-39031681154b"; :>> outcome = VerdictKind::pass; :>> judgedAgainst = "e9c5a83f27566cdc0a2a78aa9d9e85c52847019e"; :>> judgedAt = "2026-09-09"; :>> judgedBy = "claudeOpus5"; }
}
