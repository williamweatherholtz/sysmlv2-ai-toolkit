// ProjectDeliveryS413 — Sprint 413: the D0070 marker becomes a recorder flag (issue213) - the forgettable hand-edit that refused two landing commits is now one word. EXECUTE. 1 pts.
package ProjectDeliveryS413 {
    private import EngineElement::*;
    private import EngineWork::*;
    private import EngineVerification::*;
    private import EngineRelationships::*;

    #CharteredBy dependency from recordDecisionMarkerFlagStory to d0193;

    part recordDecisionMarkerFlagStory : Story {
        :>> id = "12bff7c0-7e58-4b15-b7ae-ceb9264c9783";
        :>> title = "Sprint 413: --process-change (1 pts)";
        :>> createdAt = "2026-08-22"; :>> createdBy = "claudeFable5"; :>> kind = WorkKind::code; :>> priority = WorkPriority::p0; :>> owner = "claudeFable5"; :>> estimatedPoints = 1;
    }

    action def DeliveryRunS413 {
        action storyRecordDecisionMarkerFlag;
        verification storyRecordDecisionMarkerFlagDoD : Test { :>> id = "0751c65a-6656-4ba0-b8d1-888cd887d50f"; :>> method = VerificationMethod::test; :>> procedureText = "DELIVERED: dcRecordDecisionMarkerFlag (resolves issue213). keel record decision gains --process-change and --safety-change: the flag emits the #ProspectiveChange/#SafetyChange marker with the standard D0070 governs-comment on the part declaration, so the marker the process-change guard demands is authored BY the recorder instead of remembered by the author - the forgettable hand-edit that refused sprints 395 and 407 at their landing commits. The guard's refusal message now names the flag (srK13 deny-and-provide). The viewer API path passes no marker (unchanged: proposing THROUGH the console never claims process-change governance silently). VERIFIED in a temp repo, both directions: with the flag, the emitted file carries the marked declaration and the D0070 comment; without it, the file is byte-shaped as before with zero marker text."; }
        part storyRecordDecisionMarkerFlagDoDR1 : TestResult { :>> id = "71c699f6-3888-4a01-af0d-007dcccf981f"; :>> outcome = VerdictKind::pass; :>> judgedAgainst = "58f54f0"; :>> judgedAt = "2026-08-22"; :>> judgedBy = "claudeFable5"; }
    }

    verification recordDecisionMarkerFlagRefineGate : Test { :>> id = "ef49b56c-8f93-4edf-b6be-7b3bd8a0a16e"; :>> title = "Sprint 413 refine gate (DoR)"; :>> createdAt = "2026-08-22"; :>> createdBy = "claudeFable5"; :>> method = VerificationMethod::inspect; :>> procedureText = "DoR. Chartered under d0193's friction-family umbrella; resolves the two-occurrence refusal class at the tool (D0054: authoring friction is the #1 risk). 1 point."; }
    part recordDecisionMarkerFlagRefineGateR1 : TestResult { :>> id = "b80b3bd2-cab0-4dd4-8570-04ac4564bff3"; :>> outcome = VerdictKind::pass; :>> judgedAgainst = "58f54f0"; :>> judgedAt = "2026-08-22"; :>> judgedBy = "claudeFable5"; }
    verification recordDecisionMarkerFlagStandupGate : Test { :>> id = "a9c6b60b-60b9-4ef1-adba-d84a55957c6d"; :>> title = "Sprint 413 standup gate"; :>> createdAt = "2026-08-22"; :>> createdBy = "claudeFable5"; :>> method = VerificationMethod::inspect; :>> procedureText = "Approach: marker as an Option through the writer, two CLI flags, the guard message names the remedy; probe both paths in a temp repo before recording. No blockers."; }
    part recordDecisionMarkerFlagStandupGateR1 : TestResult { :>> id = "7868d1bb-2759-4d62-95d7-8c0c0c0d15e8"; :>> outcome = VerdictKind::pass; :>> judgedAgainst = "58f54f0"; :>> judgedAt = "2026-08-22"; :>> judgedBy = "claudeFable5"; }
    verification recordDecisionMarkerFlagImplementGate : Test { :>> id = "8dbad40a-bb5f-4902-9ede-60b686a8d09e"; :>> title = "Sprint 413 implement gate"; :>> createdAt = "2026-08-22"; :>> createdBy = "claudeFable5"; :>> method = VerificationMethod::test; :>> procedureText = "Verified in a temp repo: --process-change emits '#ProspectiveChange part d0001' plus the D0070 governs-comment (grep-counted 1/1); the unflagged path emits a plain declaration with zero marker text (0/1 greps). clippy pedantic+nursery clean; build green."; }
    part recordDecisionMarkerFlagImplementGateR1 : TestResult { :>> id = "6160dd16-5508-41dd-8b8e-54ca8398680a"; :>> outcome = VerdictKind::pass; :>> judgedAgainst = "58f54f0"; :>> judgedAt = "2026-08-22"; :>> judgedBy = "claudeFable5"; }
    verification recordDecisionMarkerFlagReviewGate : Test { :>> id = "6c01c066-1c51-4a63-b4dd-8d22fd0323a9"; :>> title = "Sprint 413 review gate — three passes per D0172"; :>> createdAt = "2026-08-22"; :>> createdBy = "claudeFable5"; :>> method = VerificationMethod::inspect; :>> procedureText = "PASS 1, CLAIMS: both probe greps quoted from the temp-repo run. PASS 2, BOUNDARY: the flag TRUSTS the author's classification - an unflagged decision that in fact governs process change still hits the guard at its landing commit, which is the correct backstop order (the tool removes friction, the guard keeps the lock). PASS 3, OWN DIFF: the serve caller was updated in the same change so the arity break could not strand the viewer path - compile-checked. WHAT A REVIEWER SHOULD ATTACK: the marker rides a format! with conditional indentation - byte-shape verified for both branches in the probe, and the plain branch matches the previous emitter exactly."; }
    part recordDecisionMarkerFlagReviewGateR1 : TestResult { :>> id = "83a3ddf4-692d-4016-840e-d08e3e6f27f9"; :>> outcome = VerdictKind::pass; :>> judgedAgainst = "58f54f0"; :>> judgedAt = "2026-08-22"; :>> judgedBy = "claudeFable5"; }
    verification recordDecisionMarkerFlagCloseOutGate : Test { :>> id = "0f47d784-76d1-4a58-bd1b-bfe4d8159d1b"; :>> title = "Sprint 413 closeOut gate (autonomous, D0049)"; :>> createdAt = "2026-08-22"; :>> createdBy = "claudeFable5"; :>> method = VerificationMethod::inspect; :>> procedureText = "Autonomous closeOut (D0049). DoD flipped on the temp-repo evidence; issue213 resolves; validate + all 45 guards green."; }
    part recordDecisionMarkerFlagCloseOutGateR1 : TestResult { :>> id = "6a3d47f1-7aba-41f3-9e01-b2843d116bf5"; :>> outcome = VerdictKind::pass; :>> judgedAgainst = "58f54f0"; :>> judgedAt = "2026-08-22"; :>> judgedBy = "claudeFable5"; }
    verification recordDecisionMarkerFlagRetroGate : Test { :>> id = "98c6a1ee-eb7c-42d9-a55a-8e95d9e8579e"; :>> title = "Sprint 413 retro gate (autonomous, D0049)"; :>> createdAt = "2026-08-22"; :>> createdBy = "claudeFable5"; :>> method = VerificationMethod::analyze; :>> procedureText = "Autonomous retro (D0049). AVOIDABLE-ISSUE SCAN under rcRecurrence: this sprint IS the recurrence closure for the marker-refusal class - two occurrences, root-fixed at the tool per the two-instance bar. WELL: the deny-and-provide edit to the guard message means the next author who forgets learns the flag from the refusal itself. Estimate 1 pt, delivered 1."; }
    part recordDecisionMarkerFlagRetroGateR1 : TestResult { :>> id = "1f1d32fe-ff2a-4b31-a687-556fdf7f2520"; :>> outcome = VerdictKind::pass; :>> judgedAgainst = "58f54f0"; :>> judgedAt = "2026-08-22"; :>> judgedBy = "claudeFable5"; }
}
