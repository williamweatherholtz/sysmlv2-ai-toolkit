// ProjectDeliveryS370 — Sprint 370: the obligation deck becomes a declared, portable process. A
// signature is not a verdict; copy-paste is not a route. EXECUTE. 5 pts.
package ProjectDeliveryS370 {
    private import EngineElement::*;
    private import EngineWork::*;
    private import EngineVerification::*;
    private import EngineRelationships::*;

    #CharteredBy dependency from portableDeckStory to d0171;

    part portableDeckStory : Story {
        :>> id = "0d8006d0-0814-66d0-9b3e-0000003006d0";
        :>> title = "Sprint 370: the review deck travels — a declared process, Sign not Accept, and no copy route (5 pts)";
        :>> createdAt = "2026-08-20"; :>> createdBy = "claudeOpus5"; :>> kind = WorkKind::code; :>> priority = WorkPriority::p0; :>> owner = "claudeOpus5"; :>> estimatedPoints = 5;
    }

    action def DeliveryRunS370 {
        action storyPortableDeck;
        verification storyPortableDeckDoD : Test { :>> id = "0d8006d1-0814-66d1-9b3e-0000003006d1"; :>> method = VerificationMethod::test; :>> procedureText = "DELIVERED BACKLOG ITEMS: dcDeckIsPortable. Clears issue187 under D0171. Their five named properties: mobile, automatic feedback with NO copy-paste, Claude-hosted artifact, clearly delineates decisions, reusable anywhere keel is used. THREE ALREADY HELD and are stated so the change is not inflated - a 680px fluid column with a device-width viewport, published as a Claude-hosted artifact, and already a LIVE DOC through the `artifact` capability. TWO DID NOT. NOT REUSABLE: obligation-review was a skill deploying NO process, and D0128 makes a process the movable unit, so it could not travel - `.engine/processes/obligation-review.sysml` now declares five steps and the registry purpose names it (D0059). The catalogue goes 19 to 20 with `process-skill` PASS at 20 scanned. COPY WAS STILL A ROUTE: the button sat in every view including writable ones; it is now hidden unless the view genuinely cannot write, where it is the only thing that works. DECISIONS DELINEATED STRUCTURALLY: acceptance cards carry `Sign`, a heavier rail and a `needs your signature` ribbon. VERIFIED FROM THE EMITTED HTML, not from reading the generator: 45 cards, 4 with `Sign` on 4 acceptance cards, 41 with `Accept`. Published live at 1b5ba2eb. validate 402 clean; check-engine clean; 38 guards ALL PASS."; }
        part storyPortableDeckDoDR1 : TestResult { :>> id = "0d8006d2-0814-66d2-9b3e-0000003006d2"; :>> outcome = VerdictKind::pass; :>> judgedAgainst = "650f04e"; :>> judgedAt = "2026-08-20"; :>> judgedBy = "claudeOpus5"; }
    }

    verification pdRefineGate : Test { :>> id = "0d8006d3-0814-66d3-9b3e-0000003006d3"; :>> title = "Sprint 370 refine gate (DoR)"; :>> createdAt = "2026-08-20"; :>> createdBy = "claudeOpus5"; :>> method = VerificationMethod::inspect; :>> procedureText = "DoR. FIRST ACTION WAS TO READ WHAT ALREADY EXISTED rather than to build, and that is what kept the sprint at 5 points: three of their five properties already held. Claiming credit for mobile-first layout, artifact hosting and the live-doc capability would have made the sprint look bigger and the record less useful. The two real gaps were structural, not cosmetic - a skill that deploys no process cannot be adopted by anything, and a copy button in a writable view is a taught habit. estimatedPoints=5."; }
    part pdRefineGateR1 : TestResult { :>> id = "0d8006d4-0814-66d4-9b3e-0000003006d4"; :>> outcome = VerdictKind::pass; :>> judgedAgainst = "650f04e"; :>> judgedAt = "2026-08-20"; :>> judgedBy = "claudeOpus5"; }

    verification pdStandupGate : Test { :>> id = "0d8006d5-0814-66d5-9b3e-0000003006d5"; :>> title = "Sprint 370 standup gate"; :>> createdAt = "2026-08-20"; :>> createdBy = "claudeOpus5"; :>> method = VerificationMethod::inspect; :>> procedureText = "Approach: verify every claim from the EMITTED HTML rather than from the generator source. Counting `Sign` and `Accept` occurrences and `data-cls=acceptance` cards in the output settles what a reader will actually see; reading the python only settles what I intended. This is the same discipline the hardening series arrived at after five hand probes produced wrong numbers. No blockers."; }
    part pdStandupGateR1 : TestResult { :>> id = "0d8006d6-0814-66d6-9b3e-0000003006d6"; :>> outcome = VerdictKind::pass; :>> judgedAgainst = "650f04e"; :>> judgedAt = "2026-08-20"; :>> judgedBy = "claudeOpus5"; }

    verification pdImplementGate : Test { :>> id = "0d8006d7-0814-66d7-9b3e-0000003006d7"; :>> title = "Sprint 370 implement gate"; :>> createdAt = "2026-08-20"; :>> createdBy = "claudeOpus5"; :>> method = VerificationMethod::test; :>> procedureText = "THE SIGNATURE DISTINCTION IS NOT AESTHETICS AND THE PROCESS FILE SAYS WHY. Every non-acceptance class asks for a judgment an AI could in principle have formed and is deferring to a human. An acceptance asks for something an AI may NEVER supply: section 4 says a `method=confirmation` result records a human's word and cannot be inferred from an instruction, from the work being done, or from my own judgment. Rendering both with the same green `Accept` button on the same card shape is the confusion that produced issue144 - where I turned an instruction into a recorded attestation by mechanical substitution - and the deck is where that confusion is cheapest to make, because the human's tap is the only evidence that ever existed. TWO SELF-INFLICTED DEFECTS IN THIS SPRINT, both from authoring through a shell. `action orRecord = ProcessStep` instead of `:`, caught by the edit gate at the point of the edit. And backticked command names in a `record issue` argument were EXECUTED as command substitution, silently DELETING their words from the recorded description - it read `the movable unit and  operates on processes`, with the subject gone. Repaired by hand and the damage annotated inside the issue itself, because a description that reads as a grammatical slip hides that content was lost. FOURTH TIME THIS SESSION the shell has reinterpreted content I was authoring, against a remedy recorded three times."; }
    part pdImplementGateR1 : TestResult { :>> id = "0d8006d8-0814-66d8-9b3e-0000003006d8"; :>> outcome = VerdictKind::pass; :>> judgedAgainst = "650f04e"; :>> judgedAt = "2026-08-20"; :>> judgedBy = "claudeOpus5"; }

    verification pdReviewGate : Test { :>> id = "0d8006d9-0814-66d9-9b3e-0000003006d9"; :>> title = "Sprint 370 review gate"; :>> createdAt = "2026-08-20"; :>> createdBy = "claudeOpus5"; :>> method = VerificationMethod::inspect; :>> procedureText = "Reviewed. WHAT I DID NOT DELETE: the copy fallback. A read-only viewer has no other way to return anything, so deleting it would make the deck useless in exactly the case where it is the only thing that works. Hiding it until then is the whole fix - the reader who needs it sees it, and the reader who does not is never taught the habit. WHAT I DELIBERATELY DID NOT BUILD: automatic publication from the turn-boundary hook. `keel hook stop` already advises when obligations exist and no console answers (issue150), and wiring it to publish an artifact unasked is a different kind of change - a hook that creates hosted pages without being asked is not a gate, it is an actor. That is a separate proposal and D0171's consequences say so rather than leaving it as an unmentioned gap. THE HONEST LIMIT: the deck reports what is waiting, and nothing forces anyone to look at it. That is not a defect this sprint can fix."; }
    part pdReviewGateR1 : TestResult { :>> id = "0d8006da-0814-66da-9b3e-0000003006da"; :>> outcome = VerdictKind::pass; :>> judgedAgainst = "650f04e"; :>> judgedAt = "2026-08-20"; :>> judgedBy = "claudeOpus5"; }

    verification pdCloseOutGate : Test { :>> id = "0d8006db-0814-66db-9b3e-0000003006db"; :>> title = "Sprint 370 closeOut gate (autonomous, D0049)"; :>> createdAt = "2026-08-20"; :>> createdBy = "claudeOpus5"; :>> method = VerificationMethod::inspect; :>> procedureText = "Autonomous closeOut (D0049). issue187 cleared, D0171 PROPOSED and unsigned. 20 declared processes, all with deploying skills. The deck is published live and its 4 acceptance cards - D0167, D0168, D0169, D0170 - are the very signatures D0171 itself is waiting on, which is the process working on its own author. validate 402 clean; check-engine clean; 38 guards ALL PASS."; }
    part pdCloseOutGateR1 : TestResult { :>> id = "0d8006dc-0814-66dc-9b3e-0000003006dc"; :>> outcome = VerdictKind::pass; :>> judgedAgainst = "650f04e"; :>> judgedAt = "2026-08-20"; :>> judgedBy = "claudeOpus5"; }

    verification pdRetroGate : Test { :>> id = "0d8006dd-0814-66dd-9b3e-0000003006dd"; :>> title = "Sprint 370 retro gate (autonomous, D0049)"; :>> createdAt = "2026-08-20"; :>> createdBy = "claudeOpus5"; :>> method = VerificationMethod::analyze; :>> procedureText = "Autonomous retro (D0049) under D0131's retroTrack. WELL: (1) three of their five properties were found already satisfied and reported as such, keeping the sprint small and the record accurate; (2) every claim was verified from the EMITTED HTML - 45 cards, 4 Sign, 41 Accept - not from the generator source; (3) the copy fallback was hidden rather than deleted, because a read-only viewer needs it; (4) automatic publication from the stop hook was NOT built, and the reason is recorded in D0171 rather than left as an unmentioned gap - a hook that creates hosted pages unasked is an actor, not a gate; (5) the process file states WHY the signature distinction exists, so a downstream adopter inherits the reasoning and not just the CSS. AVOIDABLE-ISSUE: backticked command names in a shell argument were executed as command substitution and their words silently deleted from a recorded description, leaving a sentence with no subject. Fourth time this session that authoring through a shell let the shell reinterpret the content, against a remedy - the Write tool - recorded three times already. What makes THIS instance worse than the earlier ones is that the damage read as a grammatical slip rather than as missing content, so it would have survived a proofread; I only caught it because the substituted command printed its usage to my terminal. SECOND AVOIDABLE-ISSUE: `action orRecord = ProcessStep` instead of `:`, caught by the edit gate at the point of the edit - which is the gate working exactly as designed. Estimate 5 pts, delivered."; }
    part pdRetroGateR1 : TestResult { :>> id = "0d8006de-0814-66de-9b3e-0000003006de"; :>> outcome = VerdictKind::pass; :>> judgedAgainst = "650f04e"; :>> judgedAt = "2026-08-20"; :>> judgedBy = "claudeOpus5"; }
}
