// ProjectDeliveryS327 — Sprint 327: critique backfill pass 4 — the LAST critiquable Needs. Every Need
// not authored by claudeOpus5 is now critique-covered. EXECUTE. 3 pts.
package ProjectDeliveryS327 {
    private import EngineElement::*;
    private import EngineWork::*;
    private import EngineVerification::*;
    private import EngineRelationships::*;

    #CharteredBy dependency from critPass4Story to d0080;

    part critPass4Story : Story {
        :>> id = "0d800420-0814-6420-9b3e-000000300420";
        :>> title = "Sprint 327: critique pass 4 — the last 5 critiquable Needs, 10 fail / 5 pass (3 pts)";
        :>> createdAt = "2026-08-17"; :>> createdBy = "claudeOpus5"; :>> kind = WorkKind::modeling; :>> priority = WorkPriority::p0; :>> owner = "claudeOpus5"; :>> estimatedPoints = 3;
    }

    action def DeliveryRunS327 {
        action storyCritPass4;
        verification storyCritPass4DoD : Test { :>> id = "0d800421-0814-6421-9b3e-000000300421"; :>> method = VerificationMethod::analyze; :>> procedureText = "Pass 4: nViewerInProgramEdit, nViewerIterativeCritique, nViewerQueryExpansion, nViewerSeparation, nViewerViewpointForm. 10 fail, 5 pass. MILESTONE, read back from the computed view: Need coverage 18 -> 23 of 39, and `next_targets Need` now reports 0 critiquable with 16 blocked — every Need not authored by claudeOpus5 is critique-covered, and 39 minus 23 is exactly the blocked set. TWO FINDINGS NAME THE SAME UNNOTICED COLLISION: nViewerInProgramEdit wants edit-then-critique on one surface, and nViewerIterativeCritique wants an AI to critique each element along an axis — both run into critique independence, which neither mentions. An edit does not transfer authorship, so a user critiquing what they just edited self-critiques and the coverage computation discards it; and MEASURED, 87 of 154 uncovered elements are claudeOpus5-authored, so an AI iterating an axis would silently fail to count for 56 percent of them. A THIRD FINDING IS A CLAUSE THAT IS TESTABLE AND FALSE: nViewerSeparation says the write API and guards 'remain the ONLY write path', which CLAUDE.md itself contradicts, so a faithful verification must fail permanently on correct behaviour — worse than an untestable clause, because honest verification becomes impossible. validate 355 clean; 34 guards ALL PASS."; }
        part storyCritPass4DoDR1 : TestResult { :>> id = "0d800422-0814-6422-9b3e-000000300422"; :>> outcome = VerdictKind::pass; :>> judgedAgainst = "13f825e"; :>> judgedAt = "2026-08-17"; :>> judgedBy = "claudeOpus5"; }
    }

    verification c4RefineGate : Test { :>> id = "0d800423-0814-6423-9b3e-000000300423"; :>> title = "Sprint 327 refine gate (DoR)"; :>> createdAt = "2026-08-17"; :>> createdBy = "claudeOpus5"; :>> method = VerificationMethod::inspect; :>> procedureText = "DoR. The last five critiquable Needs, all keel-viewer. Two factual claims were checked before writing: that `keel render` still accepts exactly three modes (it does — main.rs and the view.rs dispatch), and that the architecture question N-6 presents as open has been answered (D0114 chose a shape and D0152 superseded it, #Supersede edge at 0152 line 24). Both checks changed what the critiques say. estimatedPoints=3."; }
    part c4RefineGateR1 : TestResult { :>> id = "0d800424-0814-6424-9b3e-000000300424"; :>> outcome = VerdictKind::pass; :>> judgedAgainst = "13f825e"; :>> judgedAt = "2026-08-17"; :>> judgedBy = "claudeOpus5"; }

    verification c4StandupGate : Test { :>> id = "0d800425-0814-6425-9b3e-000000300425"; :>> title = "Sprint 327 standup gate"; :>> createdAt = "2026-08-17"; :>> createdBy = "claudeOpus5"; :>> method = VerificationMethod::inspect; :>> procedureText = "Approach: unchanged from pass 3 — verify every factual claim against the codebase or the model before writing it, batch as JSON through the writer that refuses unquotable text, read coverage back from the computed view rather than counting what I wrote. No blockers."; }
    part c4StandupGateR1 : TestResult { :>> id = "0d800426-0814-6426-9b3e-000000300426"; :>> outcome = VerdictKind::pass; :>> judgedAgainst = "13f825e"; :>> judgedAt = "2026-08-17"; :>> judgedBy = "claudeOpus5"; }

    verification c4ImplementGate : Test { :>> id = "0d800427-0814-6427-9b3e-000000300427"; :>> title = "Sprint 327 implement gate"; :>> createdAt = "2026-08-17"; :>> createdBy = "claudeOpus5"; :>> method = VerificationMethod::analyze; :>> procedureText = "THE MOST VALUABLE FINDING OF THE WHOLE NEEDS BACKFILL IS A CROSS-NEED COLLISION NO SINGLE NEED COULD SHOW: critique INDEPENDENCE constrains two accepted must-priority Needs that never mention it. nViewerInProgramEdit's edit-then-critique loop self-critiques whenever the editor is the author, because an edit does not change createdBy; nViewerIterativeCritique's axis iteration produces findings that do not count for 87 of 154 elements. Neither Need is wrong on its own terms, and a reader examining either alone would not see it — which is the argument for critiquing a corpus rather than an element, and for doing it with the measurement in hand. A SECOND CROSS-NEED FACT: three Needs (N-1's form vocabulary, N-5's bound, N-6's shape) defer their own acceptance criteria to a handoff document or to a later Need, and one of those later Needs (N-18) is itself still unaccepted — so an accepted Need's only elaboration is unapproved, and decomposing it today means inventing the criterion or waiting."; }
    part c4ImplementGateR1 : TestResult { :>> id = "0d800428-0814-6428-9b3e-000000300428"; :>> outcome = VerdictKind::pass; :>> judgedAgainst = "13f825e"; :>> judgedAt = "2026-08-17"; :>> judgedBy = "claudeOpus5"; }

    verification c4ReviewGate : Test { :>> id = "0d800429-0814-6429-9b3e-000000300429"; :>> title = "Sprint 327 review gate"; :>> createdAt = "2026-08-17"; :>> createdBy = "claudeOpus5"; :>> method = VerificationMethod::inspect; :>> procedureText = "Reviewed across all four passes: 20 Needs, 60 lenses, 45 fail and 15 pass. THE PASSES ARE THE PART I RE-EXAMINED, because a critic's passes are where laziness hides and they carry no visible cost. Of the 15, four pass on a NEGATIVE clause that is falsifiable and currently FAILS in the implementation (nViewerViewpointForm's three fixed modes, nViewerExplorableGraph's incremental loading, nViewerInProgramEdit's no-second-store, nServeReuseModel's set equivalence) — those are the most useful verifications in the corpus, because each measures a real gap rather than asserting one. Two pass because a check CONTRADICTED my expectation (pass 3). The rest pass on properties that are genuinely well-formed. None passes because I ran out of things to say. WHAT I AM NOT CLAIMING: that these 20 Needs are now good. They are EXAMINED — a judgment has been formed and recorded against each, with its reasoning — which is the EXAMINED half of `keel verification` and says nothing about whether the owner agrees or acts."; }
    part c4ReviewGateR1 : TestResult { :>> id = "0d80042a-0814-642a-9b3e-00000030042a"; :>> outcome = VerdictKind::pass; :>> judgedAgainst = "13f825e"; :>> judgedAt = "2026-08-17"; :>> judgedBy = "claudeOpus5"; }

    verification c4CloseOutGate : Test { :>> id = "0d80042b-0814-642b-9b3e-00000030042b"; :>> title = "Sprint 327 closeOut gate (autonomous, D0049)"; :>> createdAt = "2026-08-17"; :>> createdBy = "claudeOpus5"; :>> method = VerificationMethod::inspect; :>> procedureText = "Autonomous closeOut (D0049). NEEDS ARE EXHAUSTED for this critic: 0 critiquable, 16 blocked, Need coverage 23 of 39. Remaining critiquable elsewhere: 25 SystemRequirements and 22 Decisions. Zero open issues; ready frontier empty; D0159 queued for acceptance. validate 355 clean; check-engine clean; 34 guards ALL PASS; no code changed in any of the four passes."; }
    part c4CloseOutGateR1 : TestResult { :>> id = "0d80042c-0814-642c-9b3e-00000030042c"; :>> outcome = VerdictKind::pass; :>> judgedAgainst = "13f825e"; :>> judgedAt = "2026-08-17"; :>> judgedBy = "claudeOpus5"; }

    verification c4RetroGate : Test { :>> id = "0d80042d-0814-642d-9b3e-00000030042d"; :>> title = "Sprint 327 retro gate (autonomous, D0049)"; :>> createdAt = "2026-08-17"; :>> createdBy = "claudeOpus5"; :>> method = VerificationMethod::analyze; :>> procedureText = "Autonomous retro (D0049) under D0131's retroTrack, covering the four-pass Needs backfill as a unit. WELL: (1) measuring the independence split first meant zero wasted critiques across 60 lenses; (2) checking factual claims before writing them caught two that were false, and the checks are recorded inside the passes so a reader inherits the correction; (3) the cross-Need findings — the independence collision and the deferred-criteria chain — could only surface by working a corpus with the measurement in hand, which is the case for doing this as a sequence of passes rather than element by element on demand. AVOIDABLE-ISSUE across the four passes: one tool defect (the helper's two-bug author lookup, pass 2) and one shell-quoting failure (pass 1), both already-recorded classes, both caught before they reached the model. WHAT I WOULD DO DIFFERENTLY: pass 1 wrote 14 fails of 15 and its rigor self-check came only in the review gate; the later passes checked claims BEFORE writing, which is both cheaper and more honest. The ordering of that check is the lesson, not its existence. Estimate 3 pts, delivered — 12 pts across the four passes against 12 estimated."; }
    part c4RetroGateR1 : TestResult { :>> id = "0d80042e-0814-642e-9b3e-00000030042e"; :>> outcome = VerdictKind::pass; :>> judgedAgainst = "13f825e"; :>> judgedAt = "2026-08-17"; :>> judgedBy = "claudeOpus5"; }
}
