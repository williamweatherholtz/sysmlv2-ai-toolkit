// ProjectDeliveryS571 — Sprint 571: D0201 option B delivered - a tap is bound to the paired device that made it, and a chat acceptance must read back the decision it accepts. EXECUTE. 5 pts.
package ProjectDeliveryS571 {
    private import EngineElement::*;
    private import EngineWork::*;
    private import EngineVerification::*;
    private import EngineRelationships::*;

    #CharteredBy dependency from deviceBoundTapsStory to d0334;

    part deviceBoundTapsStory : Story {
        :>> id = "c807d143-71c6-4d54-9b6f-722364057bef";
        :>> title = "Sprint 571: D0201 option B delivered - a tap is bound to the paired device that made it, and a chat acceptance must read back the decision it accepts (5 pts)";
        :>> createdAt = "2026-09-06"; :>> createdBy = "claudeOpus5"; :>> kind = WorkKind::code; :>> priority = WorkPriority::p0; :>> owner = "claudeOpus5"; :>> estimatedPoints = 5;
    }

    action def DeliveryRunS571 {
        action storyDeviceBoundTaps;
        verification storyDeviceBoundTapsDoD : Test { :>> id = "70f2aaa3-9b03-48e5-ad2c-e20ff67403d6"; :>> method = VerificationMethod::test; :>> procedureText = "DELIVERED BACKLOG ITEMS: dcAttestationBindsToDevice (D0334 device binding, D0335 read-back; the human's choice of 2026-08-23 that no work had carried). DONE: device.rs - HMAC-SHA256 on sha2 pinned to RFC 4231, a machine-local paired-device store, constant-time verify; keel serve prints a pairing code to its terminal and serves POST /api/device/enroll; every human tap (accept, reject, gate result, disposition, test verdict, sitting review) requires device_id + hmac over kind|target|date|judge|note and is refused 401 with nothing written otherwise; a recorded tap carries the device tag; console.html and the deck sign with WebCrypto and prompt to pair on the first tap; keel accept under delegation refuses a quote that does not name the decision (id, option letter, or three words of title/decision text). SCOPE stated in both Decisions: a device, not a person; the terminal's reader is the trust root."; }
        // RAN: same suite receipt: 533/0 exit 0; deck e2e 20 ok
        part storyDeviceBoundTapsDoDR1 : TestResult { :>> id = "e57bc2eb-4edd-4638-bedc-1b7ae143de46"; :>> outcome = VerdictKind::pass; :>> judgedAgainst = "c850affdf3632c8cd59241064900f313de83ae38"; :>> judgedAt = "2026-09-05"; :>> judgedBy = "claudeOpus5"; }
    }

    verification deviceBoundTapsRefineGate : Test { :>> id = "433a0e6c-f751-441d-adec-52a75b5515b9"; :>> title = "Sprint 571 refine gate (DoR)"; :>> createdAt = "2026-09-06"; :>> createdBy = "claudeOpus5"; :>> method = VerificationMethod::inspect; :>> procedureText = "READY: D0201 B named the mechanism and the DoD named both directions. The design question was what a localhost server can bind to at all - a key the browser holds that the server learned only through the human typing the terminal's code - and the scope statement that follows from it, which the DoD demanded be said rather than implied."; }
    verification deviceBoundTapsStandupGate : Test { :>> id = "0683abeb-6d7e-42c9-a140-a907e644a1d5"; :>> title = "Sprint 571 standup gate"; :>> createdAt = "2026-09-06"; :>> createdBy = "claudeOpus5"; :>> method = VerificationMethod::inspect; :>> procedureText = "TWO DEFECTS THE LIVE TESTS CAUGHT: dropping the child's stderr pipe in the serve test killed the server on its next eprintln (a test-harness fact worth knowing), and the deck e2e tool's 30-second client timeout could not survive GET /deck's 42-second governance walk on this tree (D0265) - raised to 180 with the reason in the tool. The read-back rule bit the D0329 test's third note ('yes, corrected as well' names nothing) until the note read back the decision text."; }
    verification deviceBoundTapsImplementGate : Test { :>> id = "36018e1b-c0d7-44c1-a995-b834c345e4b1"; :>> title = "Sprint 571 implement gate"; :>> createdAt = "2026-09-06"; :>> createdBy = "claudeOpus5"; :>> method = VerificationMethod::test; :>> procedureText = "RAN: cargo test --lib device 3 passed (RFC vector; absent/unknown/wrong refused, valid verifies, altered text refused; store round-trip); cargo test --test device_bound_taps 1 passed on a live serve (five directions); --lib read_back 3 passed; acceptance_binds_to_text, tty_accept_cites_the_gesture, disguised_fork tests pass through the changed accept path; python .engine/tools/test_deck_e2e.py: 20 ok, exit 0, including an unsigned tap refused and an AI-signed sitting tap refused; clippy -D warnings clean; the full suite in the background to completion (receipt on the DoD result)."; }
    verification deviceBoundTapsReviewGate : Test { :>> id = "9b2ca856-eac4-4d4e-be1f-6301ac362d3f"; :>> title = "Sprint 571 review gate — three passes per D0172"; :>> createdAt = "2026-09-06"; :>> createdBy = "claudeOpus5"; :>> method = VerificationMethod::inspect; :>> procedureText = "THREE PASSES. (1) WHAT IS PROVEN: that a tap came from the paired browser - both Decisions say it is not a person, and the residual (the terminal's reader can pair) is written down. (2) IS ANYTHING WEAKENED: no path gained; five gained a requirement; the AI-refusal on sitting still fires first. (3) IS THE HUMAN BURDENED: one pairing prompt per browser, then nothing; a plain answer that names the decision - which theirs already do - records."; }
    verification deviceBoundTapsCloseOutGate : Test { :>> id = "8724d5e4-487f-4b1c-8dce-4522212ed8bd"; :>> title = "Sprint 571 closeOut gate (autonomous, D0049)"; :>> createdAt = "2026-09-06"; :>> createdBy = "claudeOpus5"; :>> method = VerificationMethod::inspect; :>> procedureText = "CLOSED. D0334 and D0335 accepted under standing consent; dcAttestationBindsToDevice done; D0201 B carried in full."; }
    verification deviceBoundTapsRetroGate : Test { :>> id = "5b395b0e-1a42-4d59-bd49-529ad15c5db7"; :>> title = "Sprint 571 retro gate (autonomous, D0049)"; :>> createdAt = "2026-09-06"; :>> createdBy = "claudeOpus5"; :>> method = VerificationMethod::analyze; :>> procedureText = "no new item - already tracked: the residual that the serving terminal's reader is the trust root is the standing dcScheduledCurrency / console-hosting question and D0334 states it; the deck's inbox transport (Smartsheet rows Claude records) is out of this binding's scope by construction and stays the artifact-frame path. The lesson: a localhost control must say what it binds to, and the answer is always the channel the secret travelled through."; }
}
