// ProjectDeliveryS280 — Sprint 280: the Model ingests `.engine/workflows`; the flow edges emitted in
// sprint 270 finally land (issue104). First item run through the new dorConsumer gate. EXECUTE. 2 pts.
package ProjectDeliveryS280 {
    private import EngineElement::*;
    private import EngineWork::*;
    private import EngineVerification::*;
    private import EngineRelationships::*;

    #CharteredBy dependency from ingestWorkflowsStory to d0144;

    part ingestWorkflowsStory : Story {
        :>> id = "0d80012c-0814-612c-9b3e-00000030012c";
        :>> title = "Sprint 280: the Model ingests .engine/workflows; flow edges land (2 pts)";
        :>> createdAt = "2026-08-14"; :>> createdBy = "claudeOpus5"; :>> kind = WorkKind::code; :>> priority = WorkPriority::p0; :>> owner = "claudeOpus5"; :>> estimatedPoints = 2;
    }

    action def DeliveryRunS280 {
        action storyIngestWorkflows;
        verification storyIngestWorkflowsDoD : Test { :>> id = "0d80012d-0814-612d-9b3e-00000030012d"; :>> method = VerificationMethod::test; :>> procedureText = "Resolves issue104. `Model::build` ingested `.tracking` plus five `.engine` subdirectories and NOT `.engine/workflows`, so the six workflow definitions contributed nothing to any view, trace, diagram or guard — and they are the ONE place this repo models behaviour in base SysML v2, with typed in/out parameters, `first..then` successions and `flow`. The flow edges emitted in sprint 270 had nowhere to land. FIRST ITEM RUN THROUGH THE NEW dorConsumer GATE (D0144), and the gate named the right risk: adding a directory changes what EVERY guard evaluates at once, so guard output was captured BEFORE and diffed AFTER rather than reasoned about. RESULT: no guard changed verdict — blast radius zero — and 18 flow edges now land, matching the 18 flow statements exactly. A workflow action (`dataArch`) is reachable in the model where it was previously absent. clippy clean; 161 tests; validate + all 28 guards + check-engine green."; }
        part storyIngestWorkflowsDoDR1 : TestResult { :>> id = "0d80012e-0814-612e-9b3e-00000030012e"; :>> outcome = VerdictKind::pass; :>> judgedAgainst = "f7f7296"; :>> judgedAt = "2026-08-14"; :>> judgedBy = "claudeOpus5"; }
    }

    verification iwRefineGate : Test { :>> id = "0d80012f-0814-612f-9b3e-00000030012f"; :>> title = "Sprint 280 refine gate (DoR)"; :>> createdAt = "2026-08-14"; :>> createdBy = "claudeOpus5"; :>> method = VerificationMethod::inspect; :>> procedureText = "DoR, including the new dorConsumer step. CONSUMER CHECK: the consumers of a new Model source directory are every guard and view that reads the Model, which is most of them — so the question is not 'can they read it' but 'what do they now SEE'. That reframing is what produced the before/after guard diff as the verification method rather than a spot check. estimatedPoints=2. DoR met."; }
    part iwRefineGateR1 : TestResult { :>> id = "0d800130-0814-6130-9b3e-000000300130"; :>> outcome = VerdictKind::pass; :>> judgedAgainst = "f7f7296"; :>> judgedAt = "2026-08-14"; :>> judgedBy = "claudeOpus5"; }

    verification iwStandupGate : Test { :>> id = "0d800131-0814-6131-9b3e-000000300131"; :>> title = "Sprint 280 standup gate"; :>> createdAt = "2026-08-14"; :>> createdBy = "claudeOpus5"; :>> method = VerificationMethod::inspect; :>> procedureText = "Approach: capture per-guard verdicts before touching anything, make the one-line change, diff. If any guard had newly failed, each delta would need an individual verdict — a real gap to fix or a scope error to exclude — and never a wholesale grandfather, which would hide exactly the traceability the ingestion exists to reveal. No blockers."; }
    part iwStandupGateR1 : TestResult { :>> id = "0d800132-0814-6132-9b3e-000000300132"; :>> outcome = VerdictKind::pass; :>> judgedAgainst = "f7f7296"; :>> judgedAt = "2026-08-14"; :>> judgedBy = "claudeOpus5"; }

    verification iwImplementGate : Test { :>> id = "0d800133-0814-6133-9b3e-000000300133"; :>> title = "Sprint 280 implement gate"; :>> createdAt = "2026-08-14"; :>> createdBy = "claudeOpus5"; :>> method = VerificationMethod::test; :>> procedureText = "The change is one line and the verification is the work. That asymmetry is the point of dorConsumer: the risk in adding a Model source is never the edit, it is that thirty consumers silently start seeing content they were written without. Zero deltas is a RESULT rather than an absence of one — it means the workflow content introduces no new guard subjects, which is what makes the ingestion safe to keep."; }
    part iwImplementGateR1 : TestResult { :>> id = "0d800134-0814-6134-9b3e-000000300134"; :>> outcome = VerdictKind::pass; :>> judgedAgainst = "f7f7296"; :>> judgedAt = "2026-08-14"; :>> judgedBy = "claudeOpus5"; }

    verification iwReviewGate : Test { :>> id = "0d800135-0814-6135-9b3e-000000300135"; :>> title = "Sprint 280 review gate"; :>> createdAt = "2026-08-14"; :>> createdBy = "claudeOpus5"; :>> method = VerificationMethod::inspect; :>> procedureText = "Reviewed. This closes the loop opened in sprint 270: the flow emission was written correct-but-unexercised and RECORDED as such rather than deleted or claimed to work, and it now functions with no change to the emitting code. Recording an unexercised producer honestly is what made this a one-line sprint instead of a rediscovery."; }
    part iwReviewGateR1 : TestResult { :>> id = "0d800136-0814-6136-9b3e-000000300136"; :>> outcome = VerdictKind::pass; :>> judgedAgainst = "f7f7296"; :>> judgedAt = "2026-08-14"; :>> judgedBy = "claudeOpus5"; }

    verification iwCloseOutGate : Test { :>> id = "0d800137-0814-6137-9b3e-000000300137"; :>> title = "Sprint 280 closeOut gate (autonomous, D0049)"; :>> createdAt = "2026-08-14"; :>> createdBy = "claudeOpus5"; :>> method = VerificationMethod::inspect; :>> procedureText = "Autonomous closeOut (D0049). dcModelIngestWorkflows carries a passing DoD TestResult; issue104 resolves. 18 flow edges land; workflow actions reachable; no guard verdict changed. clippy clean; 161 tests; validate + all 28 guards + check-engine green. No gate bypassed."; }
    part iwCloseOutGateR1 : TestResult { :>> id = "0d800138-0814-6138-9b3e-000000300138"; :>> outcome = VerdictKind::pass; :>> judgedAgainst = "f7f7296"; :>> judgedAt = "2026-08-14"; :>> judgedBy = "claudeOpus5"; }

    verification iwRetroGate : Test { :>> id = "0d800139-0814-6139-9b3e-000000300139"; :>> title = "Sprint 280 retro gate (autonomous, D0049)"; :>> createdAt = "2026-08-14"; :>> createdBy = "claudeOpus5"; :>> method = VerificationMethod::analyze; :>> procedureText = "Autonomous retro (D0049) under D0131's retroTrack. WELL: (1) the new dorConsumer gate ran for the first time and CHANGED the verification method — reframing 'can the consumer read it' as 'what do the consumers now SEE' produced a before/after guard diff instead of a spot check, which is a better test than I would otherwise have chosen; (2) the blast radius was measured rather than assumed, and zero deltas is a positive result meaning the workflow content adds no new guard subjects; (3) sprint 270's decision to record the flow emission as correct-but-unexercised is what made this a one-line change. AVOIDABLE-ISSUE 1: I combined a python heredoc with a `cat > file` heredoc in one shell call and lost the call to a parse error — the THIRD instance, and sprint 273's retro recorded the exact remedy ('write the file with the Write tool rather than a heredoc inside a compound command'). NO NEW ITEM, reason stated: issue094 tracks the class and dcShellAdaptationGate is its declared resolver, still unbuilt; what this instance adds is that a recorded remedy I authored myself did not change my behaviour twice running, which is the strongest available argument for that item being a GATE rather than a note — it is now the concrete evidence for building it. Estimate 2 pts, delivered."; }
    part iwRetroGateR1 : TestResult { :>> id = "0d80013a-0814-613a-9b3e-00000030013a"; :>> outcome = VerdictKind::pass; :>> judgedAgainst = "f7f7296"; :>> judgedAt = "2026-08-14"; :>> judgedBy = "claudeOpus5"; }
}
