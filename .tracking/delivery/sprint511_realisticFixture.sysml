// ProjectDeliveryS511 — Sprint 511: the fixture stops being a fresh scaffold, and finds a defect on
// its first run. EXECUTE. 3 pts.
package ProjectDeliveryS511 {
    private import EngineElement::*;
    private import EngineWork::*;
    private import EngineVerification::*;
    private import EngineRelationships::*;

    #CharteredBy dependency from realisticFixtureStory to d0275;

    part realisticFixtureStory : Story {
        :>> id = "2c8f5b13-6e04-4a79-b3d1-58e07c4629fa";
        :>> title = "Sprint 511: a migration fixture that looks like a project people have used (3 pts)";
        :>> createdAt = "2026-09-01"; :>> createdBy = "claudeOpus5"; :>> kind = WorkKind::code; :>> priority = WorkPriority::p0; :>> owner = "claudeOpus5"; :>> estimatedPoints = 3;
    }

    action def DeliveryRunS511 {
        action storyRealisticFixture;
        verification storyRealisticFixtureDoD : Test { :>> id = "3d906c24-7f15-4b8a-c4e2-69f18d5730ab"; :>> method = VerificationMethod::test; :>> procedureText = "DELIVERED BACKLOG ITEMS: dcMigrationFixtureIsRealistic (resolves issue328, found by the fixture itself) and dcCountAssertionsParseTheNumber (resolves issue329, found by this sprint's own suite run going red). Step 3 of 5 in the D0275 plan. F9 already proved a FRESH SCAFFOLD migrates - and a fresh scaffold is the easy case, which is how seven defects got past it. A real project differs in four ways, each of which produced one of those defects: it customised an engine-shipped file, it authored its own skill naming an engine command, it holds an untracked obligation record while behind its pin, and it has its own CI workflow. DONE: cases 1-3. Case 4 is deliberately absent - issue326 and issue327 are still OPEN, so a test for it would either assert the defect (locking it in) or be ignored (a test that does not run is a claim, D0253); it lands with the fix in step 5. VERIFY: a lived-in project migrates, the resync NAMES what it wrote, the project's own skill survives untouched and the tree gates green, and issue324's escape holds on a realistic project rather than only a bare one."; }
        // RAN: migration_fixture_is_realistic 3/3; the fixture found issue328 on its first run; ARMED by emptying report_written, which makes case 1 fail
        part storyRealisticFixtureDoDR1 : TestResult { :>> id = "4e017d35-8026-4c9b-d5f3-70029e6841bc"; :>> outcome = VerdictKind::pass; :>> judgedAgainst = "6c21669"; :>> judgedAt = "2026-09-01"; :>> judgedBy = "claudeOpus5"; }
    }

    verification realisticFixtureRefineGate : Test { :>> id = "5f128e46-9137-4dac-e604-81138f7952cd"; :>> title = "Sprint 511 refine gate (DoR)"; :>> createdAt = "2026-09-01"; :>> createdBy = "claudeOpus5"; :>> method = VerificationMethod::inspect; :>> procedureText = "READY on a counted claim rather than a feeling: seven defects in the migration path, NONE found by a test, four with no test at all. The four fixture properties were not invented - each is derived from a specific defect in that list, which is why the fixture had a real chance of finding something rather than confirming what was already known."; }
    verification realisticFixtureStandupGate : Test { :>> id = "60239f57-a248-4ebd-f715-9224a0863ade"; :>> title = "Sprint 511 standup gate"; :>> createdAt = "2026-09-01"; :>> createdBy = "claudeOpus5"; :>> method = VerificationMethod::inspect; :>> procedureText = "ONE PROPERTY HELD BACK ON PURPOSE. Case 4, the project's own CI, is not in this suite. issue326 and issue327 are open, so the only honest ways to write it today are to assert the CURRENT behaviour - which would LOCK IN the defect and have to be inverted later - or to mark it ignored, and a test that does not run is a claim (D0253) in a suite whose whole argument is that claims are what got us here. It lands with the fix. Saying which property is missing and why is the point; a fixture called realistic that quietly covers three of four would be the same over-claim in smaller print."; }
    verification realisticFixtureImplementGate : Test { :>> id = "71340a68-b359-4fce-0826-a3350b174bef"; :>> title = "Sprint 511 implement gate"; :>> createdAt = "2026-09-01"; :>> createdBy = "claudeOpus5"; :>> method = VerificationMethod::test; :>> procedureText = "RAN: cargo test --release --test migration_fixture_is_realistic -> 3 passed. ARMED per D0253 by emptying report_written's body: case 1 FAILS, the other two still pass, which is the right shape - only the case that encodes the new fix should move. TWO THINGS THE FIXTURE FOUND. (1) issue328, on the first run: a customised engine file silently discarded with only a count reported. (2) A NEAR-MISS worth recording because it would have produced the OPPOSITE conclusion - the first probe ran at a deep scratchpad path, hit Windows MAX_PATH mid git-add, left the tree uncommitted, and migrate then refused on a dirty tree. The customisation survived because the migration never ran. Read casually that is 'customisations are preserved'. The fixture now roots itself shallowly on purpose, and the near-miss is written into its module docs."; }
    verification realisticFixtureReviewGate : Test { :>> id = "82451b79-c46a-40df-1937-b4461c285bf0"; :>> title = "Sprint 511 review gate — three passes per D0172"; :>> createdAt = "2026-09-01"; :>> createdBy = "claudeOpus5"; :>> method = VerificationMethod::inspect; :>> procedureText = "THREE PASSES. (1) IS issue328's FIX THE RIGHT ONE: naming rather than preserving or merging. Preserving would pin a project to a stale engine file forever with no signal; merging needs the engine content at the project's OLD vintage, which keel deliberately does not store because a stamp can drift from the tree it describes. Naming costs nothing, is always truthful, and lands exactly where pm3Reconcile already says to review. (2) DOES CASE 2 ASSERT ANYTHING REAL: yes - a skill the PROJECT authored is not engine content, so a resync touching it would be data loss rather than a policy call, and the case would have caught a resync that walked the whole skills directory. (3) IS THE SUITE HONEST ABOUT ITS OWN LIMIT: the module docs name all four properties, say which three are covered, and say why the fourth is not and when it arrives. A reader cannot mistake the coverage for complete."; }
    verification realisticFixtureCloseOutGate : Test { :>> id = "93562c8a-d57b-41e0-2a48-c5572d396c01"; :>> title = "Sprint 511 closeOut gate (autonomous, D0049)"; :>> createdAt = "2026-09-01"; :>> createdBy = "claudeOpus5"; :>> method = VerificationMethod::inspect; :>> procedureText = "CLOSED. issue328 recorded and fixed in the same commit that found it. Steps 1-3 of the D0275 plan are done: the deadlock is gone, a break is detectable downstream by name, and the fixture can see a project that looks used. Next is step 4, D0273's clean break, which is the first change these three exist to make safe."; }
    verification realisticFixtureRetroGate : Test { :>> id = "a4673d9b-e68c-42f1-3b59-d6683e4a7d12"; :>> title = "Sprint 511 retro gate (autonomous, D0049)"; :>> createdAt = "2026-09-01"; :>> createdBy = "claudeOpus5"; :>> method = VerificationMethod::analyze; :>> procedureText = "THE FINDING IS THE SPRINT'S OWN PREMISE, CONFIRMED. The plan argued that the migration path's defect density comes from being structurally unexercised - the engine refuses its own tree as a self-build, so nothing here ever runs it. Adding ONE realistic property to the fixture produced a defect immediately. That is weak evidence taken alone, and strong taken with the seven prior defects none of which a test found: the path is not fragile because migration is hard, it is fragile because nothing looks at it. The actionable form is not 'write more migration tests' but 'the fixture must resemble a used project', because the three properties added here are the difference between a suite that passes and a suite that finds things. SECOND, SMALLER: my first probe drew the opposite conclusion from a MAX_PATH failure that looked like a pass. A test environment failing in a way that mimics success is worth more suspicion than a test that simply fails - and the tell was available, since the migration reported no work done at all. THIRD, AND IT IS THE THIRD TIME TODAY: this sprint's own suite went red on a defect whose fix had already been applied ONCE, per-instance, leaving an identical live sibling (issue329). The same shape as issue322 (the backtick trap's fourth firing, fixed per-command) and issue325 (add-task's file flag added without routing through the sanitizer every other prose path used). Three recurrences in one day from the same habit: the repair is correct and local, and the CLASS stays open. The rule that would have prevented all three is one line long - after fixing a defect, grep for the shape before moving on - and it is now a control for this instance rather than a resolution, because a rule I have to remember is not a control (D0047)."; }
}
