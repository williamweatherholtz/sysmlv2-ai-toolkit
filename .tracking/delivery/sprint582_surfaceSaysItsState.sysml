// ProjectDeliveryS582 — Sprint 582: four downstream reports on the in-loop surface closed - a deactivated skill says so, the surface stamp names its build, the red-yield keeps its diagnostic, the green Stop line is the owner's one line. EXECUTE. 3 pts.
package ProjectDeliveryS582 {
    private import EngineElement::*;
    private import EngineWork::*;
    private import EngineVerification::*;
    private import EngineRelationships::*;

    #CharteredBy dependency from surfaceSaysItsStateStory to d0348;

    part surfaceSaysItsStateStory : Story {
        :>> id = "3a2c5d81-67a8-461f-8864-0cbd4a80b0d0";
        :>> title = "Sprint 582: four downstream reports on the in-loop surface closed - a deactivated skill says so, the surface stamp names its build, the red-yield keeps its diagnostic, the green Stop line is the owner's one line (3 pts)";
        :>> createdAt = "2026-09-06"; :>> createdBy = "claudeOpus5"; :>> kind = WorkKind::code; :>> priority = WorkPriority::p0; :>> owner = "claudeOpus5"; :>> estimatedPoints = 3;
    }

    action def DeliveryRunS582 {
        action storySurfaceSaysItsState;
        verification storySurfaceSaysItsStateDoD : Test { :>> id = "91d6daed-d0c9-411d-9761-34997d7e3849"; :>> method = VerificationMethod::test; :>> procedureText = "DELIVERED BACKLOG ITEMS: dcDeactivatedSkillSaysSo (D0348; GH#49, issue355), dcSurfaceStampNamesTheBuild (D0349; GH#51, issue357), dcRedYieldKeepsTheDiagnostic (D0350; GH#50), dcStopAdvisoryIsOneLine (D0351; GH#52). DONE: sync-claude deploys a deactivated process's skill with an INACTIVE banner first and the drift check compares the same deployed text, and keel activate/deactivate regenerate the surface where the fact changed; the .claude/.keel-surface sidecar stamps version and build and a drift report names the stamped build and the running build; write::clip_at_line_boundary keeps the red-yield's first problem whole or cuts on a line with (N more lines), budget 2000; the green Stop hook emits one line - N decisions outstanding (range) - how to accept. Covering: short names - and nothing when none. VERIFIED: surface_states_its_state 2/2 (deactivate render, sync, banner first, check clean, reactivate clears; forged stamp plus a mutated skill names both builds, regenerate restores); the clip unit test's three arms; stop_advisory_is_one_line 2/2 (two proposed Decisions produce exactly one JSON line in the owner's format with no console/deck words; none is silence); federation F9 green again after activate/deactivate regenerate the surface; live on this tree: 7 decisions outstanding (d0337..d0346) ... (+1)."; }
        // RAN: DoD passes recorded on keel suite 562/0 (receipt af357bb03f1a); the implement section names each run
        part storySurfaceSaysItsStateDoDR1 : TestResult { :>> id = "db6f9860-f770-405e-9299-d57141f19f69"; :>> outcome = VerdictKind::pass; :>> judgedAgainst = "a66324cffb59b843c32591c1a2e5f19ee1639036"; :>> judgedAt = "2026-09-06"; :>> judgedBy = "claudeOpus5"; }
    }

    verification surfaceSaysItsStateRefineGate : Test { :>> id = "501103ee-4c44-4529-b90c-6084c56bc347"; :>> title = "Sprint 582 refine gate (DoR)"; :>> createdAt = "2026-09-06"; :>> createdBy = "claudeOpus5"; :>> method = VerificationMethod::inspect; :>> procedureText = "READY: four Low/Medium reports from the same downstream day (GH#49-52), each one function. One coupling surfaced: once a deactivated skill is deployed differently, deactivate must regenerate the surface or the next gate reports drift - F9 found it, and the write path that changed the fact now refreshes the surface."; }
    verification surfaceSaysItsStateStandupGate : Test { :>> id = "6e82b5c2-064f-4b92-bad0-9fb3a08aceb1"; :>> title = "Sprint 582 standup gate"; :>> createdAt = "2026-09-06"; :>> createdBy = "claudeOpus5"; :>> method = VerificationMethod::inspect; :>> procedureText = "THE FACT AND ITS RENDERING ARE ONE: a deactivated process is a fact in activation.toml; its skill's opening is that fact rendered. Regenerating at the write is what keeps the two from disagreeing at the gate."; }
    verification surfaceSaysItsStateImplementGate : Test { :>> id = "6b87b4ca-1679-452a-badf-65fd32281f73"; :>> title = "Sprint 582 implement gate"; :>> createdAt = "2026-09-06"; :>> createdBy = "claudeOpus5"; :>> method = VerificationMethod::test; :>> procedureText = "RAN: cargo test --test surface_states_its_state 2/2; --lib clipping 1/1; --test stop_advisory_is_one_line 2/2 (first run red: the fixture's decision was too thin for decision-rationale - fixed in the fixture, not the guard); --test federation f9 green; clippy -D warnings clean; keel sync-claude on this tree (stamp now 0.3.1 plus build); live keel hook stop printed the one line; full suite in suite583.txt."; }
    verification surfaceSaysItsStateReviewGate : Test { :>> id = "c49019bb-be54-41af-aca6-2002c851f727"; :>> title = "Sprint 582 review gate — three passes per D0172"; :>> createdAt = "2026-09-06"; :>> createdBy = "claudeOpus5"; :>> method = VerificationMethod::inspect; :>> procedureText = "THREE PASSES. (1) DOES A DEACTIVATED SKILL EVER READ AS DRIFT: no - the check compares against the deployed text and deactivate regenerates. (2) IS THE ADVISORY EVER MORE THAN ONE LINE: the test counts lines. (3) IS ANY DIAGNOSTIC CUT MID-TOKEN: the clip cuts only at line boundaries and the first line is atomic."; }
    verification surfaceSaysItsStateCloseOutGate : Test { :>> id = "43968aca-dd62-4696-b419-cddd0f2f0dbf"; :>> title = "Sprint 582 closeOut gate (autonomous, D0049)"; :>> createdAt = "2026-09-06"; :>> createdBy = "claudeOpus5"; :>> method = VerificationMethod::inspect; :>> procedureText = "CLOSED. Four items done; GH#49-52 answered by their resolvers' passes."; }
    verification surfaceSaysItsStateRetroGate : Test { :>> id = "9f9f5da1-1d1c-4456-9278-fba0663837d5"; :>> title = "Sprint 582 retro gate (autonomous, D0049)"; :>> createdAt = "2026-09-06"; :>> createdBy = "claudeOpus5"; :>> method = VerificationMethod::analyze; :>> procedureText = "no new item - already tracked: issue357's class (which binary generated what) is the same question issue378 answered for the hooks this morning, and both now record the build. The lesson: when a rendering is derived from a fact, the write that changes the fact re-renders - a gate that finds the stale rendering later is the second-best control."; }
}
