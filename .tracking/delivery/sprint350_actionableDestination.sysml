// ProjectDeliveryS350 — Sprint 350: the click was never broken. It landed on read-only views, three
// reports running, and I checked navigation every time. EXECUTE. 5 pts.
package ProjectDeliveryS350 {
    private import EngineElement::*;
    private import EngineWork::*;
    private import EngineVerification::*;
    private import EngineRelationships::*;

    #CharteredBy dependency from actionableDestinationStory to d0093;

    part actionableDestinationStory : Story {
        :>> id = "0d800590-0814-6590-9b3e-000000300590";
        :>> title = "Sprint 350: the destination was the defect (issue154) + a console that cannot go stale unnoticed (issue153) (5 pts)";
        :>> createdAt = "2026-08-19"; :>> createdBy = "claudeOpus5"; :>> kind = WorkKind::code; :>> priority = WorkPriority::p0; :>> owner = "claudeOpus5"; :>> estimatedPoints = 5;
    }

    action def DeliveryRunS350 {
        action storyActionableDestination;
        verification storyActionableDestinationDoD : Test { :>> id = "0d800591-0814-6591-9b3e-000000300591"; :>> method = VerificationMethod::demo; :>> procedureText = "THE CLICK WAS NEVER BROKEN. Three reports, three rounds of verifying that navigation fired, and the server log settles it: /api/computed/authority-queue was requested four times, and nothing but a click-to-act navigation requests that path - the page's warm-up list is orient, decisions, dispositions, processes. THE CLICK FIRED AND THE DESTINATION HELD NOTHING TO ACT ON. Their words said so precisely - 'i see no items or content to act on' - and I read them as 'the click does nothing'. Mapped explicitly, which is what should have come first: acceptancesPendingVP lands on ORIENT (a count, and it never rendered the pendingAcceptances orient has always returned); authorityQueueVP and sittingReviewVP land on the GENERIC panel, a read-only JSON rendering; only findingsAwaitingDispositionVP lands somewhere actionable. Three of four classes took the reader where they could SEE the work and not DO it, while the `review` panel with working accept/reject buttons held 4 actionable items and 12 pending gates the whole time. SECOND FINDING, issue153: the header showed no `js ok` marker while the log showed their browser polling - both true only if their tab predated that build. issue143's `no-store` stops the browser CACHING the page and does nothing for a page ALREADY LOADED; the SSE stream and 30s interval keep repainting it so it looks current while running logic that is no longer on disk. And every marker I had added was rendered BY JAVASCRIPT, so its absence was ambiguous between three different faults. validate 378 clean; check-engine clean; 36 guards ALL PASS; 191 tests; clippy clean."; }
        part storyActionableDestinationDoDR1 : TestResult { :>> id = "0d800592-0814-6592-9b3e-000000300592"; :>> outcome = VerdictKind::fail; :>> judgedAgainst = "PENDING"; :>> judgedAt = "2026-08-19"; :>> judgedBy = "claudeOpus5"; }
    }

    verification adRefineGate : Test { :>> id = "0d800593-0814-6593-9b3e-000000300593"; :>> title = "Sprint 350 refine gate (DoR)"; :>> createdAt = "2026-08-19"; :>> createdBy = "claudeOpus5"; :>> method = VerificationMethod::inspect; :>> procedureText = "DoR. Scoped as READ THE REPORT LITERALLY rather than as the bug I had already decided it was. 'I see no items or content to act on' is a statement about the DESTINATION, and for three rounds I treated it as a statement about the click. The turn began by asking what the server log could prove about what their browser actually did - which answered in one command what three rounds of source-reading could not. estimatedPoints=5."; }
    part adRefineGateR1 : TestResult { :>> id = "0d800594-0814-6594-9b3e-000000300594"; :>> outcome = VerdictKind::pass; :>> judgedAgainst = "8ba97f9"; :>> judgedAt = "2026-08-19"; :>> judgedBy = "claudeOpus5"; }

    verification adStandupGate : Test { :>> id = "0d800595-0814-6595-9b3e-000000300595"; :>> title = "Sprint 350 standup gate"; :>> createdAt = "2026-08-19"; :>> createdBy = "claudeOpus5"; :>> method = VerificationMethod::inspect; :>> procedureText = "Approach: get EVIDENCE ABOUT THEIR BROWSER instead of reading my own source a fourth time. The request log was sitting there the whole time and settles what the page did, without a DOM, without Playwright, and without asking them to open devtools - the observability D0160 says we lack was partly available and I had not used it. Then fix the destination rather than the click, and key the fix on the PAYLOAD's shape rather than on a list of viewpoint names, so the principle that a newly declared act class needs no console change survives. No blockers."; }
    part adStandupGateR1 : TestResult { :>> id = "0d800596-0814-6596-9b3e-000000300596"; :>> outcome = VerdictKind::pass; :>> judgedAgainst = "8ba97f9"; :>> judgedAt = "2026-08-19"; :>> judgedBy = "claudeOpus5"; }

    verification adImplementGate : Test { :>> id = "0d800597-0814-6597-9b3e-000000300597"; :>> title = "Sprint 350 implement gate"; :>> createdAt = "2026-08-19"; :>> createdBy = "claudeOpus5"; :>> method = VerificationMethod::test; :>> procedureText = "issue154, THE DESTINATION. A panel holding work it cannot discharge now carries a warning-bordered note saying NOTHING ON IT IS A CONTROL, and a bridge to the panel that can act. Keyed on the payload - items whose kind matches accept or confirm, or a pendingAcceptances array - not on viewpoint names, so a class declared tomorrow gets the bridge with no console change. The orient panel gained the bridge AND an `Awaiting YOUR acceptance` card: orient has always returned pendingAcceptances and that panel never rendered it, so the single thing the human was blocking on was the one thing the panel they were sent to did not show. The bridge travels as `data-panel` through the same document-level delegation as card targets, so it needs no per-render wiring and cannot be orphaned. issue153, THE STALE PAGE. The build id is a hash of the console's own bytes and is substituted into the HTML BY THE SERVER, so `build <id>` renders with NO JavaScript - verified live, and the placeholder count in the served response is zero. That is the whole point: every previous marker was JS-rendered, so its absence was ambiguous between a dead script, an old page, and looking at something else. It is exposed as `consoleBuild` separately from `apiVersion`, because the API contract holds steady across many page changes and so cannot tell a page whether it is current; the page compares and reloads itself on SSE hello and every 30s."; }
    part adImplementGateR1 : TestResult { :>> id = "0d800598-0814-6598-9b3e-000000300598"; :>> outcome = VerdictKind::pass; :>> judgedAgainst = "8ba97f9"; :>> judgedAt = "2026-08-19"; :>> judgedBy = "claudeOpus5"; }

    verification adReviewGate : Test { :>> id = "0d800599-0814-6599-9b3e-000000300599"; :>> title = "Sprint 350 review gate"; :>> createdAt = "2026-08-19"; :>> createdBy = "claudeOpus5"; :>> method = VerificationMethod::inspect; :>> procedureText = "Reviewed, and the finding is about me rather than the code. I RECORDED THIS EXACT LIMITATION MYSELF IN SPRINT 343 - 'the generic panel remains READ-ONLY for authority-queue and sitting-coverage, so for those two classes they can see the work and still discharge it elsewhere' - scoped it carefully into a confirmation record, and then treated the same complaint as a navigation bug three times running. A limitation I have written down is one I am responsible for READING, and the whole argument for recording things rather than remembering them is that the record gets consulted. It did not. THE OTHER LESSON IS CHEAPER AND MORE USEFUL: the request log answered in one command what three rounds of reading my own source could not. D0160 says we cannot execute the page, and I generalised that into cannot observe the client at all - which was false. The server sees every request the page makes, and a request to a path only one code path can produce is strong evidence about client behaviour. WHAT I STILL WILL NOT CLAIM: that this fixes what they see. Both DoD results are recorded FAIL with method=demo, because I have asserted a browser behaviour I cannot observe three times already and the fourth would be worse than the first."; }
    part adReviewGateR1 : TestResult { :>> id = "0d80059a-0814-659a-9b3e-00000030059a"; :>> outcome = VerdictKind::pass; :>> judgedAgainst = "8ba97f9"; :>> judgedAt = "2026-08-19"; :>> judgedBy = "claudeOpus5"; }

    verification adCloseOutGate : Test { :>> id = "0d80059b-0814-659b-9b3e-00000030059b"; :>> title = "Sprint 350 closeOut gate (autonomous, D0049)"; :>> createdAt = "2026-08-19"; :>> createdBy = "claudeOpus5"; :>> method = VerificationMethod::inspect; :>> procedureText = "Autonomous closeOut (D0049). issue153 recorded and RESOLVED by dcConsoleBuildStamp - the server-side stamp is verified live and needs no browser. issue154 recorded and its resolver dcActionableDestination left FAILING with method=demo: the code shipped, the claim is unverified, and only the human can close it. The story DoD is also recorded FAIL for the same reason, which means this sprint reads as not-done in every computed view - correct, and the honest-state doctrine (D0098) exists precisely so I can record that rather than paper it. Console is up at 127.0.0.1:7777 on build 87f94652, served from a copy so it survives rebuilds. ONE MANUAL STEP REMAINS AND CANNOT BE AUTOMATED AWAY: a page that was already stale when this shipped carries no build check, so it needs one hard reload. pendingAcceptances d0159, d0161, d0162, d0163. validate 378 clean; check-engine clean; 36 guards ALL PASS; 191 tests; clippy clean."; }
    part adCloseOutGateR1 : TestResult { :>> id = "0d80059c-0814-659c-9b3e-00000030059c"; :>> outcome = VerdictKind::pass; :>> judgedAgainst = "8ba97f9"; :>> judgedAt = "2026-08-19"; :>> judgedBy = "claudeOpus5"; }

    verification adRetroGate : Test { :>> id = "0d80059d-0814-659d-9b3e-00000030059d"; :>> title = "Sprint 350 retro gate (autonomous, D0049)"; :>> createdAt = "2026-08-19"; :>> createdBy = "claudeOpus5"; :>> method = VerificationMethod::analyze; :>> procedureText = "Autonomous retro (D0049) under D0131's retroTrack. AVOIDABLE-ISSUE, AND IT IS THE LARGEST OF THE SESSION: the human reported one problem three times, described it accurately each time, and I diagnosed something else each time. 'I see no items or content to act on' names the DESTINATION. I read 'click to act does not work' and verified the click. THE MECHANISM OF THE ERROR IS WORTH MORE THAN THE ERROR: I formed a hypothesis on the first report, and each subsequent report was processed as new evidence about THAT hypothesis rather than as a fresh description of the problem. Re-reading their words literally, as words, is what broke it - and it took a fourth report plus their explicit correction about the header to force that. THE RULE: on a repeat report, re-read the report before re-reading the code, and quote it back to check the reading. SECOND AVOIDABLE-ISSUE: I had recorded the exact limitation in sprint 343's confirmation record and never consulted it. Recording is only worth its cost if the record is read on the next encounter, and mine was read by nobody including me - which is an argument for D0161's `keel why` that I did not expect to make from experience. THIRD: I concluded from D0160 that the client was unobservable, when the server's own request log distinguishes code paths precisely enough to prove a click fired. A stated limitation got over-generalised into a broader one and closed off an avenue that was open the whole time. WELL: (1) the log evidence was decisive and cost one command; (2) the destination fix is keyed on payload shape rather than a viewpoint list, so it does not erode the principle that declaring a class needs no console change; (3) the build stamp is SERVER-rendered, which is the one form of marker that survives the failure it diagnoses; (4) both results are recorded FAIL with method=demo rather than asserting a fourth unobserved browser claim. Estimate 5 pts, delivered as code with its verification outstanding."; }
    part adRetroGateR1 : TestResult { :>> id = "0d80059e-0814-659e-9b3e-00000030059e"; :>> outcome = VerdictKind::pass; :>> judgedAgainst = "8ba97f9"; :>> judgedAt = "2026-08-19"; :>> judgedBy = "claudeOpus5"; }
}
