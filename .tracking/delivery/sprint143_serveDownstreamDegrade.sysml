// ProjectDeliveryS143 — Sprint 143: serveDownstreamDegrade (D0093) — the `keel serve` agent bridge is
// OPTIONAL; a downstream consumer without the local `claude` CLI must get a CLEAR message, not a cryptic
// failure. Found + FIXED a real degradation gap: on Windows a missing `claude` spawns `cmd /C` fine and
// exits 1 (cryptic), so spawn-failure detection misses it. Added a cross-platform PATH pre-probe so BOTH
// platforms emit the clear "not installed" message; verified the read console + report/view actions work
// on a fresh `keel init` project; documented the agent-bridge requirement in the README. 2 pts. AUTONOMOUS (D0049).
package ProjectDeliveryS143 {
    private import EngineElement::*;
    private import EngineWork::*;
    private import EngineVerification::*;
    private import EngineRelationships::*;

    #CharteredBy dependency from serveDownstreamDegradeStory to d0093;

    part serveDownstreamDegradeStory : Story {
        :>> id = "63940516-2c7d-4e8f-c143-51627384c001";
        :>> title = "Sprint 143: serveDownstreamDegrade (2 pts) — agent bridge degrades gracefully without `claude`; verify read console on a fresh project (D0093)";
        :>> createdAt = "2026-06-23"; :>> createdBy = "wweatherholtz"; :>> kind = WorkKind::code; :>> priority = WorkPriority::p2; :>> owner = "claudeOpus"; :>> estimatedPoints = 2;
    }

    action def DeliveryRunS143 {
        action storyServeDownstreamDegrade;
        verification storyServeDownstreamDegradeDoD : Test { :>> id = "63940516-2c7d-4e8f-c143-51627384c002"; :>> method = VerificationMethod::test; :>> procedureText = "The D0094 console ships in the binary, but the in-console ACTIONS (critique/investigate/report) shell out to a local `claude` CLI a downstream consumer may not have. FINDING: degradation was NOT graceful on Windows — `api_agent_stream` spawns `cmd /C claude`, and `cmd` always exists, so the spawn SUCCEEDS even when `claude` is absent; the user got a cryptic 'agent finished (exit 1)' instead of a clear message (the Unix path failed the spawn and showed the clear error, but Windows missed it). FIX (serve.rs): added a cross-platform PATH pre-probe `claude_on_path()` (pure core `claude_in_dirs`, honoring PATHEXT on Windows: claude/.cmd/.exe/.bat) checked BEFORE spawning; when absent the SSE stream yields a clear 'the `claude` CLI is not on PATH — the agent bridge is optional. Install Claude Code + log in ... do NOT set ANTHROPIC_API_KEY' error and returns — uniform on both platforms. The read console, views, and reports are unaffected. VERIFIED (live, fresh `keel init` project): `keel serve --port 7788` -> GET / = HTTP 200 (17KB console); /api/orient = valid empty-state JSON; /api/decisions = 200; /view/report/assurance = 200 (deterministic action). Added a deterministic regression test (D0047): `claude_in_dirs` reports absent on an empty PATH dir, present once a platform-named `claude` executable is dropped in. DOCUMENTED: README now states the agent bridge is optional + needs Claude Code installed/on-PATH/logged-in (never ANTHROPIC_API_KEY) + degrades gracefully. VERIFY: clippy --workspace --all-targets -D warnings green; cargo test 49 lib (+ the new probe test) + init_smoke + BDD pass; keel validate + guard all (13) green."; }
        part storyServeDownstreamDegradeDoDR1 : TestResult { :>> id = "63940516-2c7d-4e8f-c143-51627384c003"; :>> outcome = VerdictKind::pass; :>> judgedAgainst = "354447d"; :>> judgedAt = "2026-06-23"; :>> judgedBy = "claudeOpus"; }
    }

    verification serveDownstreamDegradeRefineGate : Test { :>> id = "63940516-2c7d-4e8f-c143-51627384c004"; :>> title = "Sprint 143 refine gate (DoR)"; :>> createdAt = "2026-06-23"; :>> createdBy = "claudeOpus"; :>> method = VerificationMethod::inspect; :>> procedureText = "DoR: deployment-readiness #7 (last internal). The console ships in the binary but its agent actions need a local `claude`; downstream consumers may lack it — verify graceful degradation + read-console-without-claude + document. Resolver: serveDownstreamDegrade. estimatedPoints=2. #CharteredBy d0093. DoD accepted."; }
    part serveDownstreamDegradeRefineGateR1 : TestResult { :>> id = "63940516-2c7d-4e8f-c143-51627384c005"; :>> outcome = VerdictKind::pass; :>> judgedAgainst = "354447d"; :>> judgedAt = "2026-06-23"; :>> judgedBy = "claudeOpus"; }
    verification serveDownstreamDegradeStandupGate : Test { :>> id = "63940516-2c7d-4e8f-c143-51627384c006"; :>> title = "Sprint 143 standup gate"; :>> createdAt = "2026-06-23"; :>> createdBy = "claudeOpus"; :>> method = VerificationMethod::inspect; :>> procedureText = "Approach: trace the agent-spawn path; on Windows the `cmd /C` shim masks a missing `claude` (spawn succeeds, exit 1). Add a PATH pre-probe so both platforms emit the clear optional-bridge message; verify the read console on a fresh init via curl; add a deterministic test; document in README. No blockers."; }
    part serveDownstreamDegradeStandupGateR1 : TestResult { :>> id = "63940516-2c7d-4e8f-c143-51627384c007"; :>> outcome = VerdictKind::pass; :>> judgedAgainst = "354447d"; :>> judgedAt = "2026-06-23"; :>> judgedBy = "claudeOpus"; }
    verification serveDownstreamDegradeImplementGate : Test { :>> id = "63940516-2c7d-4e8f-c143-51627384c008"; :>> title = "Sprint 143 implement gate"; :>> createdAt = "2026-06-23"; :>> createdBy = "claudeOpus"; :>> method = VerificationMethod::test; :>> procedureText = "Added `claude_on_path`/`claude_in_dirs` (PATHEXT-aware) + a pre-spawn guard yielding the clear optional-bridge error; README agent-bridge note; a deterministic probe test. VERIFIED (live): fresh `keel init` -> `keel serve` serves / (200), /api/orient, /api/decisions, /view/report/assurance. clippy green (fixed unnecessary_to_owned on the literal message); cargo test 49 lib + init_smoke + BDD pass; keel validate + guard all (13) PASS."; }
    part serveDownstreamDegradeImplementGateR1 : TestResult { :>> id = "63940516-2c7d-4e8f-c143-51627384c009"; :>> outcome = VerdictKind::pass; :>> judgedAgainst = "354447d"; :>> judgedAt = "2026-06-23"; :>> judgedBy = "claudeOpus"; }
    verification serveDownstreamDegradeReviewGate : Test { :>> id = "63940516-2c7d-4e8f-c143-51627384c00a"; :>> title = "Sprint 143 review gate"; :>> createdAt = "2026-06-23"; :>> createdBy = "claudeOpus"; :>> method = VerificationMethod::inspect; :>> procedureText = "Diff reviewed. The task earned its keep: a passive read would have assumed kill_on_drop + spawn-error covered degradation, but the Windows `cmd /C` shim silently swallowed the missing-CLI case into a cryptic exit 1 — exactly the downstream-consumer scenario. The PATH pre-probe makes the optional-bridge contract explicit + uniform, the read console is verified to stand alone, and the requirement is now documented for consumers. The pure `claude_in_dirs` split makes it regression-tested without env mutation. Clean."; }
    part serveDownstreamDegradeReviewGateR1 : TestResult { :>> id = "63940516-2c7d-4e8f-c143-51627384c00b"; :>> outcome = VerdictKind::pass; :>> judgedAgainst = "354447d"; :>> judgedAt = "2026-06-23"; :>> judgedBy = "claudeOpus"; }
    verification serveDownstreamDegradeCloseOutGate : Test { :>> id = "63940516-2c7d-4e8f-c143-51627384c00c"; :>> title = "Sprint 143 closeOut gate (autonomous, D0049)"; :>> createdAt = "2026-06-23"; :>> createdBy = "claudeOpus"; :>> method = VerificationMethod::inspect; :>> procedureText = "Autonomous closeOut (D0049): DoD pass; agent bridge degrades gracefully + uniformly; read console verified standalone on a fresh project; documented. clippy + cargo test 49 + init_smoke + keel validate + guard all (13) green. Self-evidencing (D0051). Deployment-readiness: ALL 4 internal tasks done (cargoReleaseMetadata, consumerReadme, introductionDryRun, serveDownstreamDegrade); only the outward-facing releaseWorkflow + releaseTag010 remain, held for the human's ship decision."; }
    part serveDownstreamDegradeCloseOutGateR1 : TestResult { :>> id = "63940516-2c7d-4e8f-c143-51627384c00d"; :>> outcome = VerdictKind::pass; :>> judgedAgainst = "354447d"; :>> judgedAt = "2026-06-23"; :>> judgedBy = "claudeOpus"; }
    verification serveDownstreamDegradeRetroGate : Test { :>> id = "63940516-2c7d-4e8f-c143-51627384c00e"; :>> title = "Sprint 143 retro gate (autonomous, D0049)"; :>> createdAt = "2026-06-23"; :>> createdBy = "claudeOpus"; :>> method = VerificationMethod::analyze; :>> procedureText = "Autonomous retro (D0049). WELL: actually tracing the spawn path (not assuming) surfaced a platform-specific degradation gap — the Windows `cmd /C` shim that makes the CLI spawnable also masks its absence as a cryptic exit 1. AVOIDABLE-ISSUE SCAN: the gap is now guarded by a deterministic `claude_in_dirs` unit test (D0047 — the correction became a permanent guard), and the read-console-standalone claim is curl-verified on a fresh init. LESSON: a cross-platform spawn whose wrapper always exists needs an explicit availability pre-check — never infer 'installed' from 'spawn succeeded'. NON-blocking: the agent-bridge requirement is now documented in the README. This closes the 4 INTERNAL deployment-readiness tasks; releaseWorkflow + releaseTag010 are outward-facing and await the human's explicit ship decision. Estimate 2 pts held."; }
    part serveDownstreamDegradeRetroGateR1 : TestResult { :>> id = "63940516-2c7d-4e8f-c143-51627384c00f"; :>> outcome = VerdictKind::pass; :>> judgedAgainst = "354447d"; :>> judgedAt = "2026-06-23"; :>> judgedBy = "claudeOpus"; }
}
