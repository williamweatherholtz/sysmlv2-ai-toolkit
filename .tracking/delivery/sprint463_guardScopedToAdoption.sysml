// ProjectDeliveryS463 — Sprint 463: a control keel added for itself stops breaking the commit gate of projects that never adopted it. EXECUTE. 2 pts.
package ProjectDeliveryS463 {
    private import EngineElement::*;
    private import EngineWork::*;
    private import EngineVerification::*;
    private import EngineRelationships::*;

    #CharteredBy dependency from guardScopedToAdoptionStory to d0228;

    part guardScopedToAdoptionStory : Story {
        :>> id = "b7dafce5-0f51-4324-90bb-ea2a81b99bd5";
        :>> title = "Sprint 463: the guard that broke the first project it met (2 pts)";
        :>> createdAt = "2026-08-25"; :>> createdBy = "claudeFable5"; :>> kind = WorkKind::code; :>> priority = WorkPriority::p0; :>> owner = "claudeFable5"; :>> estimatedPoints = 2;
    }

    action def DeliveryRunS463 {
        action storyGuardScopedToAdoption;
        verification storyGuardScopedToAdoptionDoD : Test { :>> id = "f00d0fc4-3b33-443d-b9d4-5c8ed5dcfd49"; :>> method = VerificationMethod::test; :>> procedureText = "DELIVERED: dcGuardScopedToAdoption (resolves issue259, HIGH, discoveredInField; D0228). Guard 50 landed in the previous sprint, requiring every declared Process to carry an APPLIES-WHEN condition. Run for the first time against a REAL adopting project - penumbra, on a 20-August engine snapshot, which has never adopted project-onboarding - it failed 22 times out of 22 and would have broken that project's commit gate on arrival, for a convention it never chose. That is precisely the failure D0164 exists to prevent, and the uncomfortable part is that I wrote the guard the same day while quoting D0164 in a different context: knowing the rule did not prevent breaking it, because nothing in the self-build could feel the consequence. THE FIX: the guard enforces nothing unless project-onboarding is present in the project, and REPORTS 0 scanned rather than skipping silently, so an out-of-scope guard stays visible instead of reading as a vacuous pass. Deliberately NOT solved by having projectOnboarding claim the guard, which was the obvious move and is wrong: a claim makes a guard switchable in a project that HAS the unit, but a project that LACKS the unit has no claim either, so guard_state returns Core and enforces it anyway - the exact opposite of what is needed. Presence of the process is the fact that decides it."; }
        part storyGuardScopedToAdoptionDoDR1 : TestResult { :>> id = "55976bfc-e38c-4832-84fd-5a9427656960"; :>> outcome = VerdictKind::pass; :>> judgedAgainst = "f4417e9"; :>> judgedAt = "2026-08-24"; :>> judgedBy = "claudeFable5"; }
        part storyGuardScopedToAdoptionDoDR2 : TestResult { :>> id = "b56945f9-38a0-4c0a-a787-044a385e74be"; :>> outcome = VerdictKind::pass; :>> judgedAgainst = "f4417e9033b3d306085a2e5b34a9e89b2e708243"; :>> judgedAt = "2026-08-24"; :>> judgedBy = "claudeFable5"; }
    }

    verification guardScopedToAdoptionRefineGate : Test { :>> id = "6060f4e1-c793-4121-81d3-48b7992d8487"; :>> title = "Sprint 463 refine gate (DoR)"; :>> createdAt = "2026-08-25"; :>> createdBy = "claudeFable5"; :>> method = VerificationMethod::inspect; :>> procedureText = "DoR. Resolves issue259, found by actually attempting the adoption the author asked for rather than by reading the tree. Scope: scope the guard to adoption, verify on the real project, and record why the obvious mechanism (claiming the guard) does not work. 2 points."; }
    part guardScopedToAdoptionRefineGateR1 : TestResult { :>> id = "64828649-e055-41ba-95a6-510158572777"; :>> outcome = VerdictKind::pass; :>> judgedAgainst = "f4417e9"; :>> judgedAt = "2026-08-24"; :>> judgedBy = "claudeFable5"; }
    part guardScopedToAdoptionRefineGateR2 : TestResult { :>> id = "c1ba3d11-c96d-4308-af81-e8ca34c59c36"; :>> outcome = VerdictKind::pass; :>> judgedAgainst = "f4417e9033b3d306085a2e5b34a9e89b2e708243"; :>> judgedAt = "2026-08-24"; :>> judgedBy = "claudeFable5"; }
    verification guardScopedToAdoptionStandupGate : Test { :>> id = "5e8ccae0-36a8-45fc-8d77-b5617d8df582"; :>> title = "Sprint 463 standup gate"; :>> createdAt = "2026-08-25"; :>> createdBy = "claudeFable5"; :>> method = VerificationMethod::inspect; :>> procedureText = "Approach: verify the claim before believing it - run the current binary's guards against penumbra and read the number, rather than reasoning about whether the guard would fire. Then fix at the root and re-run the same real case. guards.rs is keystone-locked, so D0228 co-commits. No blockers."; }
    part guardScopedToAdoptionStandupGateR1 : TestResult { :>> id = "609919f9-a0c0-47e3-b541-1f0ad065bec3"; :>> outcome = VerdictKind::pass; :>> judgedAgainst = "f4417e9"; :>> judgedAt = "2026-08-24"; :>> judgedBy = "claudeFable5"; }
    part guardScopedToAdoptionStandupGateR2 : TestResult { :>> id = "e4fee392-1b6b-4057-869e-1ad0810209a1"; :>> outcome = VerdictKind::pass; :>> judgedAgainst = "f4417e9033b3d306085a2e5b34a9e89b2e708243"; :>> judgedAt = "2026-08-24"; :>> judgedBy = "claudeFable5"; }
    verification guardScopedToAdoptionImplementGate : Test { :>> id = "be086018-c9cd-46e7-b9cc-4713320b824d"; :>> title = "Sprint 463 implement gate"; :>> createdAt = "2026-08-25"; :>> createdBy = "claudeFable5"; :>> method = VerificationMethod::test; :>> procedureText = "Verified on the REAL case, both directions. penumbra: 22 violations before, [guard] ALL PASS after, with process-applicability reporting 0 scanned rather than passing silently. keel itself: unchanged at 25 scanned, still enforced. The unit test asserts the not-adopted zero, the adopted pass, the adopted violation, and that a non-Process file stays out of scope. validate 515 + all 50 guards + rules 0 violations + clippy clean; 268 + 9 + 1 + 32 tests across every target."; }
    part guardScopedToAdoptionImplementGateR1 : TestResult { :>> id = "ae2b83ae-38f7-4166-9563-2272003ee8a8"; :>> outcome = VerdictKind::pass; :>> judgedAgainst = "f4417e9"; :>> judgedAt = "2026-08-24"; :>> judgedBy = "claudeFable5"; }
    part guardScopedToAdoptionImplementGateR2 : TestResult { :>> id = "38e5dd14-52ba-4782-bcea-0190c2f3f7b9"; :>> outcome = VerdictKind::pass; :>> judgedAgainst = "f4417e9033b3d306085a2e5b34a9e89b2e708243"; :>> judgedAt = "2026-08-24"; :>> judgedBy = "claudeFable5"; }
    verification guardScopedToAdoptionReviewGate : Test { :>> id = "c2d9a214-ea82-49ac-9b39-d5d77b0de44b"; :>> title = "Sprint 463 review gate — three passes per D0172"; :>> createdAt = "2026-08-25"; :>> createdBy = "claudeFable5"; :>> method = VerificationMethod::inspect; :>> procedureText = "PASS 1, CLAIMS: the 22-of-22 and the ALL PASS are quoted tool output from runs against the real project, not estimates. PASS 2, BOUNDARY: (i) the coupling means a project can hold processes without conditions indefinitely and never be told - intended, but it does mean the guard cannot help a project drifting INTO onboarding one process at a time; (ii) the scope test is file PRESENCE, which is cruder than reading the activation contract, and a project that deleted the process file while keeping the activation entry would silently lose the guard; (iii) the 0-scanned report is the only thing standing between this and the vacuous-pass class, and it is a printed number rather than an enforced one. PASS 3, OWN DIFF: I cited D0164 in a decision written the same day as the guard that violated it. The rule was not merely known, it was IN MY HANDS, and it still did not transfer - which says the useful control is not another rule but running a real adoption before landing a guard. WHAT A REVIEWER SHOULD ATTACK: whether file presence is the right scope predicate, or whether the activation contract should decide it."; }
    part guardScopedToAdoptionReviewGateR1 : TestResult { :>> id = "c6a7f4aa-25be-4940-8434-d0405771ac14"; :>> outcome = VerdictKind::pass; :>> judgedAgainst = "f4417e9"; :>> judgedAt = "2026-08-24"; :>> judgedBy = "claudeFable5"; }
    part guardScopedToAdoptionReviewGateR2 : TestResult { :>> id = "988a3168-2cbd-4ef6-8451-66e2a9345c28"; :>> outcome = VerdictKind::pass; :>> judgedAgainst = "f4417e9033b3d306085a2e5b34a9e89b2e708243"; :>> judgedAt = "2026-08-24"; :>> judgedBy = "claudeFable5"; }
    verification guardScopedToAdoptionCloseOutGate : Test { :>> id = "27e16a62-8d7c-4370-8448-c4d80907274a"; :>> title = "Sprint 463 closeOut gate (autonomous, D0049)"; :>> createdAt = "2026-08-25"; :>> createdBy = "claudeFable5"; :>> method = VerificationMethod::inspect; :>> procedureText = "Autonomous closeOut (D0049). issue259 resolved: penumbra passes every guard with the current binary, which is what makes pinning it to a keel release viable at all. validate + all 50 guards + check-engine + rules green at f4417e9."; }
    part guardScopedToAdoptionCloseOutGateR1 : TestResult { :>> id = "7313053e-1e5c-4b09-bd99-9ee7841e7bb4"; :>> outcome = VerdictKind::pass; :>> judgedAgainst = "f4417e9"; :>> judgedAt = "2026-08-24"; :>> judgedBy = "claudeFable5"; }
    part guardScopedToAdoptionCloseOutGateR2 : TestResult { :>> id = "09a8adc8-f6d6-4247-a854-ea8d4501e7a3"; :>> outcome = VerdictKind::pass; :>> judgedAgainst = "f4417e9033b3d306085a2e5b34a9e89b2e708243"; :>> judgedAt = "2026-08-24"; :>> judgedBy = "claudeFable5"; }
    verification guardScopedToAdoptionRetroGate : Test { :>> id = "0fdad10e-2ce8-427e-8b89-c5355de5cead"; :>> title = "Sprint 463 retro gate (autonomous, D0049)"; :>> createdAt = "2026-08-25"; :>> createdBy = "claudeFable5"; :>> method = VerificationMethod::analyze; :>> procedureText = "Autonomous retro (D0049). AVOIDABLE-ISSUE SCAN under rcRecurrence: (1) THE PATTERN IS NOW UNDENIABLE - third time in four sprints that a defect was invisible to the self-build and obvious on contact with a second project (issue251, issue253, issue257, now issue259). The retro of sprint 462 said the highest-yield audit available is another adoption rather than another critique pass; this sprint is the evidence for that claim, found one sprint later. It should become a standing step: run the guards against a real adopting project BEFORE landing a new guard. (2) Knowing D0164 did not prevent violating D0164 on the same day, which is the strongest argument in this session that manual vigilance is not a control (D0047) - the rule was quoted, not forgotten. (3) The obvious fix (claim the guard from the process) was wrong for a reason that took reading guard_state to see: an absent unit claims nothing, so the guard returns to Core. Estimate 2 pts, delivered 2."; }
    part guardScopedToAdoptionRetroGateR1 : TestResult { :>> id = "479ffc0d-99b9-4289-902b-60ccf4b7d9fd"; :>> outcome = VerdictKind::pass; :>> judgedAgainst = "f4417e9"; :>> judgedAt = "2026-08-24"; :>> judgedBy = "claudeFable5"; }
    part guardScopedToAdoptionRetroGateR2 : TestResult { :>> id = "0c508a13-2e61-461a-856e-eae9e2820aff"; :>> outcome = VerdictKind::pass; :>> judgedAgainst = "f4417e9033b3d306085a2e5b34a9e89b2e708243"; :>> judgedAt = "2026-08-24"; :>> judgedBy = "claudeFable5"; }
}
