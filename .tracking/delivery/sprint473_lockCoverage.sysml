// ProjectDeliveryS473 - Sprint 473: can the workspace gate be DISARMED unsigned? It could, two ways, and one of them was the control cited to justify relaxing the other. EXECUTE. 5 pts.
package ProjectDeliveryS473 {
    private import EngineElement::*;
    private import EngineWork::*;
    private import EngineVerification::*;
    private import EngineRelationships::*;

    #CharteredBy dependency from lockCoverageStory to d0239;

    part lockCoverageStory : Story {
        :>> id = "4e0d41ef-11c7-4f78-8285-fea6827d2bba";
        :>> title = "Sprint 473: the keystone lock covers the surface no project owns, and adherence sees every project at every depth (5 pts)";
        :>> createdAt = "2026-08-27"; :>> createdBy = "claudeOpus5"; :>> kind = WorkKind::code; :>> priority = WorkPriority::p0; :>> owner = "claudeOpus5"; :>> estimatedPoints = 5;
    }

    action def DeliveryRunS473 {
        action storyLockCoverage;
        verification storyLockCoverageDoD : Test { :>> id = "5ce0fa6b-beff-4bf3-ae55-6e4b4681fba9"; :>> method = VerificationMethod::test; :>> procedureText = "DELIVERED: dcWorkspaceSurfaceIsOwned (issue276) and dcAdherenceIsWorkspaceAware (issue277) under D0239. gate --workspace now applies the keystone lock to staged paths no project gate covers and EXITS NON-ZERO - two rules, an unowned locked path and any staged deletion under an .engine/ directory at any depth, the second not being a special case of the first because deleting a project makes its paths unowned at exactly the moment they are removed. audit-adherence iterates the discovered project set, prefixing each pathspec and qualifying each signature key with the project label so monotonicity is per project, and ANCHORS to the repository root before any path-scoped read. A marked Decision in ANY project authorises the repository's own locked surface."; }
    // RAN: cargo test --release => 11 suites 0 failures, incl the_unowned_surface_is_under_the_keystone_lock, root_project_keys_are_unqualified_so_single_project_repos_are_unchanged and this_repo_yields_the_empty_prefix | issue276 in C:/kt/w4: the ONE root hook replaced with exit 0 and staged alone => gate exit 1 'KEYSTONE - 1 staged change to the locked surface carry no co-committed Decision' (previously exit 0, 2 projects gated clean, after PRINTING the unowned file); staging the deletion of an entire project => 447 deletions, 402 keystone events, exit 1 (previously silent); a co-committed #SafetyChange Decision in a peer project => exit 0 | issue277 in C:/kt/w4: 8 blocking rules downgraded to warning in alpha, committed past the hook => audit-adherence exit 1 naming 'alpha/rule:acceptanceEventRule: blocking/bound/core -> warning/active' from the REPO ROOT, from INSIDE alpha, and from beta/.tracking - three depths, exit 1 at each (one directory down previously reported PASS); a SIGNED weakening in beta => exit 0 | single-project parity: this repo's audit-adherence PASS with zero project-qualified keys, project_prefixes returns [\"\"].
        part storyLockCoverageDoDR1 : TestResult { :>> id = "00401958-8573-46ab-b94b-bcbc28602214"; :>> outcome = VerdictKind::pass; :>> judgedAgainst = "09e4e87"; :>> judgedAt = "2026-08-27"; :>> judgedBy = "claudeOpus5"; }
    }

    verification lockCoverageRefineGate : Test { :>> id = "4e80cfda-7bbc-48fb-b754-2fcc6aa89666"; :>> title = "Sprint 473 refine gate (DoR)"; :>> createdAt = "2026-08-27"; :>> createdBy = "claudeOpus5"; :>> method = VerificationMethod::inspect; :>> procedureText = "DoR: with D0238 landed the gate RUNS across a workspace, and the two remaining Criticals are both the next question - whether it can be WEAKENED without a signature. Taken together because they are two halves of one answer: 276 is the commit-time lock, 277 is the independent re-derivation CI runs, and 277 is the control D0234 CITED when relaxing 272. Both reproduced first. Resolvers: dcWorkspaceSurfaceIsOwned, dcAdherenceIsWorkspaceAware. estimatedPoints=5. #CharteredBy d0239."; }
    part lockCoverageRefineGateR1 : TestResult { :>> id = "0c212a9a-c145-4db0-a07b-a5f18d9d0be6"; :>> outcome = VerdictKind::pass; :>> judgedAgainst = "09e4e87"; :>> judgedAt = "2026-08-27"; :>> judgedBy = "claudeOpus5"; }
    verification lockCoverageStandupGate : Test { :>> id = "cb8edf8e-7e0f-4405-bfe7-edbf40941c7c"; :>> title = "Sprint 473 standup gate"; :>> createdAt = "2026-08-27"; :>> createdBy = "claudeOpus5"; :>> method = VerificationMethod::inspect; :>> procedureText = "Approach: reuse the guard's OWN predicates rather than copy them - is_locked_path and staged_marked_decision are exposed from guards.rs so the locked set has one home (D0105); a second copy in workspace.rs would drift the first time a path class is added. For adherence, qualify signature keys by project label so the existing monotonicity comparison works unchanged and a root project keeps unqualified keys. This is an ENFORCEMENT SURFACE change on both counts - guards.rs and adherence.rs are both in the locked set - so it rides a co-committed #SafetyChange Decision (D0239)."; }
    part lockCoverageStandupGateR1 : TestResult { :>> id = "92de50c2-0e9c-4178-bbfb-fe0042bfaca6"; :>> outcome = VerdictKind::pass; :>> judgedAgainst = "09e4e87"; :>> judgedAt = "2026-08-27"; :>> judgedBy = "claudeOpus5"; }
    verification lockCoverageImplementGate : Test { :>> id = "0356f4a3-ed4f-4837-bdaa-00f85b40e9db"; :>> title = "Sprint 473 implement gate"; :>> createdAt = "2026-08-27"; :>> createdBy = "claudeOpus5"; :>> method = VerificationMethod::test; :>> procedureText = "Implemented and verified against real git repositories at five case boundaries. TWO defects in my own fix were caught by running the DoD's verifications rather than the happy path. First: requiring the root-relative .engine/decisions/ form made the block work perfectly and made the shared root hook PERMANENTLY UNCHANGEABLE - with no project at the repository root, no Decision could ever authorise a change to the surface - found by the third verification, that a legitimately signed change still passes. Second: ls-tree pathspecs resolve relative to the directory git was invoked in, so the project prefix was applied on top of git's own implicit prefix and the audit reported PASS from one directory down on a tree carrying eight unsigned downgrades - found only by the every-depth clause. Also hit the heredoc backslash mangling once more, in a char literal, and fixed it through the edit tools."; }
    // RAN: cargo test --release => 11 suites 0 failures, incl the_unowned_surface_is_under_the_keystone_lock, root_project_keys_are_unqualified_so_single_project_repos_are_unchanged and this_repo_yields_the_empty_prefix | issue276 in C:/kt/w4: the ONE root hook replaced with exit 0 and staged alone => gate exit 1 'KEYSTONE - 1 staged change to the locked surface carry no co-committed Decision' (previously exit 0, 2 projects gated clean, after PRINTING the unowned file); staging the deletion of an entire project => 447 deletions, 402 keystone events, exit 1 (previously silent); a co-committed #SafetyChange Decision in a peer project => exit 0 | issue277 in C:/kt/w4: 8 blocking rules downgraded to warning in alpha, committed past the hook => audit-adherence exit 1 naming 'alpha/rule:acceptanceEventRule: blocking/bound/core -> warning/active' from the REPO ROOT, from INSIDE alpha, and from beta/.tracking - three depths, exit 1 at each (one directory down previously reported PASS); a SIGNED weakening in beta => exit 0 | single-project parity: this repo's audit-adherence PASS with zero project-qualified keys, project_prefixes returns [\"\"].
    part lockCoverageImplementGateR1 : TestResult { :>> id = "dd03b187-4513-4e18-a854-95de1a65f6d0"; :>> outcome = VerdictKind::pass; :>> judgedAgainst = "09e4e87"; :>> judgedAt = "2026-08-27"; :>> judgedBy = "claudeOpus5"; }
    verification lockCoverageReviewGate : Test { :>> id = "44e365b9-b179-4687-ad30-06f984ea1f17"; :>> title = "Sprint 473 review gate"; :>> createdAt = "2026-08-27"; :>> createdBy = "claudeOpus5"; :>> method = VerificationMethod::inspect; :>> procedureText = "Diff reviewed. The DoD offered a fallback - gate the issue272 added-file exemption on a single-project repo until the real fix lands - and it is deliberately NOT taken, because the real fix landed; taking it would have left the compensation still absent while reporting the item done. Single-project parity is measured rather than asserted: this repo's audit-adherence PASSes with zero project-qualified keys in its output and project_prefixes returns the empty prefix, both pinned by tests. A stale doc block above signature() was removed in the same commit rather than left to describe the function it no longer sits on."; }
    part lockCoverageReviewGateR1 : TestResult { :>> id = "e3a1c5bf-0306-47c4-a6e8-7a39d41d2ea9"; :>> outcome = VerdictKind::pass; :>> judgedAgainst = "09e4e87"; :>> judgedAt = "2026-08-27"; :>> judgedBy = "claudeOpus5"; }
    verification lockCoverageCloseOutGate : Test { :>> id = "608971d5-8eff-4ed4-94e7-a10796633bca"; :>> title = "Sprint 473 closeOut gate (autonomous, D0049)"; :>> createdAt = "2026-08-27"; :>> createdBy = "claudeOpus5"; :>> method = VerificationMethod::inspect; :>> procedureText = "Autonomous closeOut (D0049): both DoDs recorded pass with their RAN receipts; the frontier was read back from keel whats-next. All FOUR workspace Criticals are now closed across sprints 472 and 473. Remaining from the panel: issue279-284, none Critical - the two that touch enforcement are dcLandGatesBeforeThePush, where land pushes before it gates so nothing is gated on the success path, and dcOneGateDefinition, where three bodies of the gate carry three different bars. Both concern the gate's SHAPE rather than whether it can be disarmed unsigned. Self-evidencing (D0051): no human confirmation claimed."; }
    part lockCoverageCloseOutGateR1 : TestResult { :>> id = "5127e8b0-af8f-4ca1-9c9c-73b0fe6f1d8c"; :>> outcome = VerdictKind::pass; :>> judgedAgainst = "09e4e87"; :>> judgedAt = "2026-08-27"; :>> judgedBy = "claudeOpus5"; }
    verification lockCoverageRetroGate : Test { :>> id = "009dda00-e058-42f2-b159-27a435e0c9ab"; :>> title = "Sprint 473 retro gate (autonomous, D0049)"; :>> createdAt = "2026-08-27"; :>> createdBy = "claudeOpus5"; :>> method = VerificationMethod::analyze; :>> procedureText = "Autonomous retro (D0049). WELL: running EVERY clause of the DoD, including the ones that look like formalities, found two defects in the fix itself - the permanently-unchangeable surface and the depth blindness. Both would have shipped as a passing item on the first two verifications alone, and both are the same failure shape as the bug being fixed, one layer down. That is the strongest evidence this session has produced for writing DoDs that name specific negative cases rather than 'verify it works'. FINDING: issue277 is a control cited as compensation for relaxing another control, which did not work in the arrangement the citing Decision itself introduced. Nothing checks that. A Decision may name a compensating control in prose and no gate ever asks whether that control fires in the case being exempted - which is how the residual in issue272 stayed open for five days while reading as covered. AVOIDABLE-ISSUE SCAN: the false-green in issue276 PRINTED the unowned files before passing, so the evidence was on screen and unread - the same detected-but-unread class issue244 named as this repo's highest-frequency drift mechanism, and this time inside a gate rather than a report. Candidate forward control, stated not built: a check that a Decision naming a compensating control cites a TEST that exercises that control in the exempted case. Estimate 5 pts held."; }
    part lockCoverageRetroGateR1 : TestResult { :>> id = "5e5f64e1-8de2-4714-aafe-6bd3f7775d76"; :>> outcome = VerdictKind::pass; :>> judgedAgainst = "09e4e87"; :>> judgedAt = "2026-08-27"; :>> judgedBy = "claudeOpus5"; }
}
