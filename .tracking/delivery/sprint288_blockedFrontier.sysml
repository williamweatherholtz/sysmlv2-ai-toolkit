// ProjectDeliveryS288 — Sprint 288: the ready frontier stops ranking work that cannot be started
// (dcBlockedFrontier, issue112). EXECUTE. 2 pts.
package ProjectDeliveryS288 {
    private import EngineElement::*;
    private import EngineWork::*;
    private import EngineVerification::*;
    private import EngineRelationships::*;

    #CharteredBy dependency from blockedFrontierStory to d0144;

    part blockedFrontierStory : Story {
        :>> id = "0d8001ae-0814-61ae-9b3e-0000003001ae";
        :>> title = "Sprint 288: ready excludes work blocked on a pending human acceptance (2 pts)";
        :>> createdAt = "2026-08-15"; :>> createdBy = "claudeOpus5"; :>> kind = WorkKind::code; :>> priority = WorkPriority::p0; :>> owner = "claudeOpus5"; :>> estimatedPoints = 2;
    }

    action def DeliveryRunS288 {
        action storyBlockedFrontier;
        verification storyBlockedFrontierDoD : Test { :>> id = "0d8001af-0814-61af-9b3e-0000003001af"; :>> method = VerificationMethod::test; :>> procedureText = "Delivers dcBlockedFrontier; resolves issue112. FOUND BY WALKING INTO IT: `dcWorkClaim` needs a `Claim` type only a human can sign into frozen core (D0147, proposed), so it cannot be executed — and it ranked FIRST on the ready frontier. The frontier is auto-followed (D0052), so the next contributor selects it, rediscovers the same wall, and is told by a COMPUTED VIEW that the work is ready when it provably is not. That is the engine's central claim failing: state is computed so it cannot lie, and here it did. FIXED: `ready` now excludes any task carrying a `#DependsOn` edge to a Decision whose status is `proposed` — a predicate DISTINCT from supersession, because superseded means RETIRED and this means WAITING, and conflating them would either retire work that resumes the instant a human answers, or leave it scheduled. Exact rather than heuristic, and nothing is stored: accepting OR rejecting the Decision returns the item to the frontier with no further edit, which the unit test asserts by flipping the status and re-computing. VERIFIED BY READ-BACK from the computed view: ready 13 -> 12 with dcWorkClaim gone; `outstanding` UNCHANGED at 16, because blocked work is not done and reporting it as done would be the same lie in the other direction; an accepted Decision blocks nothing; conservative on a model-read error, matching `superseded_names`, so a failure cannot silently make everything ready again. clippy clean; 180 tests; validate 310 clean; 29 guards green."; }
        part storyBlockedFrontierDoDR1 : TestResult { :>> id = "0d8001b0-0814-61b0-9b3e-0000003001b0"; :>> outcome = VerdictKind::pass; :>> judgedAgainst = "21122a8"; :>> judgedAt = "2026-08-15"; :>> judgedBy = "claudeOpus5"; }
    }

    verification bfRefineGate : Test { :>> id = "0d8001b1-0814-61b1-9b3e-0000003001b1"; :>> title = "Sprint 288 refine gate (DoR)"; :>> createdAt = "2026-08-15"; :>> createdBy = "claudeOpus5"; :>> method = VerificationMethod::inspect; :>> procedureText = "DoR. Unplanned and correctly so: this was found while triaging why dcWorkClaim could not start, and D0047 requires a defect revealing a recurrable gap to become a tracked item and an automated control rather than a note in a retro. The gap recurs by construction — every frozen-core proposal from here on blocks its item the same way, and there are already two pending. CONSUMER CHECK (dorConsumer, D0144): the consumer is `orient`'s ready list and every reader of it, including me each session; the predicate had to live in the COMPUTATION rather than in the item's text, because a comment saying 'blocked' is prose state. estimatedPoints=2. DoR met."; }
    part bfRefineGateR1 : TestResult { :>> id = "0d8001b2-0814-61b2-9b3e-0000003001b2"; :>> outcome = VerdictKind::pass; :>> judgedAgainst = "21122a8"; :>> judgedAt = "2026-08-15"; :>> judgedBy = "claudeOpus5"; }

    verification bfStandupGate : Test { :>> id = "0d8001b3-0814-61b3-9b3e-0000003001b3"; :>> title = "Sprint 288 standup gate"; :>> createdAt = "2026-08-15"; :>> createdBy = "claudeOpus5"; :>> method = VerificationMethod::inspect; :>> procedureText = "Approach: MEASURE before fixing. I authored the `#DependsOn` edge first and re-read `orient` expecting the item to disappear — it did not, so the edge alone was never the fix and `ready` genuinely ignored it. Had I trusted the edge, the model would now carry an authored fact that looks like a fix and changes nothing, which is worse than the original defect because it also looks addressed. No blockers."; }
    part bfStandupGateR1 : TestResult { :>> id = "0d8001b4-0814-61b4-9b3e-0000003001b4"; :>> outcome = VerdictKind::pass; :>> judgedAgainst = "21122a8"; :>> judgedAt = "2026-08-15"; :>> judgedBy = "claudeOpus5"; }

    verification bfImplementGate : Test { :>> id = "0d8001b5-0814-61b5-9b3e-0000003001b5"; :>> title = "Sprint 288 implement gate"; :>> createdAt = "2026-08-15"; :>> createdBy = "claudeOpus5"; :>> method = VerificationMethod::test; :>> procedureText = "The decisive call was NOT reusing supersession. Widening `superseded_names` to include blocked items would have been three lines instead of thirty and would have made `dcWorkClaim` read as deliberately RETIRED — a false statement about a live, wanted item whose only obstacle is a human's answer. The two conditions also clear differently: supersession is permanent and authored, blocking clears itself when a status changes. Keeping them separate is what makes 'the item returns by itself' true, and the test asserts exactly that by flipping the Decision to accepted and re-computing rather than by inspecting the predicate."; }
    part bfImplementGateR1 : TestResult { :>> id = "0d8001b6-0814-61b6-9b3e-0000003001b6"; :>> outcome = VerdictKind::pass; :>> judgedAgainst = "21122a8"; :>> judgedAt = "2026-08-15"; :>> judgedBy = "claudeOpus5"; }

    verification bfReviewGate : Test { :>> id = "0d8001b7-0814-61b7-9b3e-0000003001b7"; :>> title = "Sprint 288 review gate"; :>> createdAt = "2026-08-15"; :>> createdBy = "claudeOpus5"; :>> method = VerificationMethod::inspect; :>> procedureText = "Reviewed. The `outstanding` count is the part worth checking and it is unchanged at 16: a blocked item is NOT done, and quietly dropping it from the outstanding count would have traded a visible lie for an invisible one — the burndown would improve because work became unstartable. `ready` narrows, `outstanding` does not, and `pendingAcceptances` names exactly what would widen it again. Those three numbers together are the honest picture; any one of them alone is not."; }
    part bfReviewGateR1 : TestResult { :>> id = "0d8001b8-0814-61b8-9b3e-0000003001b8"; :>> outcome = VerdictKind::pass; :>> judgedAgainst = "21122a8"; :>> judgedAt = "2026-08-15"; :>> judgedBy = "claudeOpus5"; }

    verification bfCloseOutGate : Test { :>> id = "0d8001b9-0814-61b9-9b3e-0000003001b9"; :>> title = "Sprint 288 closeOut gate (autonomous, D0049)"; :>> createdAt = "2026-08-15"; :>> createdBy = "claudeOpus5"; :>> method = VerificationMethod::inspect; :>> procedureText = "Autonomous closeOut (D0049). dcBlockedFrontier carries a passing DoD TestResult; issue112 resolves. Also in this commit: D0147 PROPOSED (a `Claim` type for dcWorkClaim) and issue111, which records the PATTERN behind it — two consecutive consumer checks each found a declared process step whose central data the schema cannot hold. clippy clean; 180 tests; validate 310 clean; check-engine clean; 29 guards green. No gate bypassed."; }
    part bfCloseOutGateR1 : TestResult { :>> id = "0d8001ba-0814-61ba-9b3e-0000003001ba"; :>> outcome = VerdictKind::pass; :>> judgedAgainst = "21122a8"; :>> judgedAt = "2026-08-15"; :>> judgedBy = "claudeOpus5"; }

    verification bfRetroGate : Test { :>> id = "0d8001bb-0814-61bb-9b3e-0000003001bb"; :>> title = "Sprint 288 retro gate (autonomous, D0049)"; :>> createdAt = "2026-08-15"; :>> createdBy = "claudeOpus5"; :>> method = VerificationMethod::analyze; :>> procedureText = "Autonomous retro (D0049) under D0131's retroTrack. WELL: (1) the fix was measured before being believed — authoring the edge and re-reading `orient` showed it changed nothing, so the real defect was in the computation and not in the missing fact, and trusting the edge would have left an authored fact that looks like a fix; (2) supersession was NOT widened to cover this, even though it was far cheaper, because it would have made a live item read as deliberately retired; (3) `outstanding` was checked as carefully as `ready` — narrowing the frontier without keeping the burndown honest would have traded a visible lie for an invisible one. AVOIDABLE-ISSUE 1: none this sprint, and I am recording that rather than manufacturing one. The sprint existed BECAUSE of a finding, was small, and nothing had to be redone. PATTERN WORTH NAMING ACROSS SPRINTS 287-288, recorded as issue111: two consecutive consumer checks each found a declared process step whose data the schema cannot hold — actor ROLE and the work CLAIM. Process definitions and schema were authored at different times against each other's intended futures and never reconciled, so this will keep surfacing one step at a time. I deliberately did NOT propose a guard for it: `producedArtifact` is prose, 'is this representable' has no exact predicate, and a heuristic firing on ambiguity is the issue081 dynamic. Estimate 2 pts, delivered."; }
    part bfRetroGateR1 : TestResult { :>> id = "0d8001bc-0814-61bc-9b3e-0000003001bc"; :>> outcome = VerdictKind::pass; :>> judgedAgainst = "21122a8"; :>> judgedAt = "2026-08-15"; :>> judgedBy = "claudeOpus5"; }
}
