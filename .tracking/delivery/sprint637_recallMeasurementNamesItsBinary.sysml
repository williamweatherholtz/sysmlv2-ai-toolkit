// ProjectDeliveryS637 — Sprint 637: Every run of recall_ab.py and recall_bench.py names the build of the binary it interrogated before the first case and re-reads it after the last, and prints no score over a binary it cannot identify (dcRecallMeasurementNamesItsBinary, issue406, D0417). EXECUTE: two Sensors' mechanisms gain a shared helper; no guard, hook or process changes. 2 pts.. EXECUTE. 2 pts.
package ProjectDeliveryS637 {
    private import EngineElement::*;
    private import EngineWork::*;
    private import EngineVerification::*;
    private import EngineRelationships::*;

    #CharteredBy dependency from recallMeasurementNamesItsBinaryStory to d0417;

    part recallMeasurementNamesItsBinaryStory : Story {
        :>> id = "f6bdde87-5ddd-4792-9472-0d1a3306151c";
        :>> title = "Sprint 637: Every run of recall_ab.py and recall_bench.py names the build of the binary it interrogated before the first case and re-reads it after the last, and prints no score over a binary it cannot identify (dcRecallMeasurementNamesItsBinary, issue406, D0417). EXECUTE: two Sensors' mechanisms gain a shared helper; no guard, hook or process changes. 2 pts. (2 pts)";
        :>> createdAt = "2026-09-09"; :>> createdBy = "claudeOpus5"; :>> kind = WorkKind::code; :>> priority = WorkPriority::p0; :>> owner = "claudeOpus5"; :>> estimatedPoints = 2;
    }

    action def DeliveryRunS637 {
        action storyRecallMeasurementNamesItsBinary;
        verification storyRecallMeasurementNamesItsBinaryDoD : Test { :>> id = "14af4832-315c-497d-978e-9d518a908efc"; :>> method = VerificationMethod::test; :>> procedureText = "DELIVERED (dcRecallMeasurementNamesItsBinary, resolves issue406 through that item): .engine/tools/recall_binary.py identifies a binary through `<path> version` and returns `keel <ver> build <commit[+dirty]>` or raises BinaryUnavailable naming the reason; Run.header prints `binary : <path> = <line>` or aborts with `ABORT: no measurement - <reason>` and exit 2; Run.footer re-reads and prints `unchanged through the run (...)` or disowns the numbers and exits 3. Both harnesses call header before their first case and footer after their last line; KEEL_BENCH_BIN overrides the path. PROBED (D0388) before the harnesses were run: python .engine/tools/recall_binary.py --probe -> known-positive the real binary yields `keel 0.4.1 build df7a54e+dirty`, known-negative ./target/release/no-such-keel.exe raises `binary absent`; both hold. VERIFIED live on tree 872497f: KEEL_BENCH_BIN=./target/release/no-such-keel.exe python .engine/tools/recall_ab.py -> `ABORT: no measurement - binary absent: ./target/release/no-such-keel.exe does not exist`, exit 2, no 0/8 printed; the same for recall_bench.py --cases 3, exit 2, no 0/3 printed; python .engine/tools/recall_ab.py -> first line `binary : ./target/release/keel.exe = keel 0.4.1 build df7a54e+dirty`, 7/8 ON, 0/8 OFF, mean 1989 ms, last line `binary : unchanged through the run (keel 0.4.1 build df7a54e+dirty)`, exit 0; python .engine/tools/recall_bench.py --cases 5 -> the same header and footer around the summary, exit 0; recall_bench.py --probe still holds all 6 cases. The two Sensor records in engine-instruments.sysml name issue406 among their known failure modes."; }
        // RAN: python .engine/tools/recall_binary.py --probe -> both cases hold (keel 0.4.1 build df7a54e+dirty; no-such-keel.exe -> binary absent); python .engine/tools/recall_ab.py -> header binary line, 7/8 ON 0/8 OFF, footer unchanged through the run, exit 0; KEEL_BENCH_BIN=./target/release/no-such-keel.exe on recall_ab.py and recall_bench.py --cases 3 -> ABORT: no measurement - binary absent, exit 2, no score printed; recall_bench.py --cases 5 -> header and footer around the summary, exit 0; recall_bench.py --probe -> all 6 cases hold
        part storyRecallMeasurementNamesItsBinaryDoDR1 : TestResult { :>> id = "914ee707-b86c-4856-a19c-174e1d3cea3f"; :>> outcome = VerdictKind::pass; :>> judgedAgainst = "872497f"; :>> judgedAt = "2026-09-09"; :>> judgedBy = "claudeOpus5"; }
    }

    verification recallMeasurementNamesItsBinaryRefineGate : Test { :>> id = "7e997df9-0609-4140-804c-ed96d65d54ba"; :>> title = "Sprint 637 refine gate (DoR)"; :>> createdAt = "2026-09-09"; :>> createdBy = "claudeOpus5"; :>> method = VerificationMethod::inspect; :>> procedureText = "Definition of Ready: dcRecallMeasurementNamesItsBinary at the head of keel whats-next . after 872497f; its DoD names the property (a measurement names the image that produced it), the DO (capture keel version before the first case, print it in every header, abort with a named reason when the binary cannot be interrogated) and the VERIFY triple (both harnesses print the build line; an absent binary aborts non-zero instead of printing 0/50; the next recall Decision carries the build line); two bench scripts and one new helper, no fork; 2 points."; }
    // RAN: sprint 637 Refine: keel validate . / check-engine . / gate --fast . clean on 872497f; recall_binary.py --probe both cases hold; recall_ab.py header+footer 7/8 exit 0; KEEL_BENCH_BIN=absent -> ABORT exit 2 on both harnesses
    part recallMeasurementNamesItsBinaryRefineGateR1 : TestResult { :>> id = "0bd9a741-9287-4df2-886f-8576d99e1f7c"; :>> outcome = VerdictKind::pass; :>> judgedAgainst = "872497f"; :>> judgedAt = "2026-09-09"; :>> judgedBy = "claudeOpus5"; }
    verification recallMeasurementNamesItsBinaryStandupGate : Test { :>> id = "7a1cd770-49fa-4686-a41e-ea3bfc5afb93"; :>> title = "Sprint 637 standup gate"; :>> createdAt = "2026-09-09"; :>> createdBy = "claudeOpus5"; :>> method = VerificationMethod::inspect; :>> procedureText = "No blocker. One point settled at design: the header alone cannot see a relink that finishes mid-run - which is the case that produced 6/8 - so the helper re-reads the binary in a footer and exits 3 when the build changed, disowning the numbers rather than letting them stand under a header that no longer describes them."; }
    // RAN: sprint 637 Standup: keel validate . / check-engine . / gate --fast . clean on 872497f; recall_binary.py --probe both cases hold; recall_ab.py header+footer 7/8 exit 0; KEEL_BENCH_BIN=absent -> ABORT exit 2 on both harnesses
    part recallMeasurementNamesItsBinaryStandupGateR1 : TestResult { :>> id = "7615637c-19bd-4e7b-b5a0-f629ff5392b8"; :>> outcome = VerdictKind::pass; :>> judgedAgainst = "872497f"; :>> judgedAt = "2026-09-09"; :>> judgedBy = "claudeOpus5"; }
    verification recallMeasurementNamesItsBinaryImplementGate : Test { :>> id = "e43868d4-35d0-418b-b15f-53d8a42d17f2"; :>> title = "Sprint 637 implement gate"; :>> createdAt = "2026-09-09"; :>> createdBy = "claudeOpus5"; :>> method = VerificationMethod::test; :>> procedureText = "recall_binary.py written with the Write tool (its body carries a Windows path, D0309): identify, BinaryUnavailable, Run.header / Run.footer, probe, KEEL_BENCH_BIN. Both harnesses wired through textpatch (patch637.py: import block, KEEL from the helper, header before the first case, footer after the last print in each exit path, one docstring paragraph each). The two Sensor comments patched through textpatch (docsync637.py)."; }
    // RAN: sprint 637 Implement: keel validate . / check-engine . / gate --fast . clean on 872497f; recall_binary.py --probe both cases hold; recall_ab.py header+footer 7/8 exit 0; KEEL_BENCH_BIN=absent -> ABORT exit 2 on both harnesses
    part recallMeasurementNamesItsBinaryImplementGateR1 : TestResult { :>> id = "7e55af67-ed9c-4f01-94b7-2327fa808a6b"; :>> outcome = VerdictKind::pass; :>> judgedAgainst = "872497f"; :>> judgedAt = "2026-09-09"; :>> judgedBy = "claudeOpus5"; }
    verification recallMeasurementNamesItsBinaryReviewGate : Test { :>> id = "4a5ca4e0-907b-45e8-abd9-bbca42e1d655"; :>> title = "Sprint 637 review gate — three passes per D0172"; :>> createdAt = "2026-09-09"; :>> createdBy = "claudeOpus5"; :>> method = VerificationMethod::inspect; :>> procedureText = "Three passes per D0172: (1) the helper is probed on its known-positive and known-negative before either harness is run; (2) the live runs cover the DoD's VERIFY on both harnesses in both directions - the real binary prints header and footer, the absent one aborts before any number; (3) recall_ab.py's 7/8 and recall_bench.py --probe are unchanged by the wiring, so the refactor moved no measurement."; }
    // RAN: sprint 637 Review: keel validate . / check-engine . / gate --fast . clean on 872497f; recall_binary.py --probe both cases hold; recall_ab.py header+footer 7/8 exit 0; KEEL_BENCH_BIN=absent -> ABORT exit 2 on both harnesses
    part recallMeasurementNamesItsBinaryReviewGateR1 : TestResult { :>> id = "a5dde9f6-b6d4-44a7-87c4-a52efed1ff5b"; :>> outcome = VerdictKind::pass; :>> judgedAgainst = "872497f"; :>> judgedAt = "2026-09-09"; :>> judgedBy = "claudeOpus5"; }
    verification recallMeasurementNamesItsBinaryCloseOutGate : Test { :>> id = "a5c9d205-8b78-4fe7-97ff-29f8bb0751cd"; :>> title = "Sprint 637 closeOut gate (autonomous, D0049)"; :>> createdAt = "2026-09-09"; :>> createdBy = "claudeOpus5"; :>> method = VerificationMethod::inspect; :>> procedureText = "keel validate . clean, keel check-engine . clean, keel gate --fast clean; dcRecallMeasurementNamesItsBinaryDoD stamped naming the probe and the live header, footer and ABORT lines; issue406 resolved through the item."; }
    // RAN: sprint 637 CloseOut: keel validate . / check-engine . / gate --fast . clean on 872497f; recall_binary.py --probe both cases hold; recall_ab.py header+footer 7/8 exit 0; KEEL_BENCH_BIN=absent -> ABORT exit 2 on both harnesses
    part recallMeasurementNamesItsBinaryCloseOutGateR1 : TestResult { :>> id = "b54ea77b-9d10-414e-b057-f58867962c70"; :>> outcome = VerdictKind::pass; :>> judgedAgainst = "872497f"; :>> judgedAt = "2026-09-09"; :>> judgedBy = "claudeOpus5"; }
    verification recallMeasurementNamesItsBinaryRetroGate : Test { :>> id = "6af966ec-5b64-4c6d-9b49-e44e09e8485c"; :>> title = "Sprint 637 retro gate (autonomous, D0049)"; :>> createdAt = "2026-09-09"; :>> createdBy = "claudeOpus5"; :>> method = VerificationMethod::analyze; :>> procedureText = "Avoidable-issue scan: the mid-relink case (the footer's exit 3) was exercised only by construction, not live - forcing a relink under a 75-second run is a timing race, and the footer's comparison is a string equality on the line the header already proved it can read. Stated as a residual, not an item: the header path is tested both ways, the footer path shares its reader. The DoD's third VERIFY clause - the next recall Decision carries the build line - is satisfied by construction from now on and first observed when the next such Decision is recorded; d0417 itself cites the line its own runs printed. No new item: the residual is the footer path of dcRecallMeasurementNamesItsBinary, the item that resolves issue406, and stays with it."; }
    // RAN: sprint 637 Retro: keel validate . / check-engine . / gate --fast . clean on 872497f; recall_binary.py --probe both cases hold; recall_ab.py header+footer 7/8 exit 0; KEEL_BENCH_BIN=absent -> ABORT exit 2 on both harnesses
    part recallMeasurementNamesItsBinaryRetroGateR1 : TestResult { :>> id = "1f9cfd6c-b9c9-4f75-bebb-75f82ef78876"; :>> outcome = VerdictKind::pass; :>> judgedAgainst = "872497f"; :>> judgedAt = "2026-09-09"; :>> judgedBy = "claudeOpus5"; }
}
