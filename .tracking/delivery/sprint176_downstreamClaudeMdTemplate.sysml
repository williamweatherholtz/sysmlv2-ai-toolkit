// ProjectDeliveryS176 — Sprint 176: downstreamClaudeMdTemplate (issue057, field defect).
// keel init shipped the SELF-BUILD CLAUDE.md ('this repo IS a work-tracking engine'), so downstream
// projects thought they were keel. FIX: a new downstream template (keel-cli/assets/claude-md-template.md)
// framing the project as TRACKED BY keel + carrying the D0106 parse-first discipline; main.rs:45 now
// include_str!s the template, not ../../CLAUDE.md. Regression test locks it (D0047). EXECUTE. 1 pt. AUTONOMOUS (D0049).
package ProjectDeliveryS176 {
    private import EngineElement::*;
    private import EngineWork::*;
    private import EngineVerification::*;
    private import EngineRelationships::*;

    #CharteredBy dependency from downstreamTemplateStory to issue057;

    part downstreamTemplateStory : Story {
        :>> id = "63940516-2c7d-4e8f-c176-51627384c001";
        :>> title = "Sprint 176: downstreamClaudeMdTemplate (1 pt) - keel init ships a 'tracked BY keel' CLAUDE.md, not the self-build's (issue057)";
        :>> createdAt = "2026-07-02"; :>> createdBy = "wweatherholtz"; :>> kind = WorkKind::code; :>> priority = WorkPriority::p1; :>> owner = "claudeOpus"; :>> estimatedPoints = 1;
    }

    action def DeliveryRunS176 {
        action storyDownstreamTemplate;
        verification storyDownstreamTemplateDoD : Test { :>> id = "63940516-2c7d-4e8f-c176-51627384c002"; :>> method = VerificationMethod::test; :>> procedureText = "Resolves issue057 (field defect from keel in other projects). Authored keel-cli/assets/claude-md-template.md — a DOWNSTREAM CLAUDE.md framing the new project as TRACKED BY keel (not 'is keel'): text-is-truth invariants, the D0106 parse-first discipline (Parsed: block + route + sign-off-as-gate), .engine as read-only tool (.engine/reference for architecture), validation commands — WITHOUT self-build specifics (no self-build backlog/decisions/kernel paths). main.rs:45 now include_str!(../assets/claude-md-template.md); cmd_init writes the TEMPLATE. VERIFIED LIVE: `keel init <tmp>` -> CLAUDE.md head 'This project is tracked by keel'; grep 'is a work-tracking engine'=0, 'tracked by keel'=1; fresh project `keel validate`=clean. D0047 permanent control: unit test init_ships_downstream_claude_md_not_self_build (asserts 'tracked by keel' present, 'is a work-tracking engine' absent, 'Parsed:' present). clippy -D warnings clean; cargo test (1 bin + 29 lib incl the new test) green; keel validate + guard all (14) green."; }
        part storyDownstreamTemplateDoDR1 : TestResult { :>> id = "63940516-2c7d-4e8f-c176-51627384c003"; :>> outcome = VerdictKind::pass; :>> judgedAgainst = "c8cf7d3"; :>> judgedAt = "2026-07-02"; :>> judgedBy = "claudeOpus"; }
    }

    verification downstreamTemplateRefineGate : Test { :>> id = "63940516-2c7d-4e8f-c176-51627384c004"; :>> title = "Sprint 176 refine gate (DoR)"; :>> createdAt = "2026-07-02"; :>> createdBy = "claudeOpus"; :>> method = VerificationMethod::inspect; :>> procedureText = "DoR: issue057 (High, field defect). Author a downstream CLAUDE.md template + repoint init + regression test. estimatedPoints=1. #CharteredBy issue057. DoR met."; }
    part downstreamTemplateRefineGateR1 : TestResult { :>> id = "63940516-2c7d-4e8f-c176-51627384c005"; :>> outcome = VerdictKind::pass; :>> judgedAgainst = "c8cf7d3"; :>> judgedAt = "2026-07-02"; :>> judgedBy = "claudeOpus"; }
    verification downstreamTemplateStandupGate : Test { :>> id = "63940516-2c7d-4e8f-c176-51627384c006"; :>> title = "Sprint 176 standup gate"; :>> createdAt = "2026-07-02"; :>> createdBy = "claudeOpus"; :>> method = VerificationMethod::inspect; :>> procedureText = "Approach: write the downstream template asset; change main.rs const CLAUDE_MD include_str! target; rebuild; live-test init in a temp dir; add a regression unit test (D0047). No blockers (killed a lingering keel.exe holding the binary lock)."; }
    part downstreamTemplateStandupGateR1 : TestResult { :>> id = "63940516-2c7d-4e8f-c176-51627384c007"; :>> outcome = VerdictKind::pass; :>> judgedAgainst = "c8cf7d3"; :>> judgedAt = "2026-07-02"; :>> judgedBy = "claudeOpus"; }
    verification downstreamTemplateImplementGate : Test { :>> id = "63940516-2c7d-4e8f-c176-51627384c008"; :>> title = "Sprint 176 implement gate"; :>> createdAt = "2026-07-02"; :>> createdBy = "claudeOpus"; :>> method = VerificationMethod::test; :>> procedureText = "Template authored; main.rs repointed; rebuilt. LIVE: keel init yields 'tracked by keel' CLAUDE.md (self-build phrase count 0), fresh project validates clean. clippy -D warnings clean; cargo test incl init_ships_downstream_claude_md_not_self_build pass; keel validate + guard all green."; }
    part downstreamTemplateImplementGateR1 : TestResult { :>> id = "63940516-2c7d-4e8f-c176-51627384c009"; :>> outcome = VerdictKind::pass; :>> judgedAgainst = "c8cf7d3"; :>> judgedAt = "2026-07-02"; :>> judgedBy = "claudeOpus"; }
    verification downstreamTemplateReviewGate : Test { :>> id = "63940516-2c7d-4e8f-c176-51627384c00a"; :>> title = "Sprint 176 review gate"; :>> createdAt = "2026-07-02"; :>> createdBy = "claudeOpus"; :>> method = VerificationMethod::inspect; :>> procedureText = "Reviewed. The template correctly separates 'tracked BY keel' (downstream) from 'IS keel' (self-build), carries the D0106 parse-first discipline so new projects inherit strict process-boundedness, and points at .engine/reference for architecture per D0093. The self-build repo keeps its own CLAUDE.md un-shipped. Regression test locks the class (D0047). Clean."; }
    part downstreamTemplateReviewGateR1 : TestResult { :>> id = "63940516-2c7d-4e8f-c176-51627384c00b"; :>> outcome = VerdictKind::pass; :>> judgedAgainst = "c8cf7d3"; :>> judgedAt = "2026-07-02"; :>> judgedBy = "claudeOpus"; }
    verification downstreamTemplateCloseOutGate : Test { :>> id = "63940516-2c7d-4e8f-c176-51627384c00c"; :>> title = "Sprint 176 closeOut gate (autonomous, D0049)"; :>> createdAt = "2026-07-02"; :>> createdBy = "claudeOpus"; :>> method = VerificationMethod::inspect; :>> procedureText = "Autonomous closeOut (D0049): DoD pass; issue057 resolved (downstream projects are now framed as tracked BY keel). clippy + cargo test + keel validate + guard all green. Self-evidencing (D0051)."; }
    part downstreamTemplateCloseOutGateR1 : TestResult { :>> id = "63940516-2c7d-4e8f-c176-51627384c00d"; :>> outcome = VerdictKind::pass; :>> judgedAgainst = "c8cf7d3"; :>> judgedAt = "2026-07-02"; :>> judgedBy = "claudeOpus"; }
    verification downstreamTemplateRetroGate : Test { :>> id = "63940516-2c7d-4e8f-c176-51627384c00e"; :>> title = "Sprint 176 retro gate (autonomous, D0049)"; :>> createdAt = "2026-07-02"; :>> createdBy = "claudeOpus"; :>> method = VerificationMethod::analyze; :>> procedureText = "Autonomous retro (D0049). WELL: a real field defect (downstream projects mis-framed as keel) closed cleanly with a permanent regression test; the new template also propagates the just-accepted D0106 discipline to every future project, so the fix compounds. AVOIDABLE-ISSUE SCAN: the avoidable root was shipping the self-build CLAUDE.md via include_str!(../../CLAUDE.md) — masked because the self-build repo IS keel, so it read fine at home; LESSON (generalizes issue053): test the SHIPPED artifact as an external user (keel init in a clean dir), not just in the self-build repo; a lingering keel.exe held the binary lock (kill stale processes before a release build). Estimate 1 pt held. Remaining unblocked: businessArchSkillAndWorkflowGuard, serveBusinessNeedsView; D0105 frozen-core still awaits its own sign-off."; }
    part downstreamTemplateRetroGateR1 : TestResult { :>> id = "63940516-2c7d-4e8f-c176-51627384c00f"; :>> outcome = VerdictKind::pass; :>> judgedAgainst = "c8cf7d3"; :>> judgedAt = "2026-07-02"; :>> judgedBy = "claudeOpus"; }
}
