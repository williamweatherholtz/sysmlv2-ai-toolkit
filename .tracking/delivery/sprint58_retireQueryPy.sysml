// =====================================================================
// ProjectDeliveryS58 — Sprint 58: retireQueryPy (D0074 migration M4; closes issue012).
// Story: retire query.py + the six python forward-guard scripts + parity_check + the query.py
//        unit test, now that all views (M2.2) + guards (M3) are Rust with proven parity. Rewire
//        the pre-commit hook to `sysmlv2 guard`; make the Rust path the SOLE gate. doc-sync the
//        engine docs + skills. report.py is UNTOUCHED (already sysmlv2-sourced, not query.py).
// Total: 5 pts  Ceremony: AUTONOMOUS (D0049).
// =====================================================================
package ProjectDeliveryS58 {
    private import EngineElement::*;
    private import EngineWork::*;
    private import EngineVerification::*;
    private import EngineRelationships::*;

    #CharteredBy dependency from retireQueryPyStory to d0074;

    part retireQueryPyStory : Story {
        :>> id = "63940516-2c7d-4e8f-b058-516273849b01";
        :>> title = "Sprint 58: retireQueryPy (5 pts) — delete query.py + python guards + parity_check; rewire hook to sysmlv2 guard; sole Rust gate; closes issue012; D0074 M4";
        :>> createdAt = "2026-06-20";
        :>> createdBy = "wweatherholtz";
        :>> kind = WorkKind::code;
        :>> priority = WorkPriority::p1;
        :>> owner = "claudeOpus";
        :>> estimatedPoints = 5;
    }

    action def DeliveryRunS58 {
        action storyRetireQueryPy;
        verification storyRetireQueryPyDoD : Test { :>> id = "63940516-2c7d-4e8f-b058-516273849b02"; :>> method = VerificationMethod::test; :>> procedureText = "retireQueryPyDoD: DELETE .engine/tools/query.py + the six validate_{actors,ceremony,charter,sprint_coverage,acceptance_events,process_change}.py + parity_check.py + _test_suspect.py. REWIRE .githooks/pre-commit: the five python guard calls -> `sysmlv2 guard <name>` (kernel validators for .engine schema/workflows/instances UNCHANGED; sysmlv2 validate for .tracking unchanged). DOC-SYNC CLAUDE.md sec1/sec5 + usage.md + the affected skills so the Rust path (sysmlv2 validate + sysmlv2 guard) is the SOLE gate (no query.py / python-guard references as live tools). report.py UNTOUCHED (already reads sysmlv2 + files, never query.py). Close issue012 (append RESOLVED). VERIFY: `sysmlv2 guard` ALL PASS, `sysmlv2 validate` clean, kernel validators still run for .engine; a fresh commit passes the rewired hook. clippy + cargo test green."; }
        part storyRetireQueryPyDoDR1 : TestResult { :>> id = "ed837498-d29d-47d8-a993-bde6d5f34850"; :>> outcome = VerdictKind::pass; :>> judgedAgainst = "0d60d03"; :>> judgedAt = "2026-06-20"; :>> judgedBy = "claudeOpus"; }
    }

    verification retireQueryPyRefineGate : Test { :>> id = "63940516-2c7d-4e8f-b058-516273849b03"; :>> title = "Sprint 58 refine gate (DoR)"; :>> createdAt = "2026-06-20"; :>> createdBy = "claudeOpus"; :>> method = VerificationMethod::inspect; :>> procedureText = "DoR: M4 — the views (M2.2) + all six guards (M3) are Rust with proven parity, so query.py + the python guards + parity_check are dead weight. INVESTIGATION (refine): the only live query.py importers are _test_suspect.py + parity_check.py (both deleted); report.py is ALREADY independent of query.py (sysmlv2.exe orient + direct file reads — verified by running it, 164KB HTML, exit 0), so the earlier 'port report.py' concern was a grep false-positive (JS querySelectorAll) — NO report.py port needed. The pre-commit hook (active, core.hooksPath=.githooks) calls 5 python guards -> rewire to sysmlv2 guard. Historical sprint/decision files are EVIDENCE (D0067) — not rewritten. issue012 closed by deletion. estimatedPoints=5. #CharteredBy to d0074. DoD accepted."; }
    part retireQueryPyRefineGateR1 : TestResult { :>> id = "63940516-2c7d-4e8f-b058-516273849b04"; :>> outcome = VerdictKind::pass; :>> judgedAgainst = "0d60d03"; :>> judgedAt = "2026-06-20"; :>> judgedBy = "claudeOpus"; }

    verification retireQueryPyStandupGate : Test { :>> id = "63940516-2c7d-4e8f-b058-516273849b05"; :>> title = "Sprint 58 standup gate"; :>> createdAt = "2026-06-20"; :>> createdBy = "claudeOpus"; :>> method = VerificationMethod::inspect; :>> procedureText = "Refine passed. Approach: (1) rewire .githooks/pre-commit FIRST (python guards -> sysmlv2 guard) so the rewired hook is what runs at this sprint's commit; keep kernel validators (schema/workflows/instances) + sysmlv2 validate. (2) git rm the 9 python files (query.py, 6 guards, parity_check, _test_suspect). (3) doc-sync: CLAUDE.md sec1/sec5, usage.md, skills (architectural-critique/engine-triage/sprint-planning/sprint-review/sprint-retro/test-verify/status-report), README/.engine README/.tracking README/computed-state.md — swap live query.py/validate_*.py invocations for sysmlv2 equivalents; leave historical sprint/decision files alone. (4) append RESOLVED to issue012. VERIFY: sysmlv2 guard ALL PASS + validate clean + the commit's own hook run is green + clippy/cargo test. No blockers."; }
    part retireQueryPyStandupGateR1 : TestResult { :>> id = "63940516-2c7d-4e8f-b058-516273849b06"; :>> outcome = VerdictKind::pass; :>> judgedAgainst = "0d60d03"; :>> judgedAt = "2026-06-20"; :>> judgedBy = "claudeOpus"; }

    verification retireQueryPyImplementGate : Test { :>> id = "63940516-2c7d-4e8f-b058-516273849b07"; :>> title = "Sprint 58 implement gate"; :>> createdAt = "2026-06-20"; :>> createdBy = "claudeOpus"; :>> method = VerificationMethod::test; :>> procedureText = "DELETED 9 python files (query.py, validate_{actors,ceremony,charter,sprint_coverage,acceptance_events,process_change}.py, parity_check.py, _test_suspect.py). REWIRED .githooks/pre-commit: the five python guard calls -> sysmlv2 guard <name> (kernel validators for .engine schema/workflows/instances + sysmlv2 validate for .tracking UNCHANGED; guard_run skips gracefully if the binary is unbuilt). DOC-SYNCED: CLAUDE.md sec1/sec5/sec3b/sec3c/sec3f/sec6, usage.md, README.md, .engine/README.md, .tracking/README.md, computed-state.md, skills (architectural-critique/test-verify/engine-triage/sprint-planning/sprint-review) — Rust path is the SOLE gate; no live query.py/python-guard references. report.py UNTOUCHED + verified independent (164KB HTML, exit 0). Closed issue012 (RESOLVED clause); recorded issue025 (7 unported subcommands, honestly tracked). VERIFY: sysmlv2 validate clean (68), sysmlv2 guard ALL PASS, cargo build green. Historical sprint/decision/design files left intact (D0067 evidence)."; }
    part retireQueryPyImplementGateR1 : TestResult { :>> id = "63940516-2c7d-4e8f-b058-516273849b08"; :>> outcome = VerdictKind::pass; :>> judgedAgainst = "0d60d03"; :>> judgedAt = "2026-06-20"; :>> judgedBy = "claudeOpus"; }

    verification retireQueryPyReviewGate : Test { :>> id = "63940516-2c7d-4e8f-b058-516273849b09"; :>> title = "Sprint 58 review gate"; :>> createdAt = "2026-06-20"; :>> createdBy = "claudeOpus"; :>> method = VerificationMethod::inspect; :>> procedureText = "Diff reviewed. The deletion is clean: only _test_suspect + parity_check imported query.py (both deleted); report.py is independent (sysmlv2 orient + file reads — verified running). The hook rewire preserves the kernel SysML validators (NOT retired by M4) and swaps only the six forward guards to `sysmlv2 guard`; the rewired hook is exercised by this very commit (eating our own dogfood). The earlier report.py 'port' concern was a grep false-positive (JS querySelectorAll) — caught in refine, so no wasted port. The seven unported query.py subcommands (workflows/trace/trace-need/item/outstanding/downstream/viewpoints-listing) are honestly recorded as issue025, not silently dropped (D0018). M4 COMPLETE — query.py fully retired, Rust is the sole authority + gate; issue012 closed. The full D0074 migration (M1 view executor -> M2 views -> M3 guards -> M4 retirement) is DONE."; }
    part retireQueryPyReviewGateR1 : TestResult { :>> id = "63940516-2c7d-4e8f-b058-516273849b0a"; :>> outcome = VerdictKind::pass; :>> judgedAgainst = "0d60d03"; :>> judgedAt = "2026-06-20"; :>> judgedBy = "claudeOpus"; }

    verification retireQueryPyCloseOutGate : Test { :>> id = "63940516-2c7d-4e8f-b058-516273849b0b"; :>> title = "Sprint 58 closeOut gate (autonomous, D0049)"; :>> createdAt = "2026-06-20"; :>> createdBy = "claudeOpus"; :>> method = VerificationMethod::inspect; :>> procedureText = "Autonomous closeOut (D0049): storyRetireQueryPy + backlog retireQueryPy DoDs recorded pass; sysmlv2 validate clean + sysmlv2 guard ALL PASS + cargo build green; the rewired pre-commit hook is exercised by this commit; issue012 closed, issue025 recorded. Self-evidencing (D0051). M4 + the full D0074 migration COMPLETE."; }
    part retireQueryPyCloseOutGateR1 : TestResult { :>> id = "63940516-2c7d-4e8f-b058-516273849b0c"; :>> outcome = VerdictKind::pass; :>> judgedAgainst = "0d60d03"; :>> judgedAt = "2026-06-20"; :>> judgedBy = "claudeOpus"; }

    verification retireQueryPyRetroGate : Test { :>> id = "63940516-2c7d-4e8f-b058-516273849b0d"; :>> title = "Sprint 58 retro gate (autonomous, D0049)"; :>> createdAt = "2026-06-20"; :>> createdBy = "claudeOpus"; :>> method = VerificationMethod::analyze; :>> procedureText = "Autonomous retro (D0049). WELL: refine-as-investigation paid off twice — it caught that report.py was ALREADY query-independent (a grep false-positive on JS querySelectorAll), saving a needless port, AND surfaced that 7 query.py subcommands were never ported (recorded as issue025 rather than silently dropped). Rewiring the hook FIRST meant this sprint's own commit dogfoods the Rust-only gate. CAUGHT (the avoidable issue): I nearly accepted a 'port report.py' scope based on a grep match without reading the code — the lesson is verify a dependency by reading the source, not trusting a substring grep; no new tracked item (the verify-before-acting discipline already covers it, and issue025 captures the concrete gap). Estimate 5 pts held. M4 COMPLETE: query.py + the 6 python guards + parity_check deleted, the Rust toolchain (sysmlv2 validate + guard) is the SOLE gate, issue012 closed. The entire D0074 full-rust migration (M1->M2->M3->M4) is DONE. Possible follow-ups (not chartered): re-add the issue025 views as TOML/Rust if needed; port report.py's rendering deeper onto sysmlv2 view output."; }
    part retireQueryPyRetroGateR1 : TestResult { :>> id = "63940516-2c7d-4e8f-b058-516273849b0e"; :>> outcome = VerdictKind::pass; :>> judgedAgainst = "0d60d03"; :>> judgedAt = "2026-06-20"; :>> judgedBy = "claudeOpus"; }
}
