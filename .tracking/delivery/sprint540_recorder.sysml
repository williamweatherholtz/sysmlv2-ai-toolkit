// ProjectDeliveryS540 — Sprint 540: the recorder of an acceptance is provenance distinct from the judge. EXECUTE. 2 pts.
package ProjectDeliveryS540 {
    private import EngineElement::*;
    private import EngineWork::*;
    private import EngineVerification::*;
    private import EngineRelationships::*;

    #CharteredBy dependency from recorderStory to d0299;

    part recorderStory : Story {
        :>> id = "c8bad6a8-a9fe-4c4c-8ee8-81c172846d74";
        :>> title = "Sprint 540: every accept path stamps who RECORDED beside who JUDGED, and the delegated-substance rule stops demanding the human quote themselves (2 pts)";
        :>> createdAt = "2026-09-04"; :>> createdBy = "claudeOpus5"; :>> kind = WorkKind::code; :>> priority = WorkPriority::p0; :>> owner = "claudeOpus5"; :>> estimatedPoints = 2;
    }

    action def DeliveryRunS540 {
        action storyRecorder;
        verification storyRecorderDoD : Test { :>> id = "2c0bc4ba-9238-4621-8a30-035d10538097"; :>> method = VerificationMethod::test; :>> procedureText = "DELIVERED BACKLOG ITEMS: dcRecorderIsDistinctFromJudge (resolves issue287). DONE: accept_decision takes recorded_by and writes createdBy on the acceptance result - no schema change, TestResult inherits it; console = judge, keel accept = judge or (--by) the session actor with an unbound-actor refusal, standing-consent auto-accept = the recording actor; acceptQuotesDelegatedWords is vacuous when createdBy equals judgedBy and reads the note otherwise; records with no createdBy stay delegated. VERIFY: five-case unit test (self-recorded passes unquoted; AI-delegated unquoted fails; AI-delegated quoted passes; unstamped unquoted fails; unstamped console gesture passes); D0299's own auto-accept record carries judgedBy wweatherholtz and createdBy claudeOpus5 and passes on its quote; 473 tests, clippy clean, validate clean."; }
        // RAN: cargo test --release 473/0; clippy 0; keel record decision --from d0299.md -> R1 line judgedBy wweatherholtz createdBy claudeOpus5; keel validate . clean; keel guard . ALL PASS with confirmation-authenticity sourcing the rule
        part storyRecorderDoDR1 : TestResult { :>> id = "100ed1f2-2f64-4925-8bbe-330c16072b5a"; :>> outcome = VerdictKind::pass; :>> judgedAgainst = "d82c512"; :>> judgedAt = "2026-09-04"; :>> judgedBy = "claudeOpus5"; }
    }

    verification recorderRefineGate : Test { :>> id = "9453a5bd-69a6-4849-b6a7-ed550dfe2846"; :>> title = "Sprint 540 refine gate (DoR)"; :>> createdAt = "2026-09-04"; :>> createdBy = "claudeOpus5"; :>> method = VerificationMethod::inspect; :>> procedureText = "READY once the schema question was answered by reading element.sysml: createdBy is already on Element with a comment saying TestResult uses judgedBy instead - the attribute was there for a second fact all along, so this was a process change, not a schema fork."; }
    verification recorderStandupGate : Test { :>> id = "b0ccdf0b-68d5-42e4-903a-7de37b58c1c4"; :>> title = "Sprint 540 standup gate"; :>> createdAt = "2026-09-04"; :>> createdBy = "claudeOpus5"; :>> method = VerificationMethod::inspect; :>> procedureText = "ONE CHOICE: unstamped records are read as DELEGATED. The other reading - absent recorder means self-recorded - would have retroactively excused every past AI-recorded acceptance from the quote rule; this reading changes nothing about them, because they already pass. Second: --by is the definition of recording on someone's behalf, so it resolves the session's own actor and refuses when none is bound - provenance is never defaulted (D0129), even at the cost of a new refusal."; }
    verification recorderImplementGate : Test { :>> id = "a1ef3e1c-9763-4829-b9f1-187de2738c97"; :>> title = "Sprint 540 implement gate"; :>> createdAt = "2026-09-04"; :>> createdBy = "claudeOpus5"; :>> method = VerificationMethod::test; :>> procedureText = "RAN: one signature change, four call sites, three existing tests re-argued, one new five-case test; built clean first time. The first live record under the new path was D0299 itself: delegated by construction, and it passed on the standing-consent quote - which is exactly the case the rule exists for."; }
    verification recorderReviewGate : Test { :>> id = "4a564dfb-7a64-4745-b82d-84e08f86ff71"; :>> title = "Sprint 540 review gate — three passes per D0172"; :>> createdAt = "2026-09-04"; :>> createdBy = "claudeOpus5"; :>> method = VerificationMethod::inspect; :>> procedureText = "THREE PASSES. (1) CAN AN AGENT FAKE SELF-RECORDING: only by passing --by with its own id as the judge, which refuse_ai_judgment already rejects (an AI cannot be the judge), or by running keel accept with no --by as a bound HUMAN actor - which is the actor-binding trust boundary every write already rests on (D0129). (2) ARE THE HUMAN'S WORDS TOUCHED: no - the console appends a channel citation, the CLI writes the note as given; the test asserts the note passes through both paths verbatim. (3) WHAT IS NOT BUILT: a lens that counts self-recorded against delegated acceptances; D0299 says so."; }
    verification recorderCloseOutGate : Test { :>> id = "3ae02d14-bb19-4c22-b4da-1c06ed29daa9"; :>> title = "Sprint 540 closeOut gate (autonomous, D0049)"; :>> createdAt = "2026-09-04"; :>> createdBy = "claudeOpus5"; :>> method = VerificationMethod::inspect; :>> procedureText = "CLOSED. issue287 resolves; CLAUDE.md's acceptance bullet names the recorder."; }
    verification recorderRetroGate : Test { :>> id = "3719d58f-9778-48f8-88ed-f8ee6e8adab1"; :>> title = "Sprint 540 retro gate (autonomous, D0049)"; :>> createdAt = "2026-09-04"; :>> createdBy = "claudeOpus5"; :>> method = VerificationMethod::analyze; :>> procedureText = "no new item - already tracked: the self-recorded/delegated lens is a consequence stated in d0299 and not owed until someone asks for it; the human-is-not-a-process-component rule (D0204) that this defect violated is already a Decision, and this sprint is one more instance of it being enforced by fact rather than by phrasing."; }
}
