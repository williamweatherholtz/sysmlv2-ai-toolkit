// ProjectDeliveryS613 — Sprint 613: Sprint 613 gives every artefact-writing instrument the property that a run which cannot complete leaves nothing that reads as a current answer (dcInstrumentsLeaveNoStaleArtifact, resolves issue399) under D0387: scripts/artefact.py holds the two shapes - a JSON answer claimed with a running stub and read only through require_complete, a page or drawing removed before the run - facts.py, the six builders, routing_probe.py, stpa_diagram.py adopt them, and keel suite writes a running receipt before cargo starts.. EXECUTE. 3 pts.
package ProjectDeliveryS613 {
    private import EngineElement::*;
    private import EngineWork::*;
    private import EngineVerification::*;
    private import EngineRelationships::*;

    #CharteredBy dependency from deadRunsLeaveNoAnswerStory to d0387;

    part deadRunsLeaveNoAnswerStory : Story {
        :>> id = "70ff9c8e-2bf5-485f-b813-e409218d212b";
        :>> title = "Sprint 613: Sprint 613 gives every artefact-writing instrument the property that a run which cannot complete leaves nothing that reads as a current answer (dcInstrumentsLeaveNoStaleArtifact, resolves issue399) under D0387: scripts/artefact.py holds the two shapes - a JSON answer claimed with a running stub and read only through require_complete, a page or drawing removed before the run - facts.py, the six builders, routing_probe.py, stpa_diagram.py adopt them, and keel suite writes a running receipt before cargo starts. (3 pts)";
        :>> createdAt = "2026-09-08"; :>> createdBy = "claudeOpus5"; :>> kind = WorkKind::code; :>> priority = WorkPriority::p0; :>> owner = "claudeOpus5"; :>> estimatedPoints = 3;
    }

    action def DeliveryRunS613 {
        action storyDeadRunsLeaveNoAnswer;
        verification storyDeadRunsLeaveNoAnswerDoD : Test { :>> id = "8a7b11e2-10f2-472a-84f7-e83931b532e9"; :>> method = VerificationMethod::test; :>> procedureText = "DONE MEANS: a failed instrument leaves no artefact that reads as a current answer. Resolves issue399: the computed-facts script raised partway through a run and left the previous run's JSON in place - valid, timestamped, indistinguishable from current, and the source the standing brief is built from. DO: sweep every instrument that writes an artefact - the facts file, the suite receipt, the routing JSON, the census output, the rendered pages - and give each the same property: a run that cannot complete removes or unmistakably marks its previous output, so a missing answer is what failure produces. A non-zero exit is not sufficient, because the exit code lives in the shell and the artefact outlives it. Weigh writing the run's own outcome INTO the artefact against deleting it, and record the choice. VERIFY: killing each instrument mid-run leaves no artefact a reader would take as current, shown per instrument rather than argued once; and the standing brief refuses to build from an artefact whose run did not complete."; }
        // RAN: artefact.py probe 11 pass; six instruments killed or broken by hand each left no current-looking artefact (see implement gate); suite unit test for the running stub; D0387
        part storyDeadRunsLeaveNoAnswerDoDR1 : TestResult { :>> id = "89bc76c2-3983-4ea5-bb2f-8b6aa50c2135"; :>> outcome = VerdictKind::pass; :>> judgedAgainst = "e0acb5604cd137fbcf8745a145cbee527dda1b84"; :>> judgedAt = "2026-09-08"; :>> judgedBy = "claudeOpus5"; }
    }

    verification deadRunsLeaveNoAnswerRefineGate : Test { :>> id = "d487424d-a2b1-43bc-b559-e42882706859"; :>> title = "Sprint 613 refine gate (DoR)"; :>> createdAt = "2026-09-08"; :>> createdBy = "claudeOpus5"; :>> method = VerificationMethod::inspect; :>> procedureText = "Scope: scripts/artefact.py (begin_json / finish_json / require_complete / claim, --probe); scripts/exec_brief/facts.py; the five build_2026_09_08_*.py and rebuild_2026_09_08.py; .engine/tools/routing_probe.py and stpa_diagram.py (inline removal - engine tools do not import from scripts/); keel-cli/src/suite.rs (running stub, land_refusal wording, unit test); D0387. The census output named in the DoD was a scratchpad script printing to stdout with no artefact, and the guard receipt already has the property by construction (receipt.rs:232-239, 260-266) - both stated, neither changed. Out of scope: a Rust kill test of keel suite (cargo cannot be killed cleanly inside a test; the demonstration is by hand and recorded). Estimate 3 points: one helper with a probe, nine instruments wired, one Rust change with a test, per-instrument demonstrations. DoR: points set, charter d0387, scope clear, no blocking dependency, DoD authored."; }
    // RAN: DoR inspected: 3 points, charter d0387, scope in the refine text, DoD authored, no blocking dependency
    part deadRunsLeaveNoAnswerRefineGateR1 : TestResult { :>> id = "f5fbe0dc-0fc5-48c8-8c33-c484cee35839"; :>> outcome = VerdictKind::pass; :>> judgedAgainst = "e0acb5604cd137fbcf8745a145cbee527dda1b84"; :>> judgedAt = "2026-09-08"; :>> judgedBy = "claudeOpus5"; }
    verification deadRunsLeaveNoAnswerStandupGate : Test { :>> id = "83c22827-01b8-460f-b273-11eb8fb1ce90"; :>> title = "Sprint 613 standup gate"; :>> createdAt = "2026-09-08"; :>> createdBy = "claudeOpus5"; :>> method = VerificationMethod::inspect; :>> procedureText = "Plan: (1) artefact.py with the four operations and a probe whose child processes are killed with os._exit, raise, and finish; (2) facts.py: claim first, treat a running suite receipt as no count, finish last with complete true on the file and on stdout; (3) the six builders: require_complete + claim, refuse prev == out; (4) routing_probe.py and stpa_diagram.py remove at start; (5) suite.rs running stub + land_refusal branch + unit test; (6) kill or break each instrument and read what it left; (7) D0387; gates."; }
    // RAN: plan of seven steps recorded in the standup text; all seven executed in this commit
    part deadRunsLeaveNoAnswerStandupGateR1 : TestResult { :>> id = "a19a6908-568f-4b40-9af2-b6f2044022c6"; :>> outcome = VerdictKind::pass; :>> judgedAgainst = "e0acb5604cd137fbcf8745a145cbee527dda1b84"; :>> judgedAt = "2026-09-08"; :>> judgedBy = "claudeOpus5"; }
    verification deadRunsLeaveNoAnswerImplementGate : Test { :>> id = "94a85814-9b1a-4f82-825d-e9184beb27ae"; :>> title = "Sprint 613 implement gate"; :>> createdAt = "2026-09-08"; :>> createdBy = "claudeOpus5"; :>> method = VerificationMethod::test; :>> procedureText = "RAN: python scripts/artefact.py --probe (11 cases); timeout -s KILL 4 python scripts/exec_brief/facts.py then read decision-facts.json; the supersession builder against that file and against a complete file missing a key; stpa_diagram.py --from missing --out existing.svg; routing_probe.py --investigate noSuchCase with a prior routing-investigation.json present; keel suite . killed at 6 s with its process tree, then the receipt read; cargo build --release; cargo clippy --release --all-targets -D warnings; cargo test --release --lib suite; keel guard instruments-declared; keel gate --fast; keel guard."; }
    // RAN: python scripts/artefact.py --probe 11 pass 0 failures; timeout -s KILL 4 facts.py exit 137 -> decision-facts.json complete=false state=running; builder on it: 'not a completed answer - state running' exit 1; builder on a complete file missing supersedeEdges: KeyError after claim, demo-page.html absent; stpa_diagram --from missing --out demo.svg: exit 1, demo.svg absent; routing_probe --investigate noSuchCase: exit 1, routing-investigation.json absent; keel suite . killed at 6s (taskkill /T): receipt outcome=running passed=0 failed=0; cargo build clean; clippy -D warnings exit 0; cargo test --lib suite 3 passed; keel guard instruments-declared PASS; keel gate --fast clean
    part deadRunsLeaveNoAnswerImplementGateR1 : TestResult { :>> id = "a8a25775-6daa-4989-a130-818bc562f1f6"; :>> outcome = VerdictKind::pass; :>> judgedAgainst = "e0acb5604cd137fbcf8745a145cbee527dda1b84"; :>> judgedAt = "2026-09-08"; :>> judgedBy = "claudeOpus5"; }
    verification deadRunsLeaveNoAnswerReviewGate : Test { :>> id = "077348dd-378b-4c48-b399-0cce67df7120"; :>> title = "Sprint 613 review gate — three passes per D0172"; :>> createdAt = "2026-09-08"; :>> createdBy = "claudeOpus5"; :>> method = VerificationMethod::inspect; :>> procedureText = "Reviewed against the DoD per instrument: facts.py killed at 4 s left complete false / state running and the builder refused it naming the state; a builder that raised after its claim left no page; stpa_diagram left no SVG; routing_probe left no JSON; keel suite killed left outcome running, not green; the guard receipt's key equality is the same property by construction; the choice is D0387 - outcome in the artefact where a single reader checks it, absence where no reader could."; }
    // RAN: reviewed per instrument against the DoD: facts (stub + reader refusal), builders (absence after claim), stpa_diagram (absence), routing_probe (absence), suite (running stub not green), guard receipt (key equality, receipt.rs:232-239/260-266, unchanged); the choice recorded as D0387
    part deadRunsLeaveNoAnswerReviewGateR1 : TestResult { :>> id = "514b86ea-2722-4cde-b9a5-4dec416207e8"; :>> outcome = VerdictKind::pass; :>> judgedAgainst = "e0acb5604cd137fbcf8745a145cbee527dda1b84"; :>> judgedAt = "2026-09-08"; :>> judgedBy = "claudeOpus5"; }
    verification deadRunsLeaveNoAnswerCloseOutGate : Test { :>> id = "6d06a4f8-75d6-4083-9eef-b6c414a9974c"; :>> title = "Sprint 613 closeOut gate (autonomous, D0049)"; :>> createdAt = "2026-09-08"; :>> createdBy = "claudeOpus5"; :>> method = VerificationMethod::inspect; :>> procedureText = "Sprint 613 closes when dcInstrumentsLeaveNoStaleArtifactDoD carries a pass at the commit that carries the helper, the wired instruments, the suite stub and the Decision, and issue399 leaves keel show open-issues."; }
    // RAN: DoD pass recorded on storyDeadRunsLeaveNoAnswerDoD and dcInstrumentsLeaveNoStaleArtifactDoD at this SHA; issue399 resolution read back from keel show open-issues after the record
    part deadRunsLeaveNoAnswerCloseOutGateR1 : TestResult { :>> id = "37de28e4-fffd-4adc-825c-ae23344df7ab"; :>> outcome = VerdictKind::pass; :>> judgedAgainst = "e0acb5604cd137fbcf8745a145cbee527dda1b84"; :>> judgedAt = "2026-09-08"; :>> judgedBy = "claudeOpus5"; }
    verification deadRunsLeaveNoAnswerRetroGate : Test { :>> id = "a8d9f43a-db7e-4fd5-b2d0-b78136084750"; :>> title = "Sprint 613 retro gate (autonomous, D0049)"; :>> createdAt = "2026-09-08"; :>> createdBy = "claudeOpus5"; :>> method = VerificationMethod::analyze; :>> procedureText = "Retro held; avoidable-issue scan: no new item - the per-instrument kill demonstrations run by hand and the probe runs by hand, which is the gap dcScriptProbesRunInCi already tracks from sprint 612. Process improvement: the D0382 routing investigation's JSON was removed by this sprint's own demonstration, as designed - the record of that investigation is the receipt on the item that motivated it, not the machine-local file, which is what D0382 said."; }
    // RAN: retro held; avoidable-issue scan: none - the hand-run gap is dcScriptProbesRunInCi from sprint 612; no new Issue recorded in this commit
    part deadRunsLeaveNoAnswerRetroGateR1 : TestResult { :>> id = "0017ef70-3bcf-4eb8-8a65-1a8f1ce6d54d"; :>> outcome = VerdictKind::pass; :>> judgedAgainst = "e0acb5604cd137fbcf8745a145cbee527dda1b84"; :>> judgedAt = "2026-09-08"; :>> judgedBy = "claudeOpus5"; }
}
