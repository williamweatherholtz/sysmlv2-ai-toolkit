// ProjectDeliveryS310 — Sprint 310: split one conflated number into two honest ones, and say what
// is pending in each. CHANGE + EXECUTE. 5 pts.
package ProjectDeliveryS310 {
    private import EngineElement::*;
    private import EngineWork::*;
    private import EngineVerification::*;
    private import EngineRelationships::*;

    #CharteredBy dependency from verificationSplitStory to srGovTieredAffordances;

    part verificationSplitStory : Story {
        :>> id = "0d800310-0814-6310-9b3e-000000300310";
        :>> title = "Sprint 310: keel verification — EXAMINED vs EXERCISED, with the pending list (5 pts)";
        :>> createdAt = "2026-08-15"; :>> createdBy = "claudeOpus5"; :>> kind = WorkKind::code; :>> priority = WorkPriority::p0; :>> owner = "claudeOpus5"; :>> estimatedPoints = 5;
    }

    action def DeliveryRunS310 {
        action storyVerificationSplit;
        verification storyVerificationSplitDoD : Test { :>> id = "0d800311-0814-6311-9b3e-000000300311"; :>> method = VerificationMethod::test; :>> procedureText = "Requested directly: 'separate these ideas into different reports - test coverage and verification. I want to know what verification is pending.' THE CONFLATION WAS REAL. `sr_verified_pct` counts a SystemRequirement as verified when ANY Test #Verify-links it, so one number was the UNION of two unrelated claims: that someone formed a judgment ABOUT the requirement, and that the SYSTEM was run against it. MEASURED, and the split is not cosmetic: 84% verified decomposes into 32% EXAMINED (26/79 — critique/inspect/analyze/confirmation) and 75% EXERCISED (60/79 — test/demo). 41 requirements have been exercised but NEVER adversarially read; 7 have been examined but nothing has ever run against them; 12 have neither. The union told a reader neither of those things. DELIVERED: `keel verification [--pending]`, reporting the two dimensions separately and never as one number, with the exact pending list per dimension — 53 pending examination, 19 pending exercise. Superseded requirements are excluded, the same scope rule coverage, tier-satisfaction and (since issue127) critique-coverage use. Two Viewpoints declared (verification-examined, verification-exercised); the viewpoint-renderer guard confirms both name a real command. Doc-sync: CLAUDE.md §2 lens list and the guards.md note that previously said only 'read verifiedByMethod alongside'. clippy clean; 221 tests; validate 335 clean; 33 guards green."; }
        part storyVerificationSplitDoDR1 : TestResult { :>> id = "0d800312-0814-6312-9b3e-000000300312"; :>> outcome = VerdictKind::pass; :>> judgedAgainst = "a82eca4"; :>> judgedAt = "2026-08-15"; :>> judgedBy = "claudeOpus5"; }
    }

    verification vsRefineGate : Test { :>> id = "0d800313-0814-6313-9b3e-000000300313"; :>> title = "Sprint 310 refine gate (DoR)"; :>> createdAt = "2026-08-15"; :>> createdBy = "claudeOpus5"; :>> method = VerificationMethod::inspect; :>> procedureText = "DoR. ADDITIVE by design: a new command plus two new Viewpoints, changing NO existing view's meaning, so this is not the §3a case that needed sign-off in sprint 309. `sr_verified_pct` is left exactly as it was — it is cited in prior records and moving it would invalidate them; the new command is where the honest answer lives and the docs now point there. CONSUMER CHECK (dorConsumer, D0144): the consumer asked for the PENDING list, not a score, so `--pending` prints the requirement names and what each already has — a percentage alone would have answered the question that was not asked. estimatedPoints=5."; }
    part vsRefineGateR1 : TestResult { :>> id = "0d800314-0814-6314-9b3e-000000300314"; :>> outcome = VerdictKind::pass; :>> judgedAgainst = "a82eca4"; :>> judgedAt = "2026-08-15"; :>> judgedBy = "claudeOpus5"; }

    verification vsStandupGate : Test { :>> id = "0d800315-0814-6315-9b3e-000000300315"; :>> title = "Sprint 310 standup gate"; :>> createdAt = "2026-08-15"; :>> createdBy = "claudeOpus5"; :>> method = VerificationMethod::inspect; :>> procedureText = "Approach: measure the split BEFORE building, so the command is designed around what the data actually shows rather than around the classification I expected; build it in the binary rather than as a script, because a report that answers a recurring question belongs where it can be re-run (D0040). No blockers."; }
    part vsStandupGateR1 : TestResult { :>> id = "0d800316-0814-6316-9b3e-000000300316"; :>> outcome = VerdictKind::pass; :>> judgedAgainst = "a82eca4"; :>> judgedAt = "2026-08-15"; :>> judgedBy = "claudeOpus5"; }

    verification vsImplementGate : Test { :>> id = "0d800317-0814-6317-9b3e-000000300317"; :>> title = "Sprint 310 implement gate"; :>> createdAt = "2026-08-15"; :>> createdBy = "claudeOpus5"; :>> method = VerificationMethod::test; :>> procedureText = "I ALMOST RECORDED A DEFECT THAT DID NOT EXIST. I reported to the human that `verifiedByMethod` returns None while guards.md tells a reader to consult it, and offered to raise it. It returns {critique:72, demo:59, test:43, inspect:18, analyze:1} — I had looked for it inside the SystemRequirement TIER object when it is emitted at the TOP LEVEL. Checking before recording is the only reason a false finding did not reach the model, and it is the third time this session that a suspicion evaporated under the check. THE REAL DISTINCTION THAT SURVIVED: `verifiedByMethod` counts EDGES, and the new command counts distinct REQUIREMENTS. 72 critique edges reach only 19 requirements, because a Core-3 critique is three edges onto one target. Both numbers are correct and they answer different questions, so the new command prints the relationship explicitly rather than leaving a reader to wonder why 72 became 19. `confirmation` is classified as EXAMINED and it is worth saying why: a human attestation is a judgment formed about the claim, not a run of the system, and counting it as test coverage would be exactly the conflation this command exists to undo."; }
    part vsImplementGateR1 : TestResult { :>> id = "0d800318-0814-6318-9b3e-000000300318"; :>> outcome = VerdictKind::pass; :>> judgedAgainst = "a82eca4"; :>> judgedAt = "2026-08-15"; :>> judgedBy = "claudeOpus5"; }

    verification vsReviewGate : Test { :>> id = "0d800319-0814-6319-9b3e-000000300319"; :>> title = "Sprint 310 review gate"; :>> createdAt = "2026-08-15"; :>> createdBy = "claudeOpus5"; :>> method = VerificationMethod::inspect; :>> procedureText = "Reviewed. The output states what each dimension does NOT tell you, next to the number: EXAMINED needs no implementation and says nothing about whether the system does the thing; EXERCISED says nothing about whether the requirement was any good. A reader who takes either as an overall verdict has been warned by the report itself rather than by a doc they may never open. The 41 exercised-but-never-examined requirements are the finding most likely to matter here — this repo has been diligent about running things and much thinner on adversarially reading what it committed to."; }
    part vsReviewGateR1 : TestResult { :>> id = "0d80031a-0814-631a-9b3e-00000030031a"; :>> outcome = VerdictKind::pass; :>> judgedAgainst = "a82eca4"; :>> judgedAt = "2026-08-15"; :>> judgedBy = "claudeOpus5"; }

    verification vsCloseOutGate : Test { :>> id = "0d80031b-0814-631b-9b3e-00000030031b"; :>> title = "Sprint 310 closeOut gate (autonomous, D0049)"; :>> createdAt = "2026-08-15"; :>> createdBy = "claudeOpus5"; :>> method = VerificationMethod::inspect; :>> procedureText = "Autonomous closeOut (D0049). Additive: no existing view's meaning changed, so no §3a sign-off was required and none was claimed. clippy clean; 221 tests; validate 335 clean; check-engine clean; 33 guards green; viewpoint-renderer 28 scanned with both new Viewpoints resolving to a real command."; }
    part vsCloseOutGateR1 : TestResult { :>> id = "0d80031c-0814-631c-9b3e-00000030031c"; :>> outcome = VerdictKind::pass; :>> judgedAgainst = "a82eca4"; :>> judgedAt = "2026-08-15"; :>> judgedBy = "claudeOpus5"; }

    verification vsRetroGate : Test { :>> id = "0d80031d-0814-631d-9b3e-00000030031d"; :>> title = "Sprint 310 retro gate (autonomous, D0049)"; :>> createdAt = "2026-08-15"; :>> createdBy = "claudeOpus5"; :>> method = VerificationMethod::analyze; :>> procedureText = "Autonomous retro (D0049) under D0131's retroTrack. WELL: (1) the human's question — why does keel serve need to verify them — was a correction, and checking it rather than defending the phrasing is what produced this command; my summary had conflated 'the system it describes does not exist' with 'nothing can verify it', which are different claims and only the second bears on the number; (2) the split was MEASURED before it was built, so the classification follows the data; (3) the false `verifiedByMethod` defect was caught before it reached the model. AVOIDABLE-ISSUE: I stated that defect to the human as fact before verifying it. It cost nothing because I checked before recording, but the honest description is that I reported an unverified claim conversationally while applying a stricter standard to the model than to what I say — and the record is the thing that must be true, but a human acting on my summary is acting on something that ought to be equally true. NO NEW ITEM: the remedy is the same verify-before-asserting discipline already tracked, and the specific instance is recorded here. Estimate 5 pts, delivered."; }
    part vsRetroGateR1 : TestResult { :>> id = "0d80031e-0814-631e-9b3e-00000030031e"; :>> outcome = VerdictKind::pass; :>> judgedAgainst = "a82eca4"; :>> judgedAt = "2026-08-15"; :>> judgedBy = "claudeOpus5"; }
}
