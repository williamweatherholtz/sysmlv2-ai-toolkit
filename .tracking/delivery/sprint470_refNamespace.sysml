// ProjectDeliveryS470 - Sprint 470: a downstream project's first recorded decision collided with the engine's own history shipped beside it. The namespace fix, and the control that was named in a retro two months ago and never built. EXECUTE. 3 pts.
package ProjectDeliveryS470 {
    private import EngineElement::*;
    private import EngineWork::*;
    private import EngineVerification::*;
    private import EngineRelationships::*;

    #CharteredBy dependency from refNamespaceStory to d0237;

    part refNamespaceStory : Story {
        :>> id = "6e6566be-e112-4932-8923-4bc3b3b5899f";
        :>> title = "Sprint 470: the shipped reference decision history gets its own package namespace, and the init smoke test finally records a fact (3 pts)";
        :>> createdAt = "2026-08-27"; :>> createdBy = "claudeOpus5"; :>> kind = WorkKind::code; :>> priority = WorkPriority::p0; :>> owner = "claudeOpus5"; :>> estimatedPoints = 3;
    }

    action def DeliveryRunS470 {
        action storyRefNamespace;
        verification storyRefNamespaceDoD : Test { :>> id = "37eee454-2042-4ad4-90aa-89aab5287a93"; :>> method = VerificationMethod::test; :>> procedureText = "DELIVERED: fixDownstreamDecisionNumbering (issue291). migrate.rs::remap_engine_content renames the reference copy's package DecisionNNNN -> ReferenceDecisionNNNN, paired with remap_engine_path and applied at BOTH copy sites (main.rs write_engine_file for init, step_engine_resync for migrate). The two namespaces are disjoint BY PREFIX, so number overlap stops mattering permanently; project decisions keep the natural DecisionNNNN/dNNNN scheme, so a downstream project's first decision is D0001 and no reader changes. Because resync compares TRANSFORMED content against disk, that step is both the repair for an existing project and a no-op for a new one. ALSO DELIVERED, as the D0047 control: init_smoke now RECORDS a decision in the fresh project and asserts guard all + validate stay green - steps 1-5 asserted init-then-read, the one state in which this entire defect class is invisible."; }
    // RAN: cargo test --release => 278 lib passed 0 failed, incl the two new declaration-only + idempotency tests; cargo test --test init_smoke => pass, and FAILED at init_smoke.rs:174 ("the gate went red once the fresh project recorded a decision") with the transform disabled, which is the proof the new control catches the defect rather than merely passing beside it; fresh fixture C:/kt/f2: init --profile guided => 236 package ReferenceDecision, record decision => D0001/package Decision0001, guard => duplicate-identity PASS 331 scanned, guard all => ALL PASS exit 0, gate --fast => clean; old-vintage fixture (packages reverted, committed 793b865): guard => duplicate-identity FAIL 2 violations, migrate . => wrote 241 files re-plan empty, guard => PASS, project's own Decision0001 untouched, second dry-run => 0 reference edits; this tree: validate 525 clean, check-engine clean, guard => 0 of 52 failing.
        part storyRefNamespaceDoDR1 : TestResult { :>> id = "abf6824d-da97-4ce9-a15c-f55d1ed0e63c"; :>> outcome = VerdictKind::pass; :>> judgedAgainst = "d07a647"; :>> judgedAt = "2026-08-27"; :>> judgedBy = "claudeOpus5"; }
    }

    verification refNamespaceRefineGate : Test { :>> id = "b45d987d-770b-48ec-92c1-307ddd035b0d"; :>> title = "Sprint 470 refine gate (DoR)"; :>> createdAt = "2026-08-27"; :>> createdBy = "claudeOpus5"; :>> method = VerificationMethod::inspect; :>> procedureText = "DoR: issue291 was filed from a field project (pdp-gate-review-3q26) where the collision was hit live, and fixDownstreamDecisionNumbering was ranked FIRST on the frontier, ahead of the workspace block - so it was taken first per D0052 rather than the workspace redesign that was in progress. Reproduced before designing: a fresh init fixture, record decision, and the same two duplicate-identity violations the field report described. Resolver: fixDownstreamDecisionNumbering. estimatedPoints=3. #CharteredBy d0237."; }
    part refNamespaceRefineGateR1 : TestResult { :>> id = "257b65e7-6658-4d45-af19-8dd7d7dba10e"; :>> outcome = VerdictKind::pass; :>> judgedAgainst = "d07a647"; :>> judgedAt = "2026-08-27"; :>> judgedBy = "claudeOpus5"; }
    verification refNamespaceStandupGate : Test { :>> id = "50adeb9f-dbcb-45d7-9aca-25bba8a1bfa3"; :>> title = "Sprint 470 standup gate"; :>> createdAt = "2026-08-27"; :>> createdBy = "claudeOpus5"; :>> method = VerificationMethod::inspect; :>> procedureText = "Approach: the DoD allowed two options and BOTH were checked against the migrate path before choosing. Numbering past the highest reference decision was REJECTED because it fixes the first allocation and reopens the hole at the next migrate, when the engine's own history reaches the number the project already took - and renumbering an accepted decision is not available as a remedy. Renaming the PART names was rejected because 189 of the 514 dNNNN occurrences sit inside procedureText prose. Renaming the PACKAGE is one line per file, always at identifier position. Checked first that nothing imports a decision package by name (0 hits), that no code matches on a package Decision prefix (0 hits), and that the 10 #JustifiedBy edges in rules.sysml still resolve (global name resolution). No process-def or schema change and no enforcement-surface change, so no keystone marker."; }
    part refNamespaceStandupGateR1 : TestResult { :>> id = "7f44c1f0-5442-40e9-9148-f7407b04436a"; :>> outcome = VerdictKind::pass; :>> judgedAgainst = "d07a647"; :>> judgedAt = "2026-08-27"; :>> judgedBy = "claudeOpus5"; }
    verification refNamespaceImplementGate : Test { :>> id = "eecfd302-1c37-4331-b547-606c31c7953a"; :>> title = "Sprint 470 implement gate"; :>> createdAt = "2026-08-27"; :>> createdBy = "claudeOpus5"; :>> method = VerificationMethod::test; :>> procedureText = "Implemented remap_engine_content + both call sites + 3 tests. The disable-and-rerun check is the one that matters: with the transform stubbed to return None the smoke test FAILS at the recording assertion, so the control is not hollow. Two heredoc backslash manglings were hit and fixed during authoring (a char literal and two string literals became real newlines); syntax-bearing content went through the edit tools after that. Two clippy fail-loud lints also blocked the commit and were fixed rather than bypassed: doc_markdown on DoD, and expect_used in the new test."; }
    // RAN: cargo test --release => 278 lib passed 0 failed; cargo test --test init_smoke => 1 passed; the same smoke test FAILED at init_smoke.rs:174 with remap_engine_content stubbed to return None, which is the disable-and-rerun proof that the control catches issue291; fresh fixture init+record decision => D0001 with duplicate-identity PASS and guard all ALL PASS exit 0; old-vintage fixture => duplicate-identity FAIL 2 then migrate 241 files then PASS with an empty re-plan; this tree => validate 526 clean, check-engine clean.
    part refNamespaceImplementGateR1 : TestResult { :>> id = "56741b1a-ec8f-4c26-9aad-c863b1f8c049"; :>> outcome = VerdictKind::pass; :>> judgedAgainst = "d07a647"; :>> judgedAt = "2026-08-27"; :>> judgedBy = "claudeOpus5"; }
    verification refNamespaceReviewGate : Test { :>> id = "5eee126c-a9d9-4935-9e3e-a0f0cbbce038"; :>> title = "Sprint 470 review gate"; :>> createdAt = "2026-08-27"; :>> createdBy = "claudeOpus5"; :>> method = VerificationMethod::inspect; :>> procedureText = "Diff reviewed. The fix is a pure function beside the path transform it pairs with, applied at both copy sites, and keel's own repo is untouched because it has no reference/ directory - which is also why this defect could not appear in the self-build and had to be reported from the field. Three things were deliberately NOT done and are recorded rather than silently skipped: the reference copy is still parsed as instance data (issue292, with resolver scopeReferenceCopyOutOfTheInstanceModel and a DoD that requires RECORDING a fact before asserting); the unexplained installed-units version bump 16->17 with identical file hashes was reverted rather than committed, and stays tracked under dcPanelRecordCorrections; and append-result's --evidence flag is missing from its usage line."; }
    part refNamespaceReviewGateR1 : TestResult { :>> id = "624aba9a-8882-4a19-be9f-726e39d9b1d8"; :>> outcome = VerdictKind::pass; :>> judgedAgainst = "d07a647"; :>> judgedAt = "2026-08-27"; :>> judgedBy = "claudeOpus5"; }
    verification refNamespaceCloseOutGate : Test { :>> id = "a13cac35-e9c6-417e-b3e4-574a5726f712"; :>> title = "Sprint 470 closeOut gate (autonomous, D0049)"; :>> createdAt = "2026-08-27"; :>> createdBy = "claudeOpus5"; :>> method = VerificationMethod::inspect; :>> procedureText = "Autonomous closeOut (D0049): storyRefNamespace DoD recorded pass with its RAN receipts; the frontier was read back from keel whats-next and fixDownstreamDecisionNumbering is off it; sprint-coverage's violation - done but not covered by any sprint - is what required this sprint record, and it was authored rather than bypassed. Self-evidencing (D0051): no human confirmation is claimed anywhere in this sprint."; }
    part refNamespaceCloseOutGateR1 : TestResult { :>> id = "ded00069-9603-4d40-acc9-4407486982a8"; :>> outcome = VerdictKind::pass; :>> judgedAgainst = "d07a647"; :>> judgedAt = "2026-08-27"; :>> judgedBy = "claudeOpus5"; }
    verification refNamespaceRetroGate : Test { :>> id = "db7813ac-910e-45b6-9754-fa85ccec584c"; :>> title = "Sprint 470 retro gate (autonomous, D0049)"; :>> createdAt = "2026-08-27"; :>> createdBy = "claudeOpus5"; :>> method = VerificationMethod::analyze; :>> procedureText = "Autonomous retro (D0049). WELL: reproducing in a real fixture BEFORE designing turned a numbering bug into three findings, because the fixture also showed 235 attestations judged by keel's human and 236 judgedAgainst SHAs that do not resolve downstream - neither of which the field report mentioned and neither of which a code read would have surfaced. Checking the REJECTED option against the migrate path is what kept the fix durable; the DoD sanctioned the unsound option first. FINDING, and the real lesson: sprint 104's own retro NAMED this exact control - an init smoke-test in CI that scaffolds + guards a temp project - and declined to track it, writing 'logged as the lesson; not yet a tracked Issue (the broader risk is low)'. That is precisely the D0047 failure mode: a lesson logged instead of a control built. Sprint 115 then built the smoke test and asserted init-then-validate, so the control existed and still could not see this class. Both gates covering init exercised the one state where the defect is invisible. AVOIDABLE-ISSUE SCAN: a false present-tense claim survived two months in sprint 104's header - NOT scanned as instance - describing a boundary that was never implemented; corrected to state what IS, with the sprint's own history left intact as the evidence of what was believed. Estimate 3 pts held. Candidate forward control, NOT built and therefore stated rather than logged as a lesson: a check that a retro naming a candidate control either creates the tracked Issue or records why not - this retro's finding is that the failure was declining to track, and nothing detects that today."; }
    part refNamespaceRetroGateR1 : TestResult { :>> id = "390efea6-c74b-4552-9086-7ec0810e3191"; :>> outcome = VerdictKind::pass; :>> judgedAgainst = "d07a647"; :>> judgedAt = "2026-08-27"; :>> judgedBy = "claudeOpus5"; }
}
