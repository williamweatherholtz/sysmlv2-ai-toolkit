// ProjectDeliveryS237 — Sprint 237: serveModelMemo — fix slow serve cold-loads. A page-load burst fires
// ~8 views that each re-parsed all ~260 model files (18-23s on an I/O-heavy host — human-reported). Memoize
// Model::build by content fingerprint so the burst shares ONE parse. Charters to d0094 (the console). 2 pts.
package ProjectDeliveryS237 {
    private import EngineElement::*;
    private import EngineWork::*;
    private import EngineVerification::*;
    private import EngineRelationships::*;

    #CharteredBy dependency from serveModelMemoStory to d0094;

    part serveModelMemoStory : Story {
        :>> id = "63940516-2c7d-4e8f-c237-51627384c001";
        :>> title = "Sprint 237: serveModelMemo (2 pts) - memoize Model::build by fingerprint (fix slow serve cold-loads)";
        :>> createdAt = "2026-07-15"; :>> createdBy = "wweatherholtz"; :>> kind = WorkKind::code; :>> priority = WorkPriority::p1; :>> owner = "claudeOpus"; :>> estimatedPoints = 2;
    }

    action def DeliveryRunS237 {
        action storyServeModelMemo;
        verification storyServeModelMemoDoD : Test { :>> id = "63940516-2c7d-4e8f-c237-51627384c002"; :>> method = VerificationMethod::test; :>> procedureText = "Fixes human-reported serve cold-load slowness (GET /api/review-queue 18024ms, /api/orient 23384ms, /api/decisions 23450ms on first load; then cached ~69ms). ROOT CAUSE: the serve JSON cache dedups per-endpoint, but a browser page-load burst fires ~8 DISTINCT views that EACH call Model::build, re-parsing all ~260 .tracking+.engine files — cheap in isolation (orient CLI ~1s) but slow when 8 run concurrently on an I/O-heavy host (Windows Defender scanning each .sysml read). FIX: memoize Model::build by a stat-only content fingerprint (path+len+mtime) in a process-global MODEL_CACHE, with a MODEL_BUILD_LOCK so a concurrent cold burst does exactly ONE parse (others wait then hit the cache). Regenerable cache, never truth (§2.1); invalidates automatically on any file change. Model/ItemInfo derive Clone (cheap vs re-parsing). VERIFY (test): 8 concurrent cold requests 2.0s -> 1.1s locally (bigger win on the reporter's host — one parse's I/O, not eight); orient still correct (counts done 473); touching a file invalidates the cache -> recompute (0.85s). clippy --workspace -D warnings clean; keel validate + guard + check-engine green (memoized model is consistent within a run)."; }
        part storyServeModelMemoDoDR1 : TestResult { :>> id = "63940516-2c7d-4e8f-c237-51627384c003"; :>> outcome = VerdictKind::pass; :>> judgedAgainst = "406d336"; :>> judgedAt = "2026-07-15"; :>> judgedBy = "claudeOpus"; }
    }

    verification smRefineGate : Test { :>> id = "63940516-2c7d-4e8f-c237-51627384c004"; :>> title = "Sprint 237 refine gate (DoR)"; :>> createdAt = "2026-07-15"; :>> createdBy = "claudeOpus"; :>> method = VerificationMethod::inspect; :>> procedureText = "DoR: human reported 18-23s serve cold-loads. Diagnosed: per-endpoint Model::build re-parses on a burst. Scope: memoize Model::build by fingerprint. #CharteredBy d0094. estimatedPoints=2. DoR met."; }
    part smRefineGateR1 : TestResult { :>> id = "63940516-2c7d-4e8f-c237-51627384c005"; :>> outcome = VerdictKind::pass; :>> judgedAgainst = "406d336"; :>> judgedAt = "2026-07-15"; :>> judgedBy = "claudeOpus"; }
    verification smStandupGate : Test { :>> id = "63940516-2c7d-4e8f-c237-51627384c006"; :>> title = "Sprint 237 standup gate"; :>> createdAt = "2026-07-15"; :>> createdBy = "claudeOpus"; :>> method = VerificationMethod::inspect; :>> procedureText = "Approach: static MODEL_CACHE (fingerprint -> Model) + MODEL_BUILD_LOCK to serialize builds (one parse per burst); derive Clone; keep Model::build signature (callers unchanged). Measure before/after + confirm invalidation. No blockers."; }
    part smStandupGateR1 : TestResult { :>> id = "63940516-2c7d-4e8f-c237-51627384c007"; :>> outcome = VerdictKind::pass; :>> judgedAgainst = "406d336"; :>> judgedAt = "2026-07-15"; :>> judgedBy = "claudeOpus"; }
    verification smImplementGate : Test { :>> id = "63940516-2c7d-4e8f-c237-51627384c008"; :>> title = "Sprint 237 implement gate"; :>> createdAt = "2026-07-15"; :>> createdBy = "claudeOpus"; :>> method = VerificationMethod::test; :>> procedureText = "MODEL_CACHE + MODEL_BUILD_LOCK + fingerprint + build/build_uncached split + Clone derives implemented. clippy clean; burst 2.0->1.1s; correctness + invalidation verified. validate/guard/check-engine green."; }
    part smImplementGateR1 : TestResult { :>> id = "63940516-2c7d-4e8f-c237-51627384c009"; :>> outcome = VerdictKind::pass; :>> judgedAgainst = "406d336"; :>> judgedAt = "2026-07-15"; :>> judgedBy = "claudeOpus"; }
    verification smReviewGate : Test { :>> id = "63940516-2c7d-4e8f-c237-51627384c00a"; :>> title = "Sprint 237 review gate"; :>> createdAt = "2026-07-15"; :>> createdBy = "claudeOpus"; :>> method = VerificationMethod::inspect; :>> procedureText = "Reviewed. Correct diagnosis (the JSON cache handled repeat-same-endpoint, but a burst of DISTINCT endpoints each rebuilt the model) and the right fix layer — memoize the expensive shared computation (parse), keyed by the same content fingerprint the serve cache uses, with a build-lock so a cold burst parses once. Cache is regenerable + auto-invalidated (never truth). Signature unchanged (no caller churn). The win scales with host I/O cost, which is exactly the reporter's case. Clean."; }
    part smReviewGateR1 : TestResult { :>> id = "63940516-2c7d-4e8f-c237-51627384c00b"; :>> outcome = VerdictKind::pass; :>> judgedAgainst = "406d336"; :>> judgedAt = "2026-07-15"; :>> judgedBy = "claudeOpus"; }
    verification smCloseOutGate : Test { :>> id = "63940516-2c7d-4e8f-c237-51627384c00c"; :>> title = "Sprint 237 closeOut gate (autonomous, D0049)"; :>> createdAt = "2026-07-15"; :>> createdBy = "claudeOpus"; :>> method = VerificationMethod::inspect; :>> procedureText = "Autonomous closeOut (D0049): DoD pass; serve cold-load burst now shares one parse (model memoized). Self-evidencing. NEXT: resume the viewer completion run — mark delivered items + build viewerIterativeCritique + viewerInProgramEdit."; }
    part smCloseOutGateR1 : TestResult { :>> id = "63940516-2c7d-4e8f-c237-51627384c00d"; :>> outcome = VerdictKind::pass; :>> judgedAgainst = "406d336"; :>> judgedAt = "2026-07-15"; :>> judgedBy = "claudeOpus"; }
    verification smRetroGate : Test { :>> id = "63940516-2c7d-4e8f-c237-51627384c00e"; :>> title = "Sprint 237 retro gate (autonomous, D0049)"; :>> createdAt = "2026-07-15"; :>> createdBy = "claudeOpus"; :>> method = VerificationMethod::analyze; :>> procedureText = "Autonomous retro (D0049). WELL: measured before guessing — profiled the CLI (fast, ~1s) vs serve (slow) to localize the cost to concurrent per-endpoint Model::build, then memoized the shared parse. Confirmed correctness + cache invalidation, not just speed. AVOIDABLE-ISSUE (banked): a per-request computed view that re-parses the whole model doesn't scale with endpoint count under a page-load burst — memoize the model (regenerable) keyed by content fingerprint. LESSON: the serve JSON cache handles repeats; the model memo handles the cross-endpoint burst. Estimate 2 pts. NEXT: resume viewer completion."; }
    part smRetroGateR1 : TestResult { :>> id = "63940516-2c7d-4e8f-c237-51627384c00f"; :>> outcome = VerdictKind::pass; :>> judgedAgainst = "406d336"; :>> judgedAt = "2026-07-15"; :>> judgedBy = "claudeOpus"; }
}
