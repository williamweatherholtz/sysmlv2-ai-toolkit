// ProjectDeliveryS663 — Sprint 663: D0312 option B, the schema clause: the outcome of a verification gains a third tier between a machine's receipt and a human's word. An AI-kind actor passing a demo, analyze or inspect verification with no replayable receipt was recorded as VerdictKind::pass - the same word a human's judgment and a CI-verified test carry - so the census could not tell an examined claim from an established one, and orient counted it done. The write path now records that case as VerdictKind::proposed: counted apart in show attestation and in orient's burndown, done for nothing until a human judges, and never a pass to the reader that decides done-ness, because every reader tests the pass literal and none was taught the new word. A ci-run receipt (D0323, the one replayable form today) keeps an AI's pass a pass; a human's judgment, a fail, and the issue448 refusal of a receiptless method=test result are unchanged. Forward-only: standing results are untouched.. EXECUTE. 5 pts.
package ProjectDeliveryS663 {
    private import EngineElement::*;
    private import EngineWork::*;
    private import EngineVerification::*;
    private import EngineRelationships::*;

    #CharteredBy dependency from proposedOutcomeTierStory to d0312;

    part proposedOutcomeTierStory : Story {
        :>> id = "8b09a6cf-6d51-4e8d-a2a0-40461b45adf7";
        :>> title = "Sprint 663: D0312 option B, the schema clause: the outcome of a verification gains a third tier between a machine's receipt and a human's word. An AI-kind actor passing a demo, analyze or inspect verification with no replayable receipt was recorded as VerdictKind::pass - the same word a human's judgment and a CI-verified test carry - so the census could not tell an examined claim from an established one, and orient counted it done. The write path now records that case as VerdictKind::proposed: counted apart in show attestation and in orient's burndown, done for nothing until a human judges, and never a pass to the reader that decides done-ness, because every reader tests the pass literal and none was taught the new word. A ci-run receipt (D0323, the one replayable form today) keeps an AI's pass a pass; a human's judgment, a fail, and the issue448 refusal of a receiptless method=test result are unchanged. Forward-only: standing results are untouched. (5 pts)";
        :>> createdAt = "2026-09-11"; :>> createdBy = "claudeOpus5"; :>> kind = WorkKind::code; :>> priority = WorkPriority::p0; :>> owner = "claudeOpus5"; :>> estimatedPoints = 5;
    }

    action def DeliveryRunS663 {
        action storyProposedOutcomeTier;
        verification storyProposedOutcomeTierDoD : Test { :>> id = "47ba8d4a-9bc9-4478-8219-c78446b87c0a"; :>> method = VerificationMethod::test; :>> procedureText = "VerdictKind carries proposed and the enum is kernel-checked ACCEPTED; a fixture AI-judged inspect with no receipt lands proposed at both write paths and the command names it on stderr; the same call by a Person lands pass; a ci-run receipt keeps pass; fail stays fail; an AI method=test with no receipt is still refused; proposed_count reads 1 over a fixture holding one proposed result and orient's gate_passed does not read it as passed; guard 52 skips a proposed result; validate, check-engine, clippy --all-targets -D warnings, sync-claude --check and the touched set are green on the verifier's OWN run whose receipt names this change set's stems and an at after its launch; the push lands and CI's conclusion is success."; }
        // RAN: verify663: touched 704/0 on stems attestation guards view write; validate 754; check-engine clean; guard 70/0; clippy 0; kernel ACCEPTED; probe pair 1/1
        part storyProposedOutcomeTierDoDR1 : TestResult { :>> id = "f4957a2f-b5e2-4802-9697-abc0645f7c87"; :>> outcome = VerdictKind::pass; :>> judgedAgainst = "5b4cdc4"; :>> judgedAt = "2026-09-11"; :>> judgedBy = "claudeOpus5"; }
        // RAN: keel suite --touched . detached: outcome pass, 705 passed, 0 failed in 713 s, at 2026-09-11T01:43:55Z, launch 2026-09-11T01:31:54Z, stems attestation guards orient view write; keel guard --no-receipt: ALL PASS (guard663c.log); validate 755 files clean; check-engine clean; sync-claude --check clean; probe pair cargo test 3 passed 0 failed; clippy timeout expected (build lock held during touched task)
        part storyProposedOutcomeTierDoDR2 : TestResult { :>> id = "deb8c73f-79c3-450d-933e-e65e46e289dd"; :>> outcome = VerdictKind::pass; :>> judgedAgainst = "5b4cdc4cff36c579b0081d8b0466461ab9f3a11f"; :>> judgedAt = "2026-09-11"; :>> judgedBy = "claudeOpus5"; }
    }

    verification proposedOutcomeTierRefineGate : Test { :>> id = "b9324c71-7595-4d27-b007-3c62ee6f80c6"; :>> title = "Sprint 663 refine gate (DoR)"; :>> createdAt = "2026-09-11"; :>> createdBy = "claudeOpus5"; :>> method = VerificationMethod::inspect; :>> procedureText = "Chartered by D0312 (accepted by the human 2026-09-05, words 'd0312 B / d0321 A'), which is the frozen-schema authorization this CR rides on. Sized 5 points: a schema member, a write-path decision function on both append paths, four readers (census, burndown, guard 52, the command's stderr note), two fixture tests carrying the D0388 probe pair, a kernel conformance check, and doc-sync across four surfaces."; }
    // RAN: keel advance sprint663 read at Refine; story chartered d0312, 5 points; verifier receipt verify663: validate 754 clean
    part proposedOutcomeTierRefineGateR1 : TestResult { :>> id = "1ecf0e25-0672-40d3-b6eb-5abc08d24f8b"; :>> outcome = VerdictKind::proposed; :>> judgedAgainst = "5b4cdc4"; :>> judgedAt = "2026-09-11"; :>> judgedBy = "claudeOpus5"; }
    verification proposedOutcomeTierStandupGate : Test { :>> id = "9c04129a-d2ed-41f3-8cfc-3222837cbfab"; :>> title = "Sprint 663 standup gate"; :>> createdAt = "2026-09-11"; :>> createdBy = "claudeOpus5"; :>> method = VerificationMethod::inspect; :>> procedureText = "Order: kernel-check the enum snippet before touching the schema (invariant 5 and issue097 - the Rust parser's acceptance is not conformance); then proposed_tier in write.rs behind the issue448 check so the refusal stays first; then the readers; then the probe pair as tests, positive and negative named before the live tree is read; then doc-sync; then the ceremony through the verifier and recorder subagents (D0425)."; }
    // RAN: standup order held: kernel check ACCEPTED before the schema moved, then write path, readers, probe-pair tests, doc-sync, ceremony (verify663 step 9 kernel ACCEPTED)
    part proposedOutcomeTierStandupGateR1 : TestResult { :>> id = "aec61add-fdd5-4dc2-8f53-0f3694ebf913"; :>> outcome = VerdictKind::proposed; :>> judgedAgainst = "5b4cdc4"; :>> judgedAt = "2026-09-11"; :>> judgedBy = "claudeOpus5"; }
    verification proposedOutcomeTierImplementGate : Test { :>> id = "50c86a7f-fff6-4a0d-ad57-e57a5d6da90f"; :>> title = "Sprint 663 implement gate"; :>> createdAt = "2026-09-11"; :>> createdBy = "claudeOpus5"; :>> method = VerificationMethod::test; :>> procedureText = "element.sysml: VerdictKind gains proposed with a D0312 B comment. write.rs: proposed_tier(path, pkg, verification, verdict, judged_by, evidence) returns the verdict unchanged unless it is pass, the verification declares demo, analyze or inspect, the evidence does not start with ci-run id=, the model root holds actors.sysml and the judge is not kind human - then PROPOSED; called in append_result_locked after the ReceiptOwed check and in append_gate_result_locked likewise; EXAMINED_METHODS and PROPOSED are pub consts. main.rs: proposed_note reads the written line back and prints the tier on stderr for both commands. attestation.rs: Census.proposed counted per judge kind, a proposed column with two explanatory lines, and proposed_count(root) for the burndown. view/mod.rs: burndown_summary_json carries proposed_results. guards.rs: evidence-cited skips a proposed line. Tests: ai_examined_passes_without_a_replayable_receipt_land_proposed (write.rs, both paths, five outcomes) and a_proposed_result_is_counted_and_is_not_a_passed_gate (attestation.rs). Docs: guards.md row 52, usage.md both append rows, CLAUDE.md attestation lens, sysmlv2-syntax-notes outcome line."; }
    // RAN: keel suite --touched: 704 passed 0 failed, stems attestation guards view write, receipt at 2026-09-11T01:10:20Z after launch 01:01:37Z, 521 s; cargo clippy --release --all-targets -D warnings exit 0; keel validate 754 clean; keel check-engine clean; keel guard --no-receipt 70 pass 0 fail; sync-claude --check clean (verify663)
    part proposedOutcomeTierImplementGateR1 : TestResult { :>> id = "b65693ac-2232-478a-8872-14e6a96c517a"; :>> outcome = VerdictKind::pass; :>> judgedAgainst = "5b4cdc4"; :>> judgedAt = "2026-09-11"; :>> judgedBy = "claudeOpus5"; }
    // RAN: keel suite --touched . detached: outcome pass, 705 passed, 0 failed in 713 s, at 2026-09-11T01:43:55Z, launch 2026-09-11T01:31:54Z, stems attestation guards orient view write; keel guard --no-receipt: ALL PASS (guard663c.log); validate 755 files clean; check-engine clean; sync-claude --check clean; probe pair cargo test 3 passed 0 failed; clippy timeout expected (build lock held during touched task)
    part proposedOutcomeTierImplementGateR2 : TestResult { :>> id = "21883dd3-1f09-4f0a-9053-4b082757b177"; :>> outcome = VerdictKind::pass; :>> judgedAgainst = "5b4cdc4cff36c579b0081d8b0466461ab9f3a11f"; :>> judgedAt = "2026-09-11"; :>> judgedBy = "claudeOpus5"; }
    verification proposedOutcomeTierReviewGate : Test { :>> id = "e5647a1d-f691-4ae6-b149-ea5c0f9db15c"; :>> title = "Sprint 663 review gate — three passes per D0172"; :>> createdAt = "2026-09-11"; :>> createdBy = "claudeOpus5"; :>> method = VerificationMethod::inspect; :>> procedureText = "Delivered: the third tier exists in the schema and is decided at the write, never authored by hand; the probe pair is a test in the suite; the readers count it apart. KNOWN CONSEQUENCE, stated not decided: this sprint's own Refine, Standup, Review and CloseOut gates are inspect and Retro is analyze, all judged by the recorder subagent - an AI actor with no ci-run receipt - so from this commit they land proposed, and keel advance reads the ceremony as incomplete until a human judges them. That is the tier working as D0312 B says, and it sits in tension with D0049 (closeOut and retro are AI-recorded and autonomous). Two ways out, neither taken here: dcSetJudgmentWritePath (next on the frontier) gives the human one command to judge a set; or a scaffold change makes the ceremony gates method=test with the verifier's receipt as evidence - that is a CHANGE for the human, not this sprint's. Not delivered: no backfill of standing AI-examined passes (forward-only by D0312 B)."; }
    // RAN: D0388 probe pair against the live binary: AI inspect no receipt landed VerdictKind::proposed count 1; the same by a Person landed pass count 1 (verify663 step 10); known consequence stated in the review section, not decided
    part proposedOutcomeTierReviewGateR1 : TestResult { :>> id = "2246b4cf-f25f-41ee-b040-ffda5670e5bc"; :>> outcome = VerdictKind::proposed; :>> judgedAgainst = "5b4cdc4"; :>> judgedAt = "2026-09-11"; :>> judgedBy = "claudeOpus5"; }
    verification proposedOutcomeTierCloseOutGate : Test { :>> id = "14def86b-f579-4b04-8464-6a07ba2551b2"; :>> title = "Sprint 663 closeOut gate (autonomous, D0049)"; :>> createdAt = "2026-09-11"; :>> createdBy = "claudeOpus5"; :>> method = VerificationMethod::inspect; :>> procedureText = "Sprint 663 closes on the verifier's receipt only (D0425): the touched set with the lib, clippy --all-targets, validate, check-engine, guard --no-receipt, sync-claude --check, the kernel verdict on the enum, and the receipt's own at and stems checked against the run's log. The dcProposedOutcomeTier DoD pass appended by the recorder from that receipt - and, being an inspect judged by an AI with no ci-run receipt, that DoD result itself lands proposed: the item reads not done until a human judges it, which is the first live case of the tier."; }
    // RAN: closed on the verifier receipt verify663 only: touched 704/0, validate 754, check-engine clean, guard 70/0, clippy 0, sync-claude clean, kernel ACCEPTED, probe 1/1
    part proposedOutcomeTierCloseOutGateR1 : TestResult { :>> id = "7b6116a7-d2d8-49e2-b239-50abf1619d37"; :>> outcome = VerdictKind::proposed; :>> judgedAgainst = "5b4cdc4"; :>> judgedAt = "2026-09-11"; :>> judgedBy = "claudeOpus5"; }
    verification proposedOutcomeTierRetroGate : Test { :>> id = "efdb5a7d-f86c-470d-b23d-409d26742df2"; :>> title = "Sprint 663 retro gate (autonomous, D0049)"; :>> createdAt = "2026-09-11"; :>> createdBy = "claudeOpus5"; :>> method = VerificationMethod::analyze; :>> procedureText = "AVOIDABLE-ISSUE SCAN: two new Issues this sprint, both in-field. issue469 (Medium): the verifier subagent's foreground touched run was killed at the harness's ten-minute cap; the issue468 running stub held, nothing false landed, the run was relaunched detached - resolver dcVerifierProcedureIsASkill, the D0425 verifier procedure as a deployed skill instead of retyped prompt text. issue470 (High): the ceremony guard's ORDER check reused orient::gate_passed, so the first sprint recorded under the tier went red at the Stop hook - Implement passed while Refine and Standup were proposed - and the recorder subagent concluded the human must accept five proposed gates; the reader plan663 missed. Resolver D0437 (process-change, proposed for the human): the guard reads the RECORDED set, pass or proposed, and every done-ness reader keeps pass alone. FINDING 1: the tier's first live effect falls on the sprint ceremony itself - every AI-recorded inspect/analyze gate from here on is proposed, so the frontier's next item (dcSetJudgmentWritePath) is not optional polish but the other half of this change; it stays at the frontier's head by declaration order, no reorder needed. FINDING 2, process: one textpatch anchor was misquoted (a hyphen for an em dash) and the helper refused and wrote nothing - D0386 evidenced, second time this session; no item. FINDING 3: the D0388 probe pair was named in the plan before the schema was touched and both cases are now tests, so the check is a Sensor, not a receipt line. FINDING 4, tension to surface: D0049 says closeOut and retro are autonomous; D0312 B says an AI's examined pass is proposed. Both hold at once only if the human judges sets cheaply - that is the case for dcSetJudgmentWritePath and belongs in its refine, not in a Decision here."; }
    // RAN: retro recorded in the sprint file; AVOIDABLE-ISSUE SCAN present; issue469 recorded in-field this sprint (verifier run killed at the harness cap, running stub held) with resolver dcVerifierProcedureIsASkill
    part proposedOutcomeTierRetroGateR1 : TestResult { :>> id = "d419fbba-98bf-45ec-9aee-a5e8cc2afc5c"; :>> outcome = VerdictKind::proposed; :>> judgedAgainst = "5b4cdc4"; :>> judgedAt = "2026-09-11"; :>> judgedBy = "claudeOpus5"; }
    // RAN: retro text re-read after edit: AVOIDABLE-ISSUE SCAN names issue469 (2 references) and issue470 (1 reference); tree at receipt: guard ALL PASS
    part proposedOutcomeTierRetroGateR2 : TestResult { :>> id = "f447c3dc-5ebd-4034-aad7-3f306a79512d"; :>> outcome = VerdictKind::proposed; :>> judgedAgainst = "5b4cdc4cff36c579b0081d8b0466461ab9f3a11f"; :>> judgedAt = "2026-09-11"; :>> judgedBy = "claudeOpus5"; }
}
