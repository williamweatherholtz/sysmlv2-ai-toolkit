// ProjectDeliveryS410 — Sprint 410: the pre-push behind-check (issue209): a raw push gated in isolation is refused at the pusher's own terminal - proven in a two-clone scratch. EXECUTE. 1 pts.
package ProjectDeliveryS410 {
    private import EngineElement::*;
    private import EngineWork::*;
    private import EngineVerification::*;
    private import EngineRelationships::*;

    #CharteredBy dependency from prePushBehindCheckStory to d0191;

    part prePushBehindCheckStory : Story {
        :>> id = "8126194d-f964-4d84-bf88-87489d15471d";
        :>> title = "Sprint 410: raw pushes meet the loop (1 pts)";
        :>> createdAt = "2026-08-22"; :>> createdBy = "claudeFable5"; :>> kind = WorkKind::code; :>> priority = WorkPriority::p0; :>> owner = "claudeFable5"; :>> estimatedPoints = 1;
    }

    action def DeliveryRunS410 {
        action storyPrePushBehindCheck;
        verification storyPrePushBehindCheckDoD : Test { :>> id = "e3c8601d-22db-4937-8ea9-b5b3e84c2e7b"; :>> method = VerificationMethod::test; :>> procedureText = "DELIVERED: dcPrePushBehindCheck (resolves issue209). .githooks/pre-push refuses a main push whose HEAD is not a descendant of the FRESHLY-FETCHED trunk, naming keel land as the sanctioned path (srK13 deny-and-provide) - behind-ness detection only, never a duplicate full gate (keel land already gates the merged tree; D0054). Non-main refs pass untouched (tags, scratch branches); a fetch failure REFUSES rather than allowing (K2). PROVEN IN A TWO-CLONE SCRATCH: clone B diverged from a trunk clone A had advanced - B's raw push exited 1 with the REFUSED message naming the rule and the path; after B fetched and merged (the keel-land shape), the same push exited 0. The point joined the enforcementPoints inventory and the control-events declaration (record=inventory - a shell hook cannot reach the ledger); guard 45 re-ran clean at 13 declared. Executable bit set in the index so the hook ships runnable."; }
        part storyPrePushBehindCheckDoDR1 : TestResult { :>> id = "641397e1-6405-4053-987a-74ff5abc1bbe"; :>> outcome = VerdictKind::pass; :>> judgedAgainst = "42e5c6b"; :>> judgedAt = "2026-08-22"; :>> judgedBy = "claudeFable5"; }
    }

    verification prePushBehindCheckRefineGate : Test { :>> id = "97e8ff7f-db53-47eb-abb8-f4a14c4a8a0b"; :>> title = "Sprint 410 refine gate (DoR)"; :>> createdAt = "2026-08-22"; :>> createdBy = "claudeFable5"; :>> method = VerificationMethod::inspect; :>> procedureText = "DoR. Chartered by d0191's enforcement family; resolves the critique campaign's enforcement-at-the-wrong-layer finding. 1 point."; }
    part prePushBehindCheckRefineGateR1 : TestResult { :>> id = "9a87e930-6a61-4feb-ae9b-99f749f97296"; :>> outcome = VerdictKind::pass; :>> judgedAgainst = "42e5c6b"; :>> judgedAt = "2026-08-22"; :>> judgedBy = "claudeFable5"; }
    verification prePushBehindCheckStandupGate : Test { :>> id = "c809d8c1-ee95-4ba2-a0d8-a352ffbfa2f1"; :>> title = "Sprint 410 standup gate"; :>> createdAt = "2026-08-22"; :>> createdBy = "claudeFable5"; :>> method = VerificationMethod::inspect; :>> procedureText = "Approach: the cheapest structural close the finding named - force the loop, never duplicate the gate; test against a real bare-remote pair before recording. One environmental trap hit and routed around: the scratch remote at the deep session path failed with Windows filename-too-long, re-run at a short path. No blockers."; }
    part prePushBehindCheckStandupGateR1 : TestResult { :>> id = "b926d7f9-6d7e-41da-87a3-bc56a476ba4e"; :>> outcome = VerdictKind::pass; :>> judgedAgainst = "42e5c6b"; :>> judgedAt = "2026-08-22"; :>> judgedBy = "claudeFable5"; }
    verification prePushBehindCheckImplementGate : Test { :>> id = "ff0ec5a6-f4cf-4615-b805-787acaeff985"; :>> title = "Sprint 410 implement gate"; :>> createdAt = "2026-08-22"; :>> createdBy = "claudeFable5"; :>> method = VerificationMethod::test; :>> procedureText = "Verified by running: diverged push refused (exit 1, message names srDcGateOnMergedTree and keel land), post-merge push passed (exit 0), non-main refs untouched by construction (the case list); guard 45 clean at 13 declared events; inventory row present; hook mode 100755 in the index."; }
    part prePushBehindCheckImplementGateR1 : TestResult { :>> id = "82cdcbe5-ce55-4420-be18-1340f35c9242"; :>> outcome = VerdictKind::pass; :>> judgedAgainst = "42e5c6b"; :>> judgedAt = "2026-08-22"; :>> judgedBy = "claudeFable5"; }
    verification prePushBehindCheckReviewGate : Test { :>> id = "6e3ccae5-1d2e-44bc-9127-56623c04f3d5"; :>> title = "Sprint 410 review gate — three passes per D0172"; :>> createdAt = "2026-08-22"; :>> createdBy = "claudeFable5"; :>> method = VerificationMethod::inspect; :>> procedureText = "PASS 1, CLAIMS: both push outcomes are exit codes from the scratch run in this session. PASS 2, BOUNDARY: an up-to-date-but-isolation-gated push still lands (the finding's own recorded caveat) - the hook forces the FETCH-INTEGRATE half of the loop and keel land remains the path of least resistance for the gate half; stated, not solved. PASS 3, OWN DIFF: the first scratch run's refusal came from the FETCH-FAILURE branch (the too-long path), not the behind branch - which would have been a false pass of the wrong path; caught by reading the message text, re-run cleanly. WHAT A REVIEWER SHOULD ATTACK: the hook trusts refs/heads/main as THE trunk name; a project with a different default branch gets no protection - one-line fix when it bites, named here."; }
    part prePushBehindCheckReviewGateR1 : TestResult { :>> id = "e42738de-6ed7-4797-8da1-aed9d3e1120d"; :>> outcome = VerdictKind::pass; :>> judgedAgainst = "42e5c6b"; :>> judgedAt = "2026-08-22"; :>> judgedBy = "claudeFable5"; }
    verification prePushBehindCheckCloseOutGate : Test { :>> id = "aa0c2369-b9d3-4668-8fdf-fd90184af299"; :>> title = "Sprint 410 closeOut gate (autonomous, D0049)"; :>> createdAt = "2026-08-22"; :>> createdBy = "claudeFable5"; :>> method = VerificationMethod::inspect; :>> procedureText = "Autonomous closeOut (D0049). DoD flipped on the scratch evidence; issue209 resolves; validate + all 45 guards green."; }
    part prePushBehindCheckCloseOutGateR1 : TestResult { :>> id = "22733dd0-2719-4e15-8420-1909ba6d738f"; :>> outcome = VerdictKind::pass; :>> judgedAgainst = "42e5c6b"; :>> judgedAt = "2026-08-22"; :>> judgedBy = "claudeFable5"; }
    verification prePushBehindCheckRetroGate : Test { :>> id = "e188d8ca-cb12-4eba-857c-ae46f9ed2e4f"; :>> title = "Sprint 410 retro gate (autonomous, D0049)"; :>> createdAt = "2026-08-22"; :>> createdBy = "claudeFable5"; :>> method = VerificationMethod::analyze; :>> procedureText = "Autonomous retro (D0049). AVOIDABLE-ISSUE SCAN under rcRecurrence: the wrong-branch-of-the-refusal near-miss (fetch-failure vs behind) is the verify-the-RIGHT-refusal discipline - read the message, not just the exit code; kept as practice, no control needed at one occurrence. WELL: the two-clone scratch harness is now a proven ten-line recipe for any distributed-behavior test. Estimate 1 pt, delivered 1."; }
    part prePushBehindCheckRetroGateR1 : TestResult { :>> id = "0578b9e5-5c0f-45ed-8995-5494e2c30754"; :>> outcome = VerdictKind::pass; :>> judgedAgainst = "42e5c6b"; :>> judgedAt = "2026-08-22"; :>> judgedBy = "claudeFable5"; }
}
