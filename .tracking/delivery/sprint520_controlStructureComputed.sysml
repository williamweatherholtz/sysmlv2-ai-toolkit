// ProjectDeliveryS520 — Sprint 520: keel's control structure is a computed view. EXECUTE. 5 pts.
package ProjectDeliveryS520 {
    private import EngineElement::*;
    private import EngineWork::*;
    private import EngineVerification::*;
    private import EngineRelationships::*;

    #CharteredBy dependency from controlStructureComputedStory to d0284;

    part controlStructureComputedStory : Story {
        :>> id = "2b7c4d1e-8f3a-4b5c-9d6e-7f8091a2b3c4";
        :>> title = "Sprint 520: keel show control-structure - STPA step 2 for the project's own workflow, computed from the facts that wire it (5 pts)";
        :>> createdAt = "2026-09-02"; :>> createdBy = "claudeOpus5"; :>> kind = WorkKind::code; :>> priority = WorkPriority::p0; :>> owner = "claudeOpus5"; :>> estimatedPoints = 5;
    }

    action def DeliveryRunS520 {
        action storyControlStructureComputed;
        verification storyControlStructureComputedDoD : Test { :>> id = "3c8d5e2f-9a4b-4c6d-ae7f-8091a2b3c4d5"; :>> method = VerificationMethod::test; :>> procedureText = "DELIVERED BACKLOG ITEMS: dcControlStructureIsComputed. DONE: keel show control-structure derives every control action and feedback path from facts - hook events in .claude/settings.json, git hooks, workflow steps, CLI facts by effect, declared deciders, the remote's branch protection fetched live and never stored, the console's approve queue, deliverable-manifest drift - and decorates the view's stable roles with the authored residue (anchors, process models with the Issues their false beliefs cite, hazard-to-process edges) when a project has authored it. The safety viewpoint's renderer is bound to the lens by a committed D0067 transform (the registry is human-owned). VERIFY: a fresh scaffold computes the structure with null anchors and an inert channel (not imported - true); removing a hook event removes its action with no model edit; this repository decorates all eight roles; the live remote row reads CI as DETECTIVE (no required checks, no reviews, force-push blocked), computed."; }
        // RAN: cargo test --test control_structure_is_computed 3/3; cargo test --lib view::control_structure 5/5; keel show control-structure . live: 44 actions, 76 feedback, 0 inert, remote fetched live requiresStatusChecks=false requiresReviews=false refusesForcePush=true; keel guard viewpoint-renderer -> safety no longer planned (2 warnings remain: baselines, requirements); clippy clean
        part storyControlStructureComputedDoDR1 : TestResult { :>> id = "4d9e6f30-ab5c-4d7e-bf80-91a2b3c4d5e6"; :>> outcome = VerdictKind::pass; :>> judgedAgainst = "7459b45"; :>> judgedAt = "2026-09-02"; :>> judgedBy = "claudeOpus5"; }
    }

    verification controlStructureComputedRefineGate : Test { :>> id = "5eaf7041-bc6d-4e8f-c091-a2b3c4d5e6f7"; :>> title = "Sprint 520 refine gate (DoR)"; :>> createdAt = "2026-09-02"; :>> createdBy = "claudeOpus5"; :>> method = VerificationMethod::inspect; :>> procedureText = "READY because every source the DoD names was already a fact in the tree or fetchable - the only missing one, the CLI facts, landed as sprint 519 the same day and for this reason. The design question at refine was identity: does the view depend on the authored anchors existing? Answered no - roles are the view's own, anchors decorate - because a fresh project has every authority and has authored nothing, and the view must describe it."; }
    verification controlStructureComputedStandupGate : Test { :>> id = "6fb08152-cd7e-4f90-d1a2-b3c4d5e6f708"; :>> title = "Sprint 520 standup gate"; :>> createdAt = "2026-09-02"; :>> createdBy = "claudeOpus5"; :>> method = VerificationMethod::inspect; :>> procedureText = "TWO CHOICES with a cost. (1) The remote's rules are fetched live inside a lens - a network call in a read command. Accepted because a stored copy would be a claim about the remote the remote can falsify silently; the cost is paid by KEEL_OFFLINE for tests and by an honest unverified row when gh is absent. (2) accept is attributed to the human by a const in the view, which is a claim about the write layer; it is held equal to write::HUMAN_ONLY_WRITE_COMMANDS by a test, so it is a fact about the code and not a label. The first run showed two inert controllers and a process acted on by nothing; the first two were derivations not yet written (remote refusal from the live row, console approval from serve), the third is TRUE - keel has no control action on the deliverable - and stays visible."; }
    verification controlStructureComputedImplementGate : Test { :>> id = "70c19263-de8f-4a01-e2b3-c4d5e6f70819"; :>> title = "Sprint 520 implement gate"; :>> createdAt = "2026-09-02"; :>> createdBy = "claudeOpus5"; :>> method = VerificationMethod::test; :>> procedureText = "RAN: three integration tests on shallow C:/kt roots (a fresh init computes with null anchors; removing UserPromptSubmit from settings.json removes hookUserPromptSubmit; this repo decorates all eight roles and cites issue343 from pmHuman); five unit tests on the pure halves; clippy clean after the view was split into gather, decoration and render for the line budget. The safety renderer rebinding ran as a dry run, an apply, and an idempotent second run. The scaffold's inert channel failed the first version of the test and was found to be TRUE - the channel is a unit a project imports - so the test now pins that truth rather than hiding it."; }
    verification controlStructureComputedReviewGate : Test { :>> id = "81d2a374-ef90-4b12-f3c4-d5e6f708192a"; :>> title = "Sprint 520 review gate — three passes per D0172"; :>> createdAt = "2026-09-02"; :>> createdBy = "claudeOpus5"; :>> method = VerificationMethod::inspect; :>> procedureText = "THREE PASSES. (1) IS ANYTHING AUTHORED THAT COULD BE COMPUTED: the roles and the process-for-family mapping are the view's judgments, visible in the output as role and actsOn so they can be argued with; nothing about a specific hook, workflow or command is written by hand. (2) DOES THE VIEW CLAIM MORE THAN ITS SOURCES: the remote row says unverified rather than guessing; an absent source contributes nothing and the role reads inert; the deliverable's zero is reported, not filled. (3) IS THE HUMAN-OWNED EDIT SANCTIONED: one field on one item through a committed, idempotent D0067 transform, the same path the ten renderer edits took on 2026-09-01."; }
    verification controlStructureComputedCloseOutGate : Test { :>> id = "92e3b485-f0a1-4c23-04d5-e6f708192a3b"; :>> title = "Sprint 520 closeOut gate (autonomous, D0049)"; :>> createdAt = "2026-09-02"; :>> createdBy = "claudeOpus5"; :>> method = VerificationMethod::inspect; :>> procedureText = "CLOSED. The human's first step is done in both halves: residue authored (518), rest computed (520), prerequisite facts (519). Four computed readings stand as the first input to the STPA process: CI is detective; the deliverable is acted on by no keel command; a scaffold's channel is inert until imported; the human's direction has no receiving control. dcStpaProcessForKeel and dcVerificationByAuthority are next and both were written to wait on exactly this."; }
    verification controlStructureComputedRetroGate : Test { :>> id = "a3f4c596-01b2-4d34-15e6-f708192a3b4c"; :>> title = "Sprint 520 retro gate (autonomous, D0049)"; :>> createdAt = "2026-09-02"; :>> createdBy = "claudeOpus5"; :>> method = VerificationMethod::analyze; :>> procedureText = "no new item - already tracked: the sprint's findings are the four computed readings, which are inputs to dcStpaProcessForKeel rather than Issues in themselves - CI being detective is a design fact under D0129 and branch policy, not a defect until a UCA says what it costs. The one thing worth naming is the arc of three sprints: an authored document refused by two guards, a residue that passed, and a computed view that made the residue's decoration optional. That is Invariant 1 enforced by controls that never mention it."; }
}
