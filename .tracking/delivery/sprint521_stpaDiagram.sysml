// ProjectDeliveryS521 — Sprint 521: the STPA diagram becomes a process with a tool. CHANGE. 3 pts.
package ProjectDeliveryS521 {
    private import EngineElement::*;
    private import EngineWork::*;
    private import EngineVerification::*;
    private import EngineRelationships::*;

    #CharteredBy dependency from stpaDiagramStory to d0285;

    part stpaDiagramStory : Story {
        :>> id = "3f8a3907-29bb-460b-a79c-b1760a8f283f";
        :>> title = "Sprint 521: the control-structure diagram holds the human's five conventions by construction - process, skill, tool, and the reviewed render on the page (3 pts)";
        :>> createdAt = "2026-09-02"; :>> createdBy = "claudeOpus5"; :>> kind = WorkKind::modeling; :>> priority = WorkPriority::p0; :>> owner = "claudeOpus5"; :>> estimatedPoints = 3;
    }

    action def DeliveryRunS521 {
        action storyStpaDiagram;
        verification storyStpaDiagramDoD : Test { :>> id = "705a52e3-414e-4038-b0ae-3d3d8cea502f"; :>> method = VerificationMethod::demo; :>> procedureText = "DELIVERED: the stpa-diagram process (sd0Compute..sd6Verify) and skill; .engine/tools/stpa_diagram.py rendering keel show control-structure JSON as an SVG in which the five conventions hold by construction - authority descending, control down-left and feedback up-right, ortholinear with one channel per edge and unique slots so no segments are collinear, every edge labelled with what passes and placed off other edges' verticals with a leader when the channel is short, semicircular hops at crossings; the human's four utterances recorded verbatim (st067-st070) with the story that translates them (us072); the port into the binary chartered (dcStpaDiagramInTheBinary, D0221); the page republished with the reviewed diagram. VERIFY: the tool's output on the live JSON is byte-identical to the render the human reviewed; the render was screenshotted at full size and zoomed at a crossing before publishing; process-skill, process-applicability, tool-reference and doc-sync pass with the two new files."; }
        // RAN: diff of the tool's output against the reviewed render -> IDENTICAL; playwright screenshots v3, v4, v5 (full page) and two 4x crops (a label hiding risers in v3 -> fixed by placement search; hops visible in v4 crop); keel show control-structure . | python .engine/tools/stpa_diagram.py -> 29582 bytes; keel guard . ALL PASS after the doc-sync edit
        part storyStpaDiagramDoDR1 : TestResult { :>> id = "a9dafbc6-e4af-4b59-a154-9c9ef6056a30"; :>> outcome = VerdictKind::pass; :>> judgedAgainst = "7459b45"; :>> judgedAt = "2026-09-02"; :>> judgedBy = "claudeOpus5"; }
    }

    verification stpaDiagramRefineGate : Test { :>> id = "c4ed9fda-b930-4c4d-8086-f9ee6549ceb8"; :>> title = "Sprint 521 refine gate (DoR)"; :>> createdAt = "2026-09-02"; :>> createdBy = "claudeOpus5"; :>> method = VerificationMethod::inspect; :>> procedureText = "READY the moment the human said save this: the conventions had been stated in their words across three messages and a render that met all of them existed and had been looked at. The one design question was where the conventions live - a checklist the drawer reads, or a tool that cannot violate them. The drawer had just violated them three times, so the tool."; }
    verification stpaDiagramStandupGate : Test { :>> id = "19504ac9-15c5-4890-9fab-bab6f8066a7e"; :>> title = "Sprint 521 standup gate"; :>> createdAt = "2026-09-02"; :>> createdBy = "claudeOpus5"; :>> method = VerificationMethod::inspect; :>> procedureText = "TWO CHOICES. (1) Python under .engine/tools as the interim rather than a Rust port now: the reviewed render existed and was right, a byte-for-byte port would have delayed saving the conventions for no reader, and D0221 is honoured by chartering the port with the interim named as such - the shape conformance_lane.py has held since D0132. (2) Mermaid was abandoned rather than tuned: a dagre layout cannot hold a vertical authority axis against seventy upward feedback edges, and the labels it allows are edge strings, not the multi-line records the human asked for. The heredoc ate the backslashes in the tool's tail on first write (the known hazard); fixed with a direct edit and the tool parse-checked before it was run."; }
    verification stpaDiagramImplementGate : Test { :>> id = "e9c3a1b2-5d47-4f68-9a0b-1c2d3e4f5a6b"; :>> title = "Sprint 521 implement gate"; :>> createdAt = "2026-09-02"; :>> createdBy = "claudeOpus5"; :>> method = VerificationMethod::demo; :>> procedureText = "RAN: five renders. v1 mermaid (rejected by the human: no axis, unlabelled). v2 curved (rejected: linear). v3 straight diagonals (rejected: ortholinear, no overlap, hops). v4 orthogonal with own channels and hops - screenshot and a 4x crop showed hops rendering and a label hiding two feedback risers. v5 with the placement search and a leader for short channels - screenshot clean. The tool was then created from the v5 renderer and its output diffed against the reviewed SVG: identical."; }
    verification stpaDiagramReviewGate : Test { :>> id = "f0d4b2c3-6e58-4a79-ab1c-2d3e4f5a6b7c"; :>> title = "Sprint 521 review gate — three passes per D0172"; :>> createdAt = "2026-09-02"; :>> createdBy = "claudeOpus5"; :>> method = VerificationMethod::inspect; :>> procedureText = "THREE PASSES. (1) ARE THE CONVENTIONS THE HUMAN'S OR MINE: each of the five is quoted from st067-st069 in the process header; the sixth thing - controllers in the gaps so no line crosses a box - is a consequence of no-overlap, and is stated as such. (2) IS ANYTHING DRAWN BY HAND: the tool reads only the JSON; role names and process order are the view's; label text is the edge's own record. (3) IS THE INTERIM HONEST: the process, skill and Decision each name the tool as interim and the port as chartered; tool-reference sees the tool exist."; }
    verification stpaDiagramCloseOutGate : Test { :>> id = "01e5c3d4-7f69-4b8a-bc2d-3e4f5a6b7c8d"; :>> title = "Sprint 521 closeOut gate (autonomous, D0049)"; :>> createdAt = "2026-09-02"; :>> createdBy = "claudeOpus5"; :>> method = VerificationMethod::inspect; :>> procedureText = "CLOSED. The diagram the human can read is on the page; the way to draw it is a process any project on this engine inherits; the port is on the frontier."; }
    verification stpaDiagramRetroGate : Test { :>> id = "12f6d4e5-807a-4c9b-cd3e-4f5a6b7c8d9e"; :>> title = "Sprint 521 retro gate (autonomous, D0049)"; :>> createdAt = "2026-09-02"; :>> createdBy = "claudeOpus5"; :>> method = VerificationMethod::analyze; :>> procedureText = "no new item - already tracked: the finding is the one the process header records - three wrong renders before a right one, each corrected by the human naming a convention I could have asked for up front. The generalisable rule is the D0157 read-back: show the first render and ask what is wrong with it before polishing, which is what happened, at the cost of three rounds instead of one. The tooling hazard (heredoc backslashes) is already a recorded feedback memory."; }
}
