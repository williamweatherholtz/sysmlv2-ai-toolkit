// ProjectDeliveryS669 — Sprint 669: The demonstration clause of D0312 option B, the one that separates B from A: a method=demo pass whose RAN receipt IS a command a machine can re-run is exercised in substance, so it stays a pass at the write instead of landing proposed, and keel reverify --demos re-runs every such receipt at HEAD and records what happened - a fresh pass carrying the same receipt, or a fail naming the command and its exit code. A demo a machine re-runs is meat; a demo a human must read is a checklist item (the human's words, 2026-09-11).. EXECUTE. 3 pts.
package ProjectDeliveryS669 {
    private import EngineElement::*;
    private import EngineWork::*;
    private import EngineVerification::*;
    private import EngineRelationships::*;

    #CharteredBy dependency from replayableDemoStaysAPassStory to d0444;

    part replayableDemoStaysAPassStory : Story {
        :>> id = "af311390-b142-4c5a-92ed-d6c80026a2bf";
        :>> title = "Sprint 669: The demonstration clause of D0312 option B, the one that separates B from A: a method=demo pass whose RAN receipt IS a command a machine can re-run is exercised in substance, so it stays a pass at the write instead of landing proposed, and keel reverify --demos re-runs every such receipt at HEAD and records what happened - a fresh pass carrying the same receipt, or a fail naming the command and its exit code. A demo a machine re-runs is meat; a demo a human must read is a checklist item (the human's words, 2026-09-11). (3 pts)";
        :>> createdAt = "2026-09-11"; :>> createdBy = "claudeOpus5"; :>> kind = WorkKind::code; :>> priority = WorkPriority::p0; :>> owner = "claudeOpus5"; :>> estimatedPoints = 3;
    }

    action def DeliveryRunS669 {
        action storyReplayableDemoStaysAPass;
        verification storyReplayableDemoStaysAPassDoD : Test { :>> id = "d32872c1-5317-4bdf-9255-97ee7a45131f"; :>> method = VerificationMethod::test; :>> procedureText = "write::proposed_tier keeps an AI demo pass whose evidence is replayable (reverify::is_replayable: one line, a declared [demo] prefix from .engine/contracts/reverify.toml, every token in the command alphabet and none a function word) - demo only, an inspect with the same receipt still lands proposed. keel reverify --demos scans every demo Test whose latest result is a pass with a replayable receipt, re-runs it (a leading keel is this binary invoked directly with the receipt's tokens; anything else runs through the shell, in its own CARGO_TARGET_DIR), and appends pass with the same receipt on exit 0 or fail whose evidence begins replay of and names the exit code; exit 2 with nothing written when no prefix is declared. attestation: Proposal carries its ProposalKind (Proposed, ProposedDemo, ReplayableDemo); replayable demo passes join the D0443 sample pool as judged false and leave it when a human's later result is the latest; proposed counts proposals alone; the JSON gains demoReplayable and demoProposed. The [demo] section ships in the scaffold. Tests: write.rs D0388 pair (keel show control-structure . --svg -> pass; looked at the picture -> proposed; rm -rf target -> proposed; inspect -> proposed; no section -> proposed), reverify.rs receipt-shape and latest-result tests, attestation.rs pool test, and integration test reverify_demos_replays_each_receipt (keel version replays green and re-stamps; cmd /C exit 3 replays red naming exit 3; prose demo never replayed; no section -> inert exit 2)."; }
        // RAN: verifier receipt 2026-09-11 head=6d9586e: keel suite --touched outcome=pass passed=731 failed=0 seconds=885; validate 763 tracking file(s) validated clean.; exit 0; guard PASS exit 0 (amendment); probe pair ok; DISCREPANCIES: NONE
        part storyReplayableDemoStaysAPassDoDR1 : TestResult { :>> id = "d3c0ffe0-881b-40ac-a567-9a7150185968"; :>> outcome = VerdictKind::pass; :>> judgedAgainst = "6d9586e"; :>> judgedAt = "2026-09-11"; :>> judgedBy = "claudeOpus5"; }
    }

    verification replayableDemoStaysAPassRefineGate : Test { :>> id = "ae80457e-7b07-4a38-826e-ab09871c91e6"; :>> title = "Sprint 669 refine gate (DoR)"; :>> createdAt = "2026-09-11"; :>> createdBy = "claudeOpus5"; :>> method = VerificationMethod::inspect; :>> procedureText = "Chartered by D0444 (proposed, HELD process-change: the write path's tier rule, a new reverify flag and a new contract key wait for the human's word, D0337; NOT A FORK - D0312 B chose the clause). Depends on dcProposedOutcomeTier (sprint 663, done) and dcSetJudgmentWritePath (sprint 668, done). 3 points: three modules touched, a new verb path with process spawning, two test tiers. The receipt-shape rule was MEASURED before it was written: scripts/probes-style census over the tree's 283 prefixed RAN receipts - prefix alone admits 283 narratives, alphabet alone admits 1, alphabet plus sixteen function words admits 0."; }
    // RAN: verifier receipt 2026-09-11 head=6d9586e: chartered by d0444 (proposed, HELD process-change); validate 763 tracking file(s) validated clean.; exit 0
    part replayableDemoStaysAPassRefineGateR1 : TestResult { :>> id = "81e8d65d-18e0-4117-93f0-27ab85d65085"; :>> outcome = VerdictKind::proposed; :>> judgedAgainst = "6d9586e"; :>> judgedAt = "2026-09-11"; :>> judgedBy = "claudeOpus5"; }
    verification replayableDemoStaysAPassStandupGate : Test { :>> id = "15af5566-feff-43c4-80f5-54e38b00bdeb"; :>> title = "Sprint 669 standup gate"; :>> createdAt = "2026-09-11"; :>> createdBy = "claudeOpus5"; :>> method = VerificationMethod::inspect; :>> procedureText = "Order: reverify.rs (DemoConfig, prefixes, is_replayable, demo_tests_in_text, demo_replays_in_text, replay_demos) then write.rs (proposed_tier consults it) then attestation.rs (ProposalKind, the pool, the counts, the JSON) then main.rs/cli_facts/commands.sysml (the flag, kept equal) then reverify.toml (the section) then the integration test then D0444's text amended with the measured rule. Blocker met and fixed in-sprint: the first replay of a keel receipt went through cmd /C with the binary path quoted and cmd stripped the wrong quotes, so keel version replayed as a fail; a keel receipt now runs this binary directly with the whitespace-split tokens (exact by the alphabet rule) and the integration test caught it before anything was recorded."; }
    // RAN: verifier receipt: touched set stems=[attestation, cli_facts, reverify, write] changed=[attestation, cli_facts, main, reverify, write] MATCH lib=true head=6d9586e; launch=1789120810 at=1789121698 at>launch ok
    part replayableDemoStaysAPassStandupGateR1 : TestResult { :>> id = "3b7e1900-a9a8-4c5c-ad72-620a61bcec89"; :>> outcome = VerdictKind::proposed; :>> judgedAgainst = "6d9586e"; :>> judgedAt = "2026-09-11"; :>> judgedBy = "claudeOpus5"; }
    verification replayableDemoStaysAPassImplementGate : Test { :>> id = "a77effe1-dd87-4068-bda7-649a7d80ff5f"; :>> title = "Sprint 669 implement gate"; :>> createdAt = "2026-09-11"; :>> createdBy = "claudeOpus5"; :>> method = VerificationMethod::test; :>> procedureText = "keel-cli/src/reverify.rs: [demo] replayable in ReverifyConfig, parse_demo_prefixes/demo_prefixes, PROSE_WORDS, is_replayable_with/is_replayable, DemoReplay, demo_tests_in_text, demo_replays_in_text (latest result per demo Test, same-line or preceding RAN line, ci-run excluded), demo_replays, Replay::{ThisBinary,Shell} with replay_command/replay_status, replay_demos. keel-cli/src/write.rs: proposed_tier's D0444 clause after the ci-run check. keel-cli/src/attestation.rs: Proposal.kind, ProposalKind, proposals_in_text(text, human, prefixes), ProposalCounts.demo_replayable/demo_proposed, the JSON keys and the text line. keel-cli/src/main.rs: --demos. keel-cli/src/cli_facts.rs and .engine/cli/commands.sysml: cliReverify invocation and synopsis. .engine/contracts/reverify.toml: the [demo] section (keel , cargo test, python scripts/probes/). keel-cli/tests/reverify_demos_replays_each_receipt.rs: the end-to-end pair. keel-cli/tests/judge_set_records_each_item.rs: the JSON asserts carry the two new keys. .engine/docs/usage.md and CLAUDE.md section 5: the tier rule and the flag. D0444 decision text: the measured receipt-shape rule."; }
    // RAN: verifier receipt: keel suite --touched outcome=pass passed=731 failed=0 seconds=885; cargo clippy --release --all-targets -D warnings exit 0; probe pair a_replayable_demo_receipt_stays_a_pass_and_demos_replays_it_recording_each_verdict: ok, without_a_demo_section_every_demo_pass_is_a_proposal_and_demos_is_inert: ok; unit probes write::tests::a_demo_pass_whose_receipt_is_a_declared_command_stays_a_pass: ok, reverify::tests::a_receipt_is_replayable_only_when_it_is_the_command_alone: ok, attestation::tests::a_replayable_demo_pass_is_in_the_pool_as_a_pass_and_leaves_when_a_human_judges_it: ok
    part replayableDemoStaysAPassImplementGateR1 : TestResult { :>> id = "1e4f50fe-f050-475b-b5c0-3641259c1519"; :>> outcome = VerdictKind::pass; :>> judgedAgainst = "6d9586e"; :>> judgedAt = "2026-09-11"; :>> judgedBy = "claudeOpus5"; }
    verification replayableDemoStaysAPassReviewGate : Test { :>> id = "37725f36-b34b-4b3a-bcec-9e97e2988bb1"; :>> title = "Sprint 669 review gate — three passes per D0172"; :>> createdAt = "2026-09-11"; :>> createdBy = "claudeOpus5"; :>> method = VerificationMethod::inspect; :>> procedureText = "Delivered: a demo receipt that names a command is a procedure anyone can repeat, and the binary repeats it - the pass stands on the replay, not on the AI's word, and a replay that fails is a recorded fail with the exit code, not a quiet proposal. On this tree today demoReplayable is 0: none of the 283 prefixed receipts is the command alone, which is the census's finding and the reason the rule is strict - the first replayable receipts will be written under it, forward-only. Residual: reverify --demos runs in no hook and no CI; when it runs is the human's to schedule by a later Decision."; }
    // RAN: verifier receipt: attestation JSON {'proposed': 31, 'sampled': 18, 'judged': 0, 'awaiting': 31, 'demoReplayable': 0, 'demoProposed': 0, 'sampling': '50%'}; check-engine .engine instance files validated clean (kernel-free; D0112 phase 2).; exit 0; sync-claude --check claude-surface: keel-owned subset matches this binary's generator (46 registry skill(s)); exit 0
    part replayableDemoStaysAPassReviewGateR1 : TestResult { :>> id = "6676bc87-6b29-43e2-9aea-f471ec02d39b"; :>> outcome = VerdictKind::proposed; :>> judgedAgainst = "6d9586e"; :>> judgedAt = "2026-09-11"; :>> judgedBy = "claudeOpus5"; }
    verification replayableDemoStaysAPassCloseOutGate : Test { :>> id = "eb733fd5-d87c-4de4-8a86-262130d74efb"; :>> title = "Sprint 669 closeOut gate (autonomous, D0049)"; :>> createdAt = "2026-09-11"; :>> createdBy = "claudeOpus5"; :>> method = VerificationMethod::inspect; :>> procedureText = "Sprint 669 closes on the verifier's receipt only (D0425). dcReplayableDemoStaysAPass gets its DoD result. D0444 stays proposed for the human (D0337). Nothing else in the frontier moved."; }
    // RAN: verifier receipt AMENDMENT 2026-09-11 04:23:20: validate 763 tracking file(s) validated clean.; exit 0; guard --no-receipt PASS — 38 actionable warning(s) across 7 guard(s); exit 0; check-engine clean exit 0; DISCREPANCIES: NONE
    part replayableDemoStaysAPassCloseOutGateR1 : TestResult { :>> id = "9a00babd-924e-4c1f-b13f-4b8cead5b713"; :>> outcome = VerdictKind::proposed; :>> judgedAgainst = "6d9586e"; :>> judgedAt = "2026-09-11"; :>> judgedBy = "claudeOpus5"; }
    verification replayableDemoStaysAPassRetroGate : Test { :>> id = "c26d78d5-c6b9-40d2-bee9-52761991a969"; :>> title = "Sprint 669 retro gate (autonomous, D0049)"; :>> createdAt = "2026-09-11"; :>> createdBy = "claudeOpus5"; :>> method = VerificationMethod::analyze; :>> procedureText = "AVOIDABLE-ISSUE SCAN: no new Issue this sprint. FINDING 1 (kept as a test, not an Issue): the cmd /C quoting fault was caught by the integration test's D0388 positive before any record was written - the test that names its positive and negative before the tree is read is what turned a wrong-quoting bug into a red test instead of a recorded fail on a real demo. FINDING 2: the receipt-shape census (283 prefixed, 1 alphabet-only false positive, 0 with function words) was run before the rule was coded (D0388) and is quoted in D0444's text; the census script lives in the session scratchpad only and is not a Sensor - tracked as dcReceiptShapeCensusIsASensor (added this commit): the census becomes scripts/probes/receipt_shape_census.py with its D0388 probe pair, so loosening the rule re-runs the measurement first. FINDING 3: clippy's -D warnings found five doc/style items after the tests were green; run clippy with the tests, not after them."; }
    // RAN: verifier receipt AMENDMENT: guard PASS exit 0 after retro-backlog fix (dcReceiptShapeCensusIsASensor added to backlog and named in the retro); original receipt guard line was FAIL retro-backlog before that fix; DISCREPANCIES: NONE
    part replayableDemoStaysAPassRetroGateR1 : TestResult { :>> id = "0e71f67e-ef2b-4ca9-a217-0a0ab7ad3f68"; :>> outcome = VerdictKind::proposed; :>> judgedAgainst = "6d9586e"; :>> judgedAt = "2026-09-11"; :>> judgedBy = "claudeOpus5"; }
}
