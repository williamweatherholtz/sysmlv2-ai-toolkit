// ProjectDeliveryS622 — Sprint 622: Sprint 622 makes supersession say itself once (dcSupersessionIsSaidOnce, D0384 option A on the human's word 2026-09-09, D0398 the schema record): the Supersede edge is authoritative and carries its scope, DecisionStatus::superseded leaves the authored vocabulary, and every reader of a Decision's standing - the queue first - computes it from the edge.. EXECUTE. 5 pts.
package ProjectDeliveryS622 {
    private import EngineElement::*;
    private import EngineWork::*;
    private import EngineVerification::*;
    private import EngineRelationships::*;

    #CharteredBy dependency from supersessionSaidOnceStory to d0384;

    part supersessionSaidOnceStory : Story {
        :>> id = "a10a7979-d3fe-4c46-b9c6-973231aa9b8f";
        :>> title = "Sprint 622: Sprint 622 makes supersession say itself once (dcSupersessionIsSaidOnce, D0384 option A on the human's word 2026-09-09, D0398 the schema record): the Supersede edge is authoritative and carries its scope, DecisionStatus::superseded leaves the authored vocabulary, and every reader of a Decision's standing - the queue first - computes it from the edge. (5 pts)";
        :>> createdAt = "2026-09-09"; :>> createdBy = "claudeOpus5"; :>> kind = WorkKind::code; :>> priority = WorkPriority::p0; :>> owner = "claudeOpus5"; :>> estimatedPoints = 5;
    }

    action def DeliveryRunS622 {
        action storySupersessionSaidOnce;
        verification storySupersessionSaidOnceDoD : Test { :>> id = "d9764a6c-c9e3-46e3-be71-b432cac0c137"; :>> method = VerificationMethod::test; :>> procedureText = "DONE MEANS: a Decision with an incoming #Supersede edge never appears in pendingAcceptances or any queue, shown by constructing that pair in a test rather than reading this tree; DecisionStatus::superseded cannot be authored - the instance gate (keel check-engine under .engine, keel validate under .tracking) refuses it as an unknown enum member; #SupersedeClause reverses one clause and leaves its target in force, so d0129 (never rebase) stays in the accepted set; the seven status values and eleven edges move by a committed D0067 transform whose dry run reconciles control totals and whose hash check proves nothing else in those files moved; record decision authors the clause form; D0384 records the choice with its cost and D0398 the schema shape. VERIFY: integration tests over a fixture - a proposed Decision with an incoming Supersede edge is absent from pending-acceptances and authority-queue while a proposed sibling is present, an accepted Decision with an incoming SupersedeClause edge stays counted accepted, and a file carrying DecisionStatus::superseded fails check-engine naming the member; the migration dry run and apply report equal totals; keel guard, validate, check-engine green; the kernel accepts the construct; CLAUDE.md and guards.md state the rule."; }
        // RAN: cargo test --release --test supersession_is_said_once 3/3 on a fresh scaffold (constructed pair: d0001 proposed + retired by d0003 absent from show authority-queue and orient pendingAcceptances while d0003/d0004 present; report governance 1 accepted / 1 retired of 4 total with d0002 under a SupersedeClause edge; check-engine FAILS naming unknown member superseded / DecisionStatus; --supersedes + --supersedes-clause on one target refused, nothing written); mod.rs standing_is_the_status_minus_the_edge + pending test with d0004 retired by edge; transform dry run {7,3,0} -> {0,7,7} hash 4b800cde279bf98a EQUAL, --apply 18 files, re-run idempotent; conformance_lane --construct ACCEPTED; keel validate 708 clean; check-engine clean; keel guard ALL PASS; clippy --all-targets clean; keel suite 625 passed 0 failed (receipt ae8e4d788476, after a first run whose one failure was run_all_is_deterministic reading the live tree while this session edited two skills mid-run); CLAUDE.md 1.4/4, guards.md, syntax-notes state the rule
        part storySupersessionSaidOnceDoDR1 : TestResult { :>> id = "50c3250a-2676-470c-8afe-80dcc683c9e5"; :>> outcome = VerdictKind::pass; :>> judgedAgainst = "9369863"; :>> judgedAt = "2026-09-09"; :>> judgedBy = "claudeOpus5"; }
    }

    verification supersessionSaidOnceRefineGate : Test { :>> id = "d63dd988-c947-452b-9246-918c8e7be347"; :>> title = "Sprint 622 refine gate (DoR)"; :>> createdAt = "2026-09-09"; :>> createdBy = "claudeOpus5"; :>> method = VerificationMethod::inspect; :>> procedureText = "Scope: .engine/schema/core/relationships.sysml (SupersedeClause) and work.sysml (enum); keel-cli/src/view/mod.rs (retired set, every proposed/accepted reader), reports.rs, critique.rs, staleness.rs, deck.rs, guards.rs judgment-request-quality; write.rs + main.rs (--supersedes-clause); .engine/tools/migrations/2026-09-09-supersede-scope.py; 11 decision files by transform; docs. Charter d0384 (accepted A), schema record d0398 (plan-covered). Out of scope: a fourth status value; retyping the 45 Need/Requirement scope-cut edges (they retire whole targets and stay #Supersede). Estimate 5 points: a frozen-schema change with a migration and a dozen readers. DoR: points set, charter d0384, scope clear, DoD authored, no blocking dependency."; }
    part supersessionSaidOnceRefineGateR1 : TestResult { :>> id = "c0199173-6dfb-4359-8fa8-70274ff58cab"; :>> outcome = VerdictKind::pass; :>> judgedAgainst = "9369863"; :>> judgedAt = "2026-09-09"; :>> judgedBy = "claudeOpus5"; }
    verification supersessionSaidOnceStandupGate : Test { :>> id = "b95e545d-7728-4745-85a3-d470d04f939c"; :>> title = "Sprint 622 standup gate"; :>> createdAt = "2026-09-09"; :>> createdBy = "claudeOpus5"; :>> method = VerificationMethod::inspect; :>> procedureText = "Plan: (1) schema + kernel check (done: ACCEPTED); (2) Model::retired + in_force helpers, readers rewired; (3) write path clause form; (4) transform with dry-run reconcile, apply, post-reconcile; (5) tests: fixture-constructed pair, validate refusal, clause-in-force; (6) docs, guards.md, CLAUDE.md; (7) gates, suite, land."; }
    part supersessionSaidOnceStandupGateR1 : TestResult { :>> id = "84c7f98d-bc3e-4d57-b649-d26d709e2fa7"; :>> outcome = VerdictKind::pass; :>> judgedAgainst = "9369863"; :>> judgedAt = "2026-09-09"; :>> judgedBy = "claudeOpus5"; }
    verification supersessionSaidOnceImplementGate : Test { :>> id = "8626545c-2923-498f-b118-85b94ec478ec"; :>> title = "Sprint 622 implement gate"; :>> createdAt = "2026-09-09"; :>> createdBy = "claudeOpus5"; :>> method = VerificationMethod::test; :>> procedureText = "RAN: 2026-09-09. Schema: relationships.sysml declares Supersede + SupersedeClause, work.sysml enum is { proposed; accepted; rejected; } (kernel: conformance_lane --construct ACCEPTED). Readers: Model::retired / Model::standing in view/mod.rs, rewired in compute_attestation, review_queue_json, compute_issue_resolution, proposed_decisions, blocked_by, decision follow-through, two-proposed-per-issue, authority-queue; critique.rs, reports.rs (governance card reads accepted / retired), staleness.rs; kernel-free keel_cli::supersede_targets for deck.rs, guards.rs judgment-request-quality, release-recorded and acceptance-binds-to-text (a retired Decision is skipped). Write path: --supersedes-clause / supersedes-clause: authors #SupersedeClause; both flags on one target refused. Transform .engine/tools/migrations/2026-09-09-supersede-scope.py: dry run {status_superseded 7, edges_whole 3, edges_clause 0} -> {0, 7, 7}, unnamed-line hash 4b800cde279bf98a EQUAL both sides, --apply 18 files, re-run 0 to change / 18 already in shape; status backfilled from each file's AcceptR event (6 accepted, d0038 proposed), 4 edges authored from the superseder named in the retired file's own trailing comment - nothing invented. Tests: keel-cli/tests/supersession_is_said_once.rs 3/3 on a fresh scaffold (queue/orient/governance from a constructed pair; check-engine refuses superseded by name; never-both refused, nothing written); mod.rs unit tests updated + standing_is_the_status_minus_the_edge. cargo clippy --release --all-targets clean; keel validate 708 clean; keel check-engine clean; keel guard ALL PASS (acceptance-binds-to-text 388 scanned, 0 violations with the five re-standinged Decisions skipped as retired). Docs: CLAUDE.md 1.4 + 4, sysmlv2-syntax-notes lifecycle, guards.md, usage.md, view/report skills, decision-authoring process actionText; sync-claude regenerated."; }
    // RAN: 2026-09-09 schema relationships.sysml + work.sysml (conformance_lane --construct ACCEPTED); Model::standing / supersede_targets rewired across view, critique, reports, staleness, deck, guards; --supersedes-clause write path; transform 2026-09-09-supersede-scope.py {7,3,0} -> {0,7,7} hash 4b800cde279bf98a EQUAL, 18 files, idempotent; tests supersession_is_said_once 3/3 + mod.rs; clippy clean; validate 708 clean; check-engine clean; guard ALL PASS; suite 625/0 (receipt ae8e4d788476)
    part supersessionSaidOnceImplementGateR1 : TestResult { :>> id = "dd4069fa-2456-435c-914a-661c5c2460ab"; :>> outcome = VerdictKind::pass; :>> judgedAgainst = "9369863"; :>> judgedAt = "2026-09-09"; :>> judgedBy = "claudeOpus5"; }
    verification supersessionSaidOnceReviewGate : Test { :>> id = "7d66df29-1f2b-448f-9981-89dc90eb3fba"; :>> title = "Sprint 622 review gate — three passes per D0172"; :>> createdAt = "2026-09-09"; :>> createdBy = "claudeOpus5"; :>> method = VerificationMethod::inspect; :>> procedureText = "Pass 1 (correctness): every reader that keyed on kind == supersede to mean retired now goes through one predicate (Model::standing / supersede_targets), so the seven clause reversals - d0149 -> d0129 never-rebase among them - no longer retire their targets; the governance card on this tree reads 389 accepted / 7 retired of 397 total, the same total as before with the 7 moved from a status value to an edge. Pass 2 (honesty): the transform fabricated nothing - each status value is the file's own last AcceptR event or proposed when none exists (d0038), and each authored edge quotes the trailing comment it was read from; the DoD text was corrected before its pass to name the gate that actually refuses (check-engine under .engine; validate covers .tracking only - the first draft said validate, which this tree would have passed with a superseded value still present). Pass 3 (controls): reintroduction of the member is refused by the parser's unknown-enum-member check on both gates that run at commit and in CI; the both-flags shape is refused at the write path; the fixture test constructs the issue396 pair instead of reading the tree, so it cannot pass vacuously when the tree is clean. Residual: D0070's consequences text still says status -> superseded for d0069 - historical text of an accepted Decision, left as written; D0398's consequences records the reversal."; }
    part supersessionSaidOnceReviewGateR1 : TestResult { :>> id = "01910403-5d01-47f3-98f0-cff94299ac42"; :>> outcome = VerdictKind::pass; :>> judgedAgainst = "9369863"; :>> judgedAt = "2026-09-09"; :>> judgedBy = "claudeOpus5"; }
    verification supersessionSaidOnceCloseOutGate : Test { :>> id = "d65550f7-c22b-455b-b887-712eae905c46"; :>> title = "Sprint 622 closeOut gate (autonomous, D0049)"; :>> createdAt = "2026-09-09"; :>> createdBy = "claudeOpus5"; :>> method = VerificationMethod::inspect; :>> procedureText = "Sprint 622 closes when dcSupersessionIsSaidOnceDoD carries a pass at the commit that carries the schema, the transform's applied output, the readers and the tests, and CI is green."; }
    part supersessionSaidOnceCloseOutGateR1 : TestResult { :>> id = "1c56ec68-0f90-44ae-bb5e-7270a01aa319"; :>> outcome = VerdictKind::pass; :>> judgedAgainst = "9369863"; :>> judgedAt = "2026-09-09"; :>> judgedBy = "claudeOpus5"; }
    verification supersessionSaidOnceRetroGate : Test { :>> id = "6e934673-d762-4b8b-9902-8ef1b41dd89b"; :>> title = "Sprint 622 retro gate (autonomous, D0049)"; :>> createdAt = "2026-09-09"; :>> createdBy = "claudeOpus5"; :>> method = VerificationMethod::analyze; :>> procedureText = "Retro held; avoidable-issue scan: one finding. keel validate reports the .tracking tree clean while .engine/decisions may hold a value the schema no longer has - the D0398 text and this sprint's first DoD draft both named validate as the refusing gate, and only running it against the migrated tree showed check-engine is the one that refuses under .engine. Tracked as issue419 (dcValidateNamesItsScope: validate says what tree it judged, or covers both). No new item beyond that: the migration ran once, reconciled, and the guard fallout was the predicted one (acceptance-binds-to-text on the five re-standinged Decisions), resolved at the root by skipping retired Decisions rather than re-binding five historical acceptances. Process improvement: a D0067 transform whose hash excludes lines by CONTENT CLASS on both sides reconciles on the first dry run; excluding by index on one side and by class on the other took a debug pass to see was the same set."; }
    part supersessionSaidOnceRetroGateR1 : TestResult { :>> id = "9857ddb4-ce5f-4488-bca1-ae08cd7638dc"; :>> outcome = VerdictKind::pass; :>> judgedAgainst = "9369863"; :>> judgedAt = "2026-09-09"; :>> judgedBy = "claudeOpus5"; }
}
