// ProjectDeliveryS687 — Sprint 687: Every adopted ProcessStep is classified by what MAKES it happen - HOOK (the harness fires it), GATE (passage is refused until it is done), MEMORY (an agent has to remember) - the three classes the human named in st111 ('Do they fire before the prompt? before work is done? after as a post-processing?') and us102 derived. D0434 gave a step its checkedBy and D0435 bound the ceremony steps to their gates; this sprint reads those bindings, the hook config and each step's own triggerCondition into one lens section, stepTrigger, and lists the MEMORY steps by process with the hook point that WOULD carry each, as a proposal. Delivers dcProcessStepsAreHookGateOrMemory. EXECUTE.. EXECUTE. 2 pts.
package ProjectDeliveryS687 {
    private import EngineElement::*;
    private import EngineWork::*;
    private import EngineVerification::*;
    private import EngineRelationships::*;

    #CharteredBy dependency from processStepsAreHookGateOrMemoryStory to d0434;

    part processStepsAreHookGateOrMemoryStory : Story {
        :>> id = "83e4babb-b055-4fc3-91a3-d26ea59f3214";
        :>> title = "Sprint 687: Every adopted ProcessStep is classified by what MAKES it happen - HOOK (the harness fires it), GATE (passage is refused until it is done), MEMORY (an agent has to remember) - the three classes the human named in st111 ('Do they fire before the prompt? before work is done? after as a post-processing?') and us102 derived. D0434 gave a step its checkedBy and D0435 bound the ceremony steps to their gates; this sprint reads those bindings, the hook config and each step's own triggerCondition into one lens section, stepTrigger, and lists the MEMORY steps by process with the hook point that WOULD carry each, as a proposal. Delivers dcProcessStepsAreHookGateOrMemory. EXECUTE. (2 pts)";
        :>> createdAt = "2026-09-13"; :>> createdBy = "claudeFable5"; :>> kind = WorkKind::code; :>> priority = WorkPriority::p0; :>> owner = "claudeFable5"; :>> estimatedPoints = 2;
    }

    action def DeliveryRunS687 {
        action storyProcessStepsAreHookGateOrMemory;
        verification storyProcessStepsAreHookGateOrMemoryDoD : Test { :>> id = "0ee5cc75-4c9c-4c7b-928f-2b12fe8b3aa6"; :>> method = VerificationMethod::test; :>> procedureText = "DELIVERED: keel show hardening gains stepTrigger (hardening.rs). Population is the units activation.toml names active (10 adopted, 23 not). Per step: GATE when checkedBy resolves - gate:<phase> refused by keel advance --to while red (D0435/D0436), a guard blocked by the Stop hook and the commit tier (D0130/D0177), a declared rule; HOOK when the step's triggerCondition names, verbatim, an event the config fires (.claude/settings.json hooks keys + .githooks files, read never assumed); MEMORY otherwise, with proposedHookPoint from the step's place in its first-then chain (no predecessor -> beforeWork, the refine gate; no successor -> afterWork, the retro gate / Stop; both -> beforeTurn, a UserPromptSubmit checklist line; no chain -> beforeTurn, the process declares no work-relative point). A step's process is the nearest preceding Process declaration - the schema ties them by no attribute, declaration order is the fact the files carry. READ BACK at this tree: 61 adopted steps = 6 gate + 0 hook + 55 memory, unresolved [] - every step in exactly one class with the fact that put it there; memoryByProcess lists 14 processes; memoryNote says why. No hook added; no file under .claude/ or .githooks/ changes. Two tests: a fixture (known-positive: a bound step is GATE, a step naming a configured event is HOOK, first/middle/last MEMORY points follow the chain; known-negative: a step naming an event the config does NOT fire is MEMORY) and this tree (partition, unresolved empty, six gate:<phase> rows, adopted <= all steps). Doc-sync: CLAUDE.md hardening line, guards.md step-check-resolves row."; }
        // RAN: RAN: ./target/release/keel-serve.exe show hardening . -> stepTrigger: adoptedUnits 10, notAdoptedUnits 23, steps 61 = gate 6 + hook 0 + memory 55, unresolved [], six gateSteps each naming checkedBy gate:<phase> and its process, 14 memoryByProcess groups each step with a proposedHookPoint, memoryNote non-empty; git status --short -> no path under .claude/ or .githooks/; cargo test --release --lib hardening::tests::step_trigger -> 2 passed
        part storyProcessStepsAreHookGateOrMemoryDoDR1 : TestResult { :>> id = "067a10ea-98f0-4444-8b8f-0682907dc853"; :>> outcome = VerdictKind::pass; :>> judgedAgainst = "51410ba"; :>> judgedAt = "2026-09-12"; :>> judgedBy = "claudeFable5"; }
    }

    verification processStepsAreHookGateOrMemoryRefineGate : Test { :>> id = "a93b9a7f-ee8d-4e52-9b0b-77dd8b519d71"; :>> title = "Sprint 687 refine gate (DoR)"; :>> createdAt = "2026-09-13"; :>> createdBy = "claudeFable5"; :>> method = VerificationMethod::inspect; :>> procedureText = "Chartered by D0434 (the checkedBy attribute is the binding this lens reads; the DoD names dcProcessStepsBindToChecks as its source). Two points: one lens section with three parsers (steps by declaration order, string fragments, first-then successions), two tests with the D0388 pair, a read-back, doc-sync, the ceremony. DoR: the DoD is on the backlog item (backlog.sysml, dcProcessStepsAreHookGateOrMemoryDoD, method inspect); derived from us102 by a #DerivedFrom edge; no blocker - D0434 and D0435 have landed and step_check_bindings/declared_check_names are the public helpers the lens reads. NOT A PROCESS CHANGE: the lens reads hooks, gates and steps; it adds no hook, no guard, no schema attribute and no workflow step - the DoD's last clause forbids exactly that, and the memory list is a proposal. NOT A FORK: the three classes are the human's words (st111/us102); the position-to-hook-point mapping is derived from the chain, not chosen among alternatives."; }
    // RAN: RAN: grep -n dcProcessStepsAreHookGateOrMemory .tracking/backlog.sysml -> DoD at :1072-1073, #DerivedFrom to us102 at :3075; charter d0434 landed (git log --oneline | grep 0434). NOT A PROCESS CHANGE / NOT A FORK stated in the story refine text
    part processStepsAreHookGateOrMemoryRefineGateR1 : TestResult { :>> id = "8aba2790-7947-4d68-a2f9-d43bee49eb3b"; :>> outcome = VerdictKind::proposed; :>> judgedAgainst = "51410ba"; :>> judgedAt = "2026-09-12"; :>> judgedBy = "claudeFable5"; }
    verification processStepsAreHookGateOrMemoryStandupGate : Test { :>> id = "db22d6e7-d016-45e5-a7dc-fa8d010547a3"; :>> title = "Sprint 687 standup gate"; :>> createdAt = "2026-09-13"; :>> createdBy = "claudeFable5"; :>> method = VerificationMethod::inspect; :>> procedureText = "Order: write the section against the fixture first (the D0388 pair chosen before the tree is read), then the this-tree test; clippy clean (five deny-level lints on the first pass: doc backticks, list continuation, a 118-line function split into gate_row / proposed_point / memory_note, if-let-else to map_or_else); rebuild, copy to keel-serve.exe, read stepTrigger back; doc-sync CLAUDE.md and guards.md in the same commit; record the sprint, the six gates and the DoD result (inspect -> proposed); gate validate, check-engine, guard --no-receipt, sync-claude --check; commit detached and read git status -sb and the CI conclusion."; }
    // RAN: RAN: cargo clippy --release --lib -> Finished, zero warnings; the five deny-level lints of the first pass (hardening.rs:393/396/401/402/435) fixed at the root
    part processStepsAreHookGateOrMemoryStandupGateR1 : TestResult { :>> id = "0a382bc1-81ef-4917-ba43-1bf914f473d6"; :>> outcome = VerdictKind::proposed; :>> judgedAgainst = "51410ba"; :>> judgedAt = "2026-09-12"; :>> judgedBy = "claudeFable5"; }
    verification processStepsAreHookGateOrMemoryImplementGate : Test { :>> id = "aaf68df3-73ba-4e41-b816-b3db152e4b61"; :>> title = "Sprint 687 implement gate"; :>> createdAt = "2026-09-13"; :>> createdBy = "claudeFable5"; :>> method = VerificationMethod::test; :>> procedureText = "hardening.rs: configured_hook_events (settings.json hooks keys + .githooks files), step_trigger (registered as stepTrigger after stepEnforcement), gate_row, proposed_point, memory_note, StepDecl, process_steps, string_fragments, successions; two tests. First read-back showed process = '-' on every row: the fixture nested its steps inside the Process block and the tree does not - agile-workflow.sysml:42 declares refinement and :50-90 its steps as SIBLINGS, and process.sysml:25-35 gives ProcessStep no attribute naming its process. Corrected to the fact the files carry: the nearest preceding Process declaration, nested or sibling. Second read-back: 61 steps, gate 6 (refinement/refineLink, standup/standupGate, implementation/implDo, implReview, implClose, retrospective/retroIdentify), hook 0, memory 55 (90%), unresolved [], 14 memoryByProcess groups across the 10 adopted units, configuredEvents = ConfigChange, PostToolUse, PreToolUse, Stop, SubagentStop, UserPromptSubmit, post-commit, pre-commit, pre-merge-commit, pre-push. HOOK is 0 because no adopted step's triggerCondition names a configured event verbatim - the lens's note states the criterion, and that is the finding us102 asked for: the process text does not speak the harness's vocabulary, so nothing carries a step but memory and six gates."; }
    // RAN: RAN: cargo test --release --lib hardening::tests::step_trigger -> 2 passed 0 failed; cargo build --release -> Finished; cp keel.exe keel-serve.exe; ./target/release/keel-serve.exe show hardening . -> stepTrigger adoptedUnits 10, steps 61, gate 6, hook 0, memory 55, memoryPct 90, unresolved []
    part processStepsAreHookGateOrMemoryImplementGateR1 : TestResult { :>> id = "cff69428-9ae1-4a8f-a160-faeb655b6e3c"; :>> outcome = VerdictKind::pass; :>> judgedAgainst = "51410ba"; :>> judgedAt = "2026-09-12"; :>> judgedBy = "claudeFable5"; }
    verification processStepsAreHookGateOrMemoryReviewGate : Test { :>> id = "8d64ee90-7c52-47c7-a81e-5aa8bb3f9971"; :>> title = "Sprint 687 review gate — three passes per D0172"; :>> createdAt = "2026-09-13"; :>> createdBy = "claudeFable5"; :>> method = VerificationMethod::inspect; :>> procedureText = "Three passes (D0172). Correctness: the classification is a partition by construction (each step takes the first matching branch and continues) and both tests assert hook + gate + memory == steps; the six GATE rows are the six D0435 bindings and no other adopted step carries checkedBy, read back not assumed; the process column was wrong on the first pass and the fix names the fact it reads (declaration order) in the function's doc. Honesty: HOOK = 0 is reported with the criterion, not softened; MEMORY = 90% is an indicator and the doc says why it is never a gate (gating it would make the cheapest fix a triggerCondition that names an event); the memory list's hook points are labelled PROPOSALS; the DoD result lands proposed because its method is inspect (D0312 B). Scope: no hook, guard, schema or process file touched; the two doc lines name the section and its source."; }
    // RAN: RAN: python read of stepTrigger.gateSteps -> six rows refinement/refineLink standup/standupGate implementation/implDo implReview implClose retrospective/retroIdentify each with checkedBy gate:<phase>; memoryByProcess 14 groups each step with proposedHookPoint; first-pass process column read - on every row, corrected to nearest preceding Process declaration (agile-workflow.sysml:42 vs :50)
    part processStepsAreHookGateOrMemoryReviewGateR1 : TestResult { :>> id = "d433ed3c-bcc4-48f2-9b1b-c905ef8337c3"; :>> outcome = VerdictKind::proposed; :>> judgedAgainst = "51410ba"; :>> judgedAt = "2026-09-12"; :>> judgedBy = "claudeFable5"; }
    verification processStepsAreHookGateOrMemoryCloseOutGate : Test { :>> id = "4fecfd11-9b3d-4426-9a89-c3d8da1f2b60"; :>> title = "Sprint 687 closeOut gate (autonomous, D0049)"; :>> createdAt = "2026-09-13"; :>> createdBy = "claudeFable5"; :>> method = VerificationMethod::inspect; :>> procedureText = "Closes on cargo clippy --release --lib clean, the two step_trigger tests passing, gate validate, gate check-engine, gate guard --no-receipt and sync-claude --check over the tree holding hardening.rs, CLAUDE.md, guards.md, this sprint and the DoD result; on keel show hardening reading stepTrigger with 61 = 6 + 0 + 55 and unresolved []; on git status showing no change under .claude/ or .githooks/."; }
    // RAN: RAN: keel gate validate . ; keel gate check-engine . ; keel gate guard --no-receipt . ; keel sync-claude --check . -> recorded from their exit codes in this commit; git status --short shows no change under .claude/ or .githooks/
    part processStepsAreHookGateOrMemoryCloseOutGateR1 : TestResult { :>> id = "1f1633e6-6d4b-4525-91a0-c5caaa8830f4"; :>> outcome = VerdictKind::proposed; :>> judgedAgainst = "51410ba"; :>> judgedAt = "2026-09-12"; :>> judgedBy = "claudeFable5"; }
    verification processStepsAreHookGateOrMemoryRetroGate : Test { :>> id = "b581a4ba-5692-4090-b0ac-2712707b01b1"; :>> title = "Sprint 687 retro gate (autonomous, D0049)"; :>> createdAt = "2026-09-13"; :>> createdBy = "claudeFable5"; :>> method = VerificationMethod::analyze; :>> procedureText = "AVOIDABLE-ISSUE SCAN, no new item (D0131): the one finding is root-fixed in this commit and its regression check is dcProcessStepsAreHookGateOrMemory's this-tree test; the second is already tracked by us102 as the question this lens answers. ROOT-FIXED: the fixture was written with steps NESTED in the Process block and passed while the tree's sibling layout read '-' for every process - a D0388 pair chosen before the tree is read does not check that the fixture's SHAPE is the tree's shape; the this-tree test now covers the shape (six gate rows name their process) so a regression is caught, and no second occurrence is known. CARRIED, not new: the 55 MEMORY steps with their proposed hook points are the computed answer to us102's question, and what to DO about them is the human's - a hook that carries a step is a process change (D0337), which is why the lens proposes and adds none; the proposal sits in the lens, not in this prose. STATED: HOOK = 0 on this tree means no adopted process text names a harness event; whether process text should is a direction Decision, not a retro finding."; }
    // RAN: RAN: retro text names one root-fixed finding (fixture shape vs tree shape, covered by the this-tree test) and one carried (55 MEMORY proposals are the lens's computed answer; acting on them is a D0337 process change for the human) - no new Issue, reason given (D0131)
    part processStepsAreHookGateOrMemoryRetroGateR1 : TestResult { :>> id = "5dec3f89-9809-46b7-b6ea-5b7d7989cd48"; :>> outcome = VerdictKind::proposed; :>> judgedAgainst = "51410ba"; :>> judgedAt = "2026-09-12"; :>> judgedBy = "claudeFable5"; }
}
