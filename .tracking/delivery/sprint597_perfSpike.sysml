// ProjectDeliveryS597 — Sprint 597: Research spike: measure where keel's computed state spends its time before proposing how to spend less of it. EXECUTE. 2 pts.
package ProjectDeliveryS597 {
    private import EngineElement::*;
    private import EngineWork::*;
    private import EngineVerification::*;
    private import EngineRelationships::*;

    #CharteredBy dependency from perfSpikeStory to d0367;

    part perfSpikeStory : Story {
        :>> id = "bf1d347e-786b-452b-a015-206690f80a5d";
        :>> title = "Sprint 597: Research spike: measure where keel's computed state spends its time before proposing how to spend less of it (2 pts)";
        :>> createdAt = "2026-09-07"; :>> createdBy = "claudeOpus5"; :>> kind = WorkKind::research; :>> priority = WorkPriority::p1; :>> owner = "claudeOpus5"; :>> estimatedPoints = 2;
    }

    action def DeliveryRunS597 {
        action storyPerfSpike;
        verification storyPerfSpikeDoD : Test { :>> id = "9ede58d0-77b2-4c22-a85d-5807528e62e0"; :>> method = VerificationMethod::test; :>> procedureText = "DELIVERED: a measured attribution of `keel guard` (25.5 s) and `keel orient` (5.1 s) to their parts, in-process, on this host - per guard, per orient step, per Model clone, with git spawns counted and their untimed state found (issue410) - against a 275 ms whole-corpus parse; D0367 recording four repetitions to remove in rank with the number that ranks each, two conditional items, three approaches declined with numbers (database or index, faster parser, incremental framework) and one left to the human (a Defender exclusion or Dev Drive, the largest lever on this host and not keel's to pull); issue409 as the tracked defect; six backlog items with DoDs that name their verification; the knowledge record .tracking/knowledge/perf-spike-2026-09-07.sysml; and docs/reviews/perf-spike-2026-09-07.md with the tables and the three reverted measurement patches beside it. VERIFIED by the numbers being read from KEEL_PERF lines and a shell timer, never estimated, and by the source being reverted before commit: git status shows no change under keel-cli/src."; }
        // RAN: KEEL_PERF=2 with a shell timer: validate 0.46 s, gate --fast 0.86 s, orient 5.1 s (git x23), guard 25.5 s (git x56, parse 273 ms, Model::build x41 40 cached); per-guard and per-step phases from the three reverted patches in docs/reviews/perf-spike-2026-09-07/; git status clean under keel-cli/src; D0367 recorded and auto-accepted; issue409/410 recorded with resolver; six items added and the four resolvers at the head with priority-inversion 0 warnings
        part storyPerfSpikeDoDR1 : TestResult { :>> id = "bf2b0180-c425-4fa9-bd1c-22f155bea06b"; :>> outcome = VerdictKind::pass; :>> judgedAgainst = "59c43368d735a299c1a2556d72390ec9a07c496f"; :>> judgedAt = "2026-09-07"; :>> judgedBy = "claudeOpus5"; }
    }

    verification perfSpikeRefineGate : Test { :>> id = "cc04d8db-4e2f-41b8-b2b7-6ff4335c45f7"; :>> title = "Sprint 597 refine gate (DoR)"; :>> createdAt = "2026-09-07"; :>> createdBy = "claudeOpus5"; :>> method = VerificationMethod::inspect; :>> procedureText = "READY: a spike, 2 pts - the human asked for research, not a build, and named the candidate mechanisms; the spike's job was to measure before answering them. The one thing decided at refine: measure IN-PROCESS with phase wrappers rather than by timing `keel guard <name>` one at a time, because a standalone run carries ~180 ms of process start that would have inflated every small guard by 60 percent."; }
    // RAN: KEEL_PERF=2 with a shell timer: validate 0.46 s, gate --fast 0.86 s, orient 5.1 s (git x23), guard 25.5 s (git x56, parse 273 ms, Model::build x41 40 cached); per-guard and per-step phases from the three reverted patches in docs/reviews/perf-spike-2026-09-07/; git status clean under keel-cli/src; D0367 recorded and auto-accepted; issue409/410 recorded with resolver; six items added and the four resolvers at the head with priority-inversion 0 warnings
    part perfSpikeRefineGateR1 : TestResult { :>> id = "40d8246e-fb30-4da7-8ddf-ef4fd5468fbe"; :>> outcome = VerdictKind::pass; :>> judgedAgainst = "59c43368d735a299c1a2556d72390ec9a07c496f"; :>> judgedAt = "2026-09-07"; :>> judgedBy = "claudeOpus5"; }
    verification perfSpikeStandupGate : Test { :>> id = "cddaec2e-c1a1-4751-bf83-3852a842392a"; :>> title = "Sprint 597 standup gate"; :>> createdAt = "2026-09-07"; :>> createdBy = "claudeOpus5"; :>> method = VerificationMethod::inspect; :>> procedureText = "ONE CHOICE: instrument by patch and revert, rather than land the instrumentation first. Landing it touches guards.rs, which is under the keystone lock and would have needed a Decision before the first number existed; the patches are kept beside the review so the numbers can be re-derived, and dcGuardsRunInParallelAndTimed makes the instrumentation permanent under its own Decision."; }
    // RAN: KEEL_PERF=2 with a shell timer: validate 0.46 s, gate --fast 0.86 s, orient 5.1 s (git x23), guard 25.5 s (git x56, parse 273 ms, Model::build x41 40 cached); per-guard and per-step phases from the three reverted patches in docs/reviews/perf-spike-2026-09-07/; git status clean under keel-cli/src; D0367 recorded and auto-accepted; issue409/410 recorded with resolver; six items added and the four resolvers at the head with priority-inversion 0 warnings
    part perfSpikeStandupGateR1 : TestResult { :>> id = "d861d677-a3d2-4445-bfcc-b46bfd38a0fb"; :>> outcome = VerdictKind::pass; :>> judgedAgainst = "59c43368d735a299c1a2556d72390ec9a07c496f"; :>> judgedAt = "2026-09-07"; :>> judgedBy = "claudeOpus5"; }
    verification perfSpikeImplementGate : Test { :>> id = "36806ef3-7330-4d99-a135-30e604fa4fc4"; :>> title = "Sprint 597 implement gate"; :>> createdAt = "2026-09-07"; :>> createdBy = "claudeOpus5"; :>> method = VerificationMethod::test; :>> procedureText = "RAN: KEEL_PERF=2 keel validate / check-engine / gate --fast / orient / whats-next / guard with a shell timer; cargo build --release three times with one measurement patch each (run_all, orient::compute, cached_model), each script refusing when its anchor is not found exactly once; a Python cold/warm read of the corpus to separate Defender from keel; `time git rev-parse HEAD` five times for the spawn cost. One anomaly - parse 18306 ms in a single run - did not reproduce on four reruns and is recorded as an attribution, not a finding. All three patches reverted with git checkout; the release binary on disk is the last instrumented build and is inert without KEEL_PERF."; }
    // RAN: KEEL_PERF=2 with a shell timer: validate 0.46 s, gate --fast 0.86 s, orient 5.1 s (git x23), guard 25.5 s (git x56, parse 273 ms, Model::build x41 40 cached); per-guard and per-step phases from the three reverted patches in docs/reviews/perf-spike-2026-09-07/; git status clean under keel-cli/src; D0367 recorded and auto-accepted; issue409/410 recorded with resolver; six items added and the four resolvers at the head with priority-inversion 0 warnings
    part perfSpikeImplementGateR1 : TestResult { :>> id = "f9fd4b28-5fa1-45bd-85eb-193759efde12"; :>> outcome = VerdictKind::pass; :>> judgedAgainst = "59c43368d735a299c1a2556d72390ec9a07c496f"; :>> judgedAt = "2026-09-07"; :>> judgedBy = "claudeOpus5"; }
    verification perfSpikeReviewGate : Test { :>> id = "d2a38e5d-815e-49ca-9a8f-2507c3f723a6"; :>> title = "Sprint 597 review gate — three passes per D0172"; :>> createdAt = "2026-09-07"; :>> createdBy = "claudeOpus5"; :>> method = VerificationMethod::inspect; :>> procedureText = "THREE QUESTIONS (D0172). (1) Did the spike answer the mechanisms the human named, or replace them? Each is answered with the measurement that bears on it: the file-index hash already exists (fingerprint::of) and keys the model cache; a database scans the same predicates and is a second truth; the intermediate layer is the daemon and is deferred behind rank 4's number. (2) Is the ranking defensible from the numbers alone? Rank 1 removes the largest term with one function; rank 2 removes what bounds rank 1; rank 3 removes the reopen that rank 1 hides; rank 4 removes the run from the common case and is last because its key must be argued. (3) What does the review NOT claim? That the numbers transfer to another host, or that any of the four is built."; }
    // RAN: KEEL_PERF=2 with a shell timer: validate 0.46 s, gate --fast 0.86 s, orient 5.1 s (git x23), guard 25.5 s (git x56, parse 273 ms, Model::build x41 40 cached); per-guard and per-step phases from the three reverted patches in docs/reviews/perf-spike-2026-09-07/; git status clean under keel-cli/src; D0367 recorded and auto-accepted; issue409/410 recorded with resolver; six items added and the four resolvers at the head with priority-inversion 0 warnings
    part perfSpikeReviewGateR1 : TestResult { :>> id = "d04c3781-d0bb-4396-9d0b-8ffe11bccd48"; :>> outcome = VerdictKind::pass; :>> judgedAgainst = "59c43368d735a299c1a2556d72390ec9a07c496f"; :>> judgedAt = "2026-09-07"; :>> judgedBy = "claudeOpus5"; }
    verification perfSpikeCloseOutGate : Test { :>> id = "fc3c07b7-d45b-4420-8a5d-91cf0467f1bf"; :>> title = "Sprint 597 closeOut gate (autonomous, D0049)"; :>> createdAt = "2026-09-07"; :>> createdBy = "claudeOpus5"; :>> method = VerificationMethod::inspect; :>> procedureText = "CLOSED. The spike's output is the four ranked items at the head of the ready list and D0367; nothing under keel-cli/src changed. The next sprint takes rank 1."; }
    // RAN: KEEL_PERF=2 with a shell timer: validate 0.46 s, gate --fast 0.86 s, orient 5.1 s (git x23), guard 25.5 s (git x56, parse 273 ms, Model::build x41 40 cached); per-guard and per-step phases from the three reverted patches in docs/reviews/perf-spike-2026-09-07/; git status clean under keel-cli/src; D0367 recorded and auto-accepted; issue409/410 recorded with resolver; six items added and the four resolvers at the head with priority-inversion 0 warnings
    part perfSpikeCloseOutGateR1 : TestResult { :>> id = "77bf8c16-edf3-4618-a89c-88fc6c4adf6a"; :>> outcome = VerdictKind::pass; :>> judgedAgainst = "59c43368d735a299c1a2556d72390ec9a07c496f"; :>> judgedAt = "2026-09-07"; :>> judgedBy = "claudeOpus5"; }
    verification perfSpikeRetroGate : Test { :>> id = "fb281edb-353c-4ddb-bc29-e8e57174947c"; :>> title = "Sprint 597 retro gate (autonomous, D0049)"; :>> createdAt = "2026-09-07"; :>> createdBy = "claudeOpus5"; :>> method = VerificationMethod::analyze; :>> procedureText = "AVOIDABLE-ISSUE SCAN HELD. One finding, already tracked: the perf line reported `git x56 in 100ms` for 4.4 s of spawns, and a reader trusting the line concludes git is free - issue410, resolved by rank 1. One finding new and NOT tracked as work: the pre-bash hook refused a heredoc twice this session for a backslash in Python source, exactly as D0309 says it should; the Write tool path cost nothing. No new item."; }
    // RAN: KEEL_PERF=2 with a shell timer: validate 0.46 s, gate --fast 0.86 s, orient 5.1 s (git x23), guard 25.5 s (git x56, parse 273 ms, Model::build x41 40 cached); per-guard and per-step phases from the three reverted patches in docs/reviews/perf-spike-2026-09-07/; git status clean under keel-cli/src; D0367 recorded and auto-accepted; issue409/410 recorded with resolver; six items added and the four resolvers at the head with priority-inversion 0 warnings
    part perfSpikeRetroGateR1 : TestResult { :>> id = "678a0f08-4469-4bb0-b50b-641e4b44722a"; :>> outcome = VerdictKind::pass; :>> judgedAgainst = "59c43368d735a299c1a2556d72390ec9a07c496f"; :>> judgedAt = "2026-09-07"; :>> judgedBy = "claudeOpus5"; }
}
