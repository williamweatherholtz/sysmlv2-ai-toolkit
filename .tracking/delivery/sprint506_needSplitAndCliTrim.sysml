// ProjectDeliveryS506 — Sprint 506: the autonomy Need splits, and 55 citations leave the help text. EXECUTE. 3 pts.
package ProjectDeliveryS506 {
    private import EngineElement::*;
    private import EngineWork::*;
    private import EngineVerification::*;
    private import EngineRelationships::*;

    #CharteredBy dependency from needSplitAndCliTrimStory to d0270;

    part needSplitAndCliTrimStory : Story {
        :>> id = "730d15f1-c858-4dd8-8acc-70163ce18db8";
        :>> title = "Sprint 506: a reversal honoured, help text trimmed, and the fourth backtick occurrence closed (3 pts)";
        :>> createdAt = "2026-09-01"; :>> createdBy = "claudeOpus5"; :>> kind = WorkKind::code; :>> priority = WorkPriority::p0; :>> owner = "claudeOpus5"; :>> estimatedPoints = 3;
    }

    action def DeliveryRunS506 {
        action storyNeedSplitAndCliTrim;
        verification storyNeedSplitAndCliTrimDoD : Test { :>> id = "c0e51725-8635-4f03-a709-147005c7c842"; :>> method = VerificationMethod::test; :>> procedureText = "THE REVERSAL (st063): the human picked SPLIT on the same fork where they had picked ONE the day before. Both answers were given with the statement quoted, so it is a change of mind, not a misread - and the trigger is the flip condition I wrote into the fork myself. DONE: nAutonomyBoundedByProof is SUPERSEDED (not deleted - the earlier acceptance records what they attested and stays visible, D0108) by nUntrustedInputPlans and nUnverifiableChangeReverts, divided along the seam the fork named: WHO is asking versus WHETHER THE OUTCOME CAN BE UNDONE. Three SystemRequirements re-pointed to the reversibility half; a new srUntrustedInputRoutesToADecision authored for the trust half, which the split had left with a mechanism in code and no contract citing it. THE CLI (st063 note): 55 help rows carried decision-id parentheticals - provenance for a maintainer, not what a user needs to run a command - all stripped, citations retained in the source doc comments. The structural half is MEASURED and NOT started, because it is breaking. FOURTH BACKTICK OCCURRENCE closed: add-task gains --dod-from FILE. VERIFY: workspace suite 0 failed; clippy clean; keel guard 0 violations; help carries 0 citations, down from 55.: DELIVERED BACKLOG ITEMS: <items>. <what done means, verified how>."; }
        // RAN: / RAN: help citations 55 -> 0 (counted both ways); workspace suite 0 failed; clippy clean; guard 0 violations; the Need split validates with the old acceptance superseded and both halves contracted
        part storyNeedSplitAndCliTrimDoDR1 : TestResult { :>> id = "50f66abb-372f-4673-b85a-ef703fc470d5"; :>> outcome = VerdictKind::pass; :>> judgedAgainst = "5453550"; :>> judgedAt = "2026-09-01"; :>> judgedBy = "claudeOpus5"; }
    }

    verification needSplitAndCliTrimRefineGate : Test { :>> id = "71a7ddab-f3ee-45f5-808e-b5f3eb58f878"; :>> title = "Sprint 506 refine gate (DoR)"; :>> createdAt = "2026-09-01"; :>> createdBy = "claudeOpus5"; :>> method = VerificationMethod::inspect; :>> procedureText = "READY: the reversal is an adjudication with the item in front of them, and the CLI note is measurable before it is actionable - the counting came first (111 dispatch arms, ~30 lenses, 16 viewpoint/command name collisions, 118 skill references) so that the proposal has numbers rather than an impression."; }
    verification needSplitAndCliTrimStandupGate : Test { :>> id = "f9ecd169-0b1e-4b8a-9a6b-a8bb03133519"; :>> title = "Sprint 506 standup gate"; :>> createdAt = "2026-09-01"; :>> createdBy = "claudeOpus5"; :>> method = VerificationMethod::inspect; :>> procedureText = "One thing deliberately NOT done. The human said 'tighten it up', which reads as an instruction to act, and I did the half that breaks nothing (descriptions) while stopping at the half that does. Collapsing ~30 verbs is a breaking change to a surface 118 call sites invoke BY NAME, and guard 39 fails a process naming a tool it did not receive - so acting on initiative would have traded their cruft complaint for a broken skill set. The consolidation is authored as a blocked task carrying the measurements."; }
    verification needSplitAndCliTrimImplementGate : Test { :>> id = "1a73c681-0a72-4006-9aa4-7b5233613e83"; :>> title = "Sprint 506 implement gate"; :>> createdAt = "2026-09-01"; :>> createdBy = "claudeOpus5"; :>> method = VerificationMethod::test; :>> procedureText = "RAN: keel --help -> 0 decision-id citations, down from 55 (counted before and after). cargo test --workspace --release -> 0 failed. cargo clippy -D warnings -> clean. keel guard -> 0 violations. keel gate --fast -> clean at 575 files. MEASUREMENTS BEHIND THE CLI FINDING, each read rather than estimated: 111 dispatch arms counted from the match table; ~30 read-only lenses; 16 of 32 declared viewpoints share a name with a top-level command; `keel view orphans` FAILS while `keel orphans` works, which is how the two mechanisms were shown to be half-connected rather than redundant; 118 references to lens commands in .engine skills and processes. THE FIRST REGEX PASS ONLY CLEANED 26 OF 55 ROWS - the misses had a different indentation shape - and the count read back after the change is what caught it."; }
    verification needSplitAndCliTrimReviewGate : Test { :>> id = "da1ec300-8fe1-41d6-8dc6-2b7c122c2af7"; :>> title = "Sprint 506 review gate — three passes per D0172"; :>> createdAt = "2026-09-01"; :>> createdBy = "claudeOpus5"; :>> method = VerificationMethod::inspect; :>> procedureText = "THREE PASSES. (1) IS THE REVERSAL HANDLED HONESTLY: the earlier acceptance is superseded and still readable, and the new acceptance's procedureText states that BOTH selections were made on the same fork with the statement quoted - so a later reader can see a change of mind rather than an inconsistency to reconcile. (2) DID THE SPLIT ORPHAN ANYTHING: yes, and it was caught - the trust half had guard 56 enforcing it and no requirement citing it, which is how a Need looks covered while nothing contracts for it. srUntrustedInputRoutesToADecision closes that, and its threshold restates the guard's own allow-case so the two cannot drift. (3) IS THE DESCRIPTION TRIM A LOSS: the citations moved nowhere - they were already in the source doc comments, which is where a maintainer looks; the help line is for someone about to type the command."; }
    verification needSplitAndCliTrimCloseOutGate : Test { :>> id = "0c732751-c622-4a28-8c03-5c8febc610db"; :>> title = "Sprint 506 closeOut gate (autonomous, D0049)"; :>> createdAt = "2026-09-01"; :>> createdBy = "claudeOpus5"; :>> method = VerificationMethod::inspect; :>> procedureText = "CLOSED. Two Needs replace one, both accepted. Help text carries no citations. issue321 (the CLI surface) and issue322 (the fourth backtick occurrence) are recorded with their measurements; the consolidation waits on the human because it breaks 118 call sites."; }
    verification needSplitAndCliTrimRetroGate : Test { :>> id = "98b52a23-8823-4fb8-8bcb-ac816316e124"; :>> title = "Sprint 506 retro gate (autonomous, D0049)"; :>> createdAt = "2026-09-01"; :>> createdBy = "claudeOpus5"; :>> method = VerificationMethod::analyze; :>> procedureText = "FINDING, and it is the sharpest one this session: the backtick trap fired a FOURTH time, and not through carelessness. After the third occurrence I wrote the rule into CLAUDE.md, into the skill, and into a Decision - all three said never pass prose as a double-quoted argument. Then I reached for `add-task --dod`, which HAD NO FILE-TAKING FLAG, so obeying the rule was impossible on that path. A rule that cannot be followed somewhere is not a control there; it is a suggestion with good documentation. The fix that would have prevented this was not a better instruction but applying the FIRST fix per-class rather than per-command. Recorded in issue322, including the residual: nothing checks that a write path taking prose offers a file alternative, so a fifth path added tomorrow reopens it."; }
}
