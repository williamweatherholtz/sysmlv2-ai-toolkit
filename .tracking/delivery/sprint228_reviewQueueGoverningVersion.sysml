// ProjectDeliveryS228 — Sprint 228: reviewQueueGoverningVersion — resolve issue068. The review queue
// (D0121) surfaced HISTORICAL ceremony confirmation gates as CURRENT human obligations, ignoring the
// engine's governing-version discipline. Fix per D0123 (accepted): declare `retro` as a Delivery phase
// so the model-driven ceremony filter drops retro gates from actionable (creation-time method
// UNCHANGED); + linkify the review queue (references clickable). EXECUTE. 2 pts.
package ProjectDeliveryS228 {
    private import EngineElement::*;
    private import EngineWork::*;
    private import EngineVerification::*;
    private import EngineRelationships::*;

    #CharteredBy dependency from reviewQueueGovStory to d0123;

    part reviewQueueGovStory : Story {
        :>> id = "63940516-2c7d-4e8f-c228-51627384c001";
        :>> title = "Sprint 228: reviewQueueGoverningVersion (2 pts) - resolve issue068 (obligation-view honors governing-version) + linkify the review queue";
        :>> createdAt = "2026-07-15"; :>> createdBy = "wweatherholtz"; :>> kind = WorkKind::code; :>> priority = WorkPriority::p1; :>> owner = "claudeOpus"; :>> estimatedPoints = 2;
    }

    action def DeliveryRunS228 {
        action storyReviewQueueGov;
        verification storyReviewQueueGovDoD : Test { :>> id = "63940516-2c7d-4e8f-c228-51627384c002"; :>> method = VerificationMethod::demo; :>> procedureText = "Resolves issue068 per D0123 (accepted). (1) GOVERNING-VERSION / no grandfathering: declared `retro` as a phase in the Delivery workflow action def (.engine/workflows/delivery.sysml) so the existing model-driven ceremony filter (view::is_ceremony_gate, phases from declared_workflow_phases) recognizes retro gates and drops them from the review queue's ACTIONABLE set — WITHOUT rewriting the 3 legacy pre-D0049 rustS5/6/7 RetroGate (their creation-time method=confirmation stands; the earlier wrong reclassification was reverted). Historical items stay governed by their charter-time process (govern.rs governing-version); the fix is in the VIEW, not the data. (2) LINKIFY (human ask, easy context): view::review_queue_json now emits a `references` array per item (typed-edge neighbours, both directions); the Review console tab renders them as clickable item links that open the detail popup. Added a #DependsOn edge keelViewerNeedsAccept5 -> nViewerEncodingViewpoints so the N-18 acceptance gate one-clicks to the Need it gates. VERIFY (demo, live serve): actionable queue dropped 8->2 (the 3 retro gates gone; D0123 + N-18 gate remain); references render + resolve (d0123 -> d0049/d0121; keelViewerNeedsAccept5 -> nViewerEncodingViewpoints); legacy gate method unchanged. clippy -D warnings clean; keel validate + guard (ALL PASS) + check-engine green."; }
        part storyReviewQueueGovDoDR1 : TestResult { :>> id = "63940516-2c7d-4e8f-c228-51627384c003"; :>> outcome = VerdictKind::pass; :>> judgedAgainst = "3d36c57"; :>> judgedAt = "2026-07-15"; :>> judgedBy = "claudeOpus"; }
    }

    verification rqgRefineGate : Test { :>> id = "63940516-2c7d-4e8f-c228-51627384c004"; :>> title = "Sprint 228 refine gate (DoR)"; :>> createdAt = "2026-07-15"; :>> createdBy = "claudeOpus"; :>> method = VerificationMethod::inspect; :>> procedureText = "DoR: issue068 (review queue ignored governing-version) + the human's linkify ask. D0123 accepted governs the fix. Scope: declare retro (ceremony filter) + references in the queue view + tab. #CharteredBy d0123. DoR met."; }
    part rqgRefineGateR1 : TestResult { :>> id = "63940516-2c7d-4e8f-c228-51627384c005"; :>> outcome = VerdictKind::pass; :>> judgedAgainst = "3d36c57"; :>> judgedAt = "2026-07-15"; :>> judgedBy = "claudeOpus"; }
    verification rqgStandupGate : Test { :>> id = "63940516-2c7d-4e8f-c228-51627384c006"; :>> title = "Sprint 228 standup gate"; :>> createdAt = "2026-07-15"; :>> createdBy = "claudeOpus"; :>> method = VerificationMethod::inspect; :>> procedureText = "Approach: fix the VIEW (declare retro so ceremony filter catches retro gates), not the data (no reclassification); add references (edge neighbours) to review_queue_json + render clickable in the Review tab; add the N-18 gate->Need edge. No blockers."; }
    part rqgStandupGateR1 : TestResult { :>> id = "63940516-2c7d-4e8f-c228-51627384c007"; :>> outcome = VerdictKind::pass; :>> judgedAgainst = "3d36c57"; :>> judgedAt = "2026-07-15"; :>> judgedBy = "claudeOpus"; }
    verification rqgImplementGate : Test { :>> id = "63940516-2c7d-4e8f-c228-51627384c008"; :>> title = "Sprint 228 implement gate"; :>> createdAt = "2026-07-15"; :>> createdBy = "claudeOpus"; :>> method = VerificationMethod::demo; :>> procedureText = "retro declared; review_queue_json references + Review-tab rendering + N-18 edge implemented. Live-verified: actionable 8->2, retro gates dropped, references resolve. clippy/validate/guard/check-engine green."; }
    part rqgImplementGateR1 : TestResult { :>> id = "63940516-2c7d-4e8f-c228-51627384c009"; :>> outcome = VerdictKind::pass; :>> judgedAgainst = "3d36c57"; :>> judgedAt = "2026-07-15"; :>> judgedBy = "claudeOpus"; }
    verification rqgReviewGate : Test { :>> id = "63940516-2c7d-4e8f-c228-51627384c00a"; :>> title = "Sprint 228 review gate"; :>> createdAt = "2026-07-15"; :>> createdBy = "claudeOpus"; :>> method = VerificationMethod::inspect; :>> procedureText = "Reviewed. The fix is in the right layer (the view honors governing-version; history preserved) — the human's principle that items are governed by their creation-time process is respected, and the miss (new view built without the governing-version discipline) is captured as issue068 + the D0123 design rule. Linkify delivers the requested easy-context (click a reference -> popup). No retroactive migration, no retroactive guard. Clean."; }
    part rqgReviewGateR1 : TestResult { :>> id = "63940516-2c7d-4e8f-c228-51627384c00b"; :>> outcome = VerdictKind::pass; :>> judgedAgainst = "3d36c57"; :>> judgedAt = "2026-07-15"; :>> judgedBy = "claudeOpus"; }
    verification rqgCloseOutGate : Test { :>> id = "63940516-2c7d-4e8f-c228-51627384c00c"; :>> title = "Sprint 228 closeOut gate (autonomous, D0049)"; :>> createdAt = "2026-07-15"; :>> createdBy = "claudeOpus"; :>> method = VerificationMethod::inspect; :>> procedureText = "Autonomous closeOut (D0049): DoD pass; issue068 resolved (resolver reviewQueueGoverningVersion done); review queue honors governing-version + is linkified. Self-evidencing. NEXT: on N-18 disposition, build the encoding-viewpoints feature (D0120) or continue the viewer bricks."; }
    part rqgCloseOutGateR1 : TestResult { :>> id = "63940516-2c7d-4e8f-c228-51627384c00d"; :>> outcome = VerdictKind::pass; :>> judgedAgainst = "3d36c57"; :>> judgedAt = "2026-07-15"; :>> judgedBy = "claudeOpus"; }
    verification rqgRetroGate : Test { :>> id = "63940516-2c7d-4e8f-c228-51627384c00e"; :>> title = "Sprint 228 retro gate (autonomous, D0049)"; :>> createdAt = "2026-07-15"; :>> createdBy = "claudeOpus"; :>> method = VerificationMethod::analyze; :>> procedureText = "Autonomous retro (D0049). WELL: the human caught a real process-integrity miss (a new obligation-view ignored governing-version, re-introducing grandfathering) and I corrected COURSE rather than doubling down — reverted the wrong reclassification, refused the retroactive guard, fixed the view, and captured the durable design rule (D0123) + tracked issue068. AVOIDABLE-ISSUE (banked): NEW computed obligation-views/guards must be checked against governing-version + retroactivity BEFORE shipping — add to the review checklist. LESSON: when adding a control/view, ask 'does this respect creation-time governance?' — the engine already had the resolver; the miss was not using it. Estimate 2 pts. NEXT: N-18 disposition."; }
    part rqgRetroGateR1 : TestResult { :>> id = "63940516-2c7d-4e8f-c228-51627384c00f"; :>> outcome = VerdictKind::pass; :>> judgedAgainst = "3d36c57"; :>> judgedAt = "2026-07-15"; :>> judgedBy = "claudeOpus"; }
}
