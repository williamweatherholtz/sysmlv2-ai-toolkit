// ProjectDeliveryS538 — Sprint 538: the remaining controls are proven, and the controls view counts its evidence. EXECUTE. 3 pts.
package ProjectDeliveryS538 {
    private import EngineElement::*;
    private import EngineWork::*;
    private import EngineVerification::*;
    private import EngineRelationships::*;

    #CharteredBy dependency from armingStory to d0298;

    part armingStory : Story {
        :>> id = "828c8262-e531-4ea6-886b-e6af72234024";
        :>> title = "Sprint 538: four arming probes (edit gate, turn gate, override, adherence audit), five arming entries, and an armingEvidence count that tells proof from reasoning (3 pts)";
        :>> createdAt = "2026-09-04"; :>> createdBy = "claudeOpus5"; :>> kind = WorkKind::code; :>> priority = WorkPriority::p0; :>> owner = "claudeOpus5"; :>> estimatedPoints = 3;
    }

    action def DeliveryRunS538 {
        action storyArming;
        verification storyArmingDoD : Test { :>> id = "b8678a35-2ac1-4f48-82b7-5700e161a461"; :>> method = VerificationMethod::test; :>> procedureText = "DELIVERED BACKLOG ITEMS: dcProveTheRemainingControls (resolves issue303). DONE: remaining_controls_actually_fire.rs - ctlPostEditGate (clean edit silent, unparseable edit blocked), ctlTurnBoundaryGate (fresh scaffold ends its turn, broken file cannot), ctlOverrideObligation (denied; one path opened once, a second path stays closed; the write announced; an obligation recorded; denied again), ctlAuditAdherence (unchanged range passes; unsigned downgrade fails naming the rule; signed downgrade passes); control-arming.toml gains those four plus ctlAdoptionCheck naming adoption_check_can_fail.rs; the controls view reads provenBy, checks the file exists (PROOF-MISSING otherwise) and carries armingEvidence. VERIFY: 4/4 new probes; read-back 1 probe-armed, 11 proven by test, 3 reason-only with reasons, 0 missing, 0 undeclared; 471 tests; clippy clean."; }
        // RAN: cargo test --release --test remaining_controls_actually_fire 4/4; full suite 471/0; clippy 0; KEEL_OFFLINE=1 keel show controls . -> armingEvidence {armedByProbe 1, provenByTest 11, reasonOnly 3, proofMissing 0, notArmed 0, undeclared 0}; before the entries the same view listed five controls UNDECLARED
        part storyArmingDoDR1 : TestResult { :>> id = "2785bf93-6644-4c17-a39b-cbd47532dd51"; :>> outcome = VerdictKind::pass; :>> judgedAgainst = "d3338c3"; :>> judgedAt = "2026-09-04"; :>> judgedBy = "claudeOpus5"; }
    }

    verification armingRefineGate : Test { :>> id = "3c1892cb-49f8-459d-a9a2-3a856b37b52a"; :>> title = "Sprint 538 refine gate (DoR)"; :>> createdAt = "2026-09-04"; :>> createdBy = "claudeOpus5"; :>> method = VerificationMethod::inspect; :>> procedureText = "READY from the DoD's own rule - allow before refuse - and from the read-back that opened the sprint: the view listed five controls UNDECLARED, one of which had been proven for several sprints. The DoD's list of seven was already half done by sprint 486 and its successors; the sprint scoped to what the view still could not show."; }
    verification armingStandupGate : Test { :>> id = "c19cb5f9-3185-41d4-bc25-e8ffd137dff9"; :>> title = "Sprint 538 standup gate"; :>> createdAt = "2026-09-04"; :>> createdBy = "claudeOpus5"; :>> method = VerificationMethod::inspect; :>> procedureText = "ONE CHOICE: the turn-gate probe uses a `keel init` scaffold, not the bare seed the pre-write probes use, because the turn gate runs every guard and only a real project passes them - a bare fixture would have made the ALLOW half fail and tempted a weaker assertion. Second: the view checks that a provenBy file exists; an entry naming a deleted test is the arming-view equivalent of a receipt naming a command that was never run (D0232)."; }
    verification armingImplementGate : Test { :>> id = "e2bb3256-a767-4d68-b267-8515a002d42c"; :>> title = "Sprint 538 implement gate"; :>> createdAt = "2026-09-04"; :>> createdBy = "claudeOpus5"; :>> method = VerificationMethod::test; :>> procedureText = "RAN: all four probes passed on the first run, which was checked rather than trusted - each asserts a refusal with a named reason after an allow, so a vacuous pass would need the control to both allow and block the same fixture. Three clippy items on the view (a Json variant that does not exist, a cast, a function grown past 100 lines - extracted). The arming TOML is keystone-locked under contracts, so D0298 rides the commit."; }
    verification armingReviewGate : Test { :>> id = "6c05784f-6884-41cf-b74a-ccd1a25211fa"; :>> title = "Sprint 538 review gate — three passes per D0172"; :>> createdAt = "2026-09-04"; :>> createdBy = "claudeOpus5"; :>> method = VerificationMethod::inspect; :>> procedureText = "THREE PASSES. (1) ARE THE THREE REASON-ONLY CONTROLS A GAP: they are infrastructure the binary cannot observe - GitHub branch protection, CI run records - and each says so; the DoD called that a legitimate outcome when stated, and the count now shows 3 so nobody mistakes them for proven. (2) DOES PROVEN-BY-TEST OVERCLAIM: it asserts that a named test exists and (by CI) passes; it does not assert the test is GOOD - that is the sitting review's to judge, and the file is named so it can be opened. (3) WHAT THE HARNESS CAVEAT STILL IS: whether Claude Code invokes the hooks at all remains a harness property (issue248); D0296's launch pin and status line are what address it, not these probes."; }
    verification armingCloseOutGate : Test { :>> id = "cba18243-472b-4e5b-af6b-1d06402cb8fb"; :>> title = "Sprint 538 closeOut gate (autonomous, D0049)"; :>> createdAt = "2026-09-04"; :>> createdBy = "claudeOpus5"; :>> method = VerificationMethod::inspect; :>> procedureText = "CLOSED. issue303 resolves; CLAUDE.md's lens list names the evidence count; every declared control has an entry."; }
    verification armingRetroGate : Test { :>> id = "6cb63e45-9f5c-4f62-9b93-4ff3694664f3"; :>> title = "Sprint 538 retro gate (autonomous, D0049)"; :>> createdAt = "2026-09-04"; :>> createdBy = "claudeOpus5"; :>> method = VerificationMethod::analyze; :>> procedureText = "no new item - already tracked: the harness-invocation caveat is issue248 and D0296's programme; the review's second pass (a named test is not a judged test) is the sitting-review pull-audit D0204 already provides. The one-line lesson: ctlAdoptionCheck had been proven for sprints and read as UNDECLARED because nobody had looked at the count - the count now exists, and d0298 says a control declared without evidence will show as 1."; }
}
