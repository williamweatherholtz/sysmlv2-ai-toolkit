// ProjectDeliveryS633 — Sprint 633: Sprint 633: A CliCommand synopsis that cites a Decision cites one that exists and is not retired - guard cli-surface-declared holds the citation to the tree in both fact homes (dcSynopsisCitesLiveDecisions, issue423, D0412). EXECUTE under the Change Request route: guard source is the enforcement surface. 2 pts.. EXECUTE. 2 pts.
package ProjectDeliveryS633 {
    private import EngineElement::*;
    private import EngineWork::*;
    private import EngineVerification::*;
    private import EngineRelationships::*;

    #CharteredBy dependency from synopsisCitesLiveDecisionsStory to d0412;

    part synopsisCitesLiveDecisionsStory : Story {
        :>> id = "f1b22ba8-149e-4a02-9a32-915ff91e48db";
        :>> title = "Sprint 633: Sprint 633: A CliCommand synopsis that cites a Decision cites one that exists and is not retired - guard cli-surface-declared holds the citation to the tree in both fact homes (dcSynopsisCitesLiveDecisions, issue423, D0412). EXECUTE under the Change Request route: guard source is the enforcement surface. 2 pts. (2 pts)";
        :>> createdAt = "2026-09-09"; :>> createdBy = "claudeOpus5"; :>> kind = WorkKind::code; :>> priority = WorkPriority::p0; :>> owner = "claudeOpus5"; :>> estimatedPoints = 2;
    }

    action def DeliveryRunS633 {
        action storySynopsisCitesLiveDecisions;
        verification storySynopsisCitesLiveDecisionsDoD : Test { :>> id = "c571cd66-2b2c-4950-a71b-6d25755b9857"; :>> method = VerificationMethod::test; :>> procedureText = "DELIVERED (dcSynopsisCitesLiveDecisions, resolves issue423 through that item): guards.rs decision_ids_cited extracts every dNNNN/DNNNN whole token, decision_ids_present reads the ids with a file under .engine/decisions, synopsis_citation_violations fails a retired id naming its superseder and an absent id naming the id, and cli_surface_declared applies it to the authored facts and the cli_facts.rs mirror alike; lib.rs supersede_edges keeps the (superseder, retired) pair and supersede_targets projects it. PROBED (D0388) before the real tree was read: known-positive a fixture synopsis citing D0353 (the push gate, retired by D0356) -> violation naming d0356; known-negative the corrected suite synopsis citing D0356 -> no violation; both named in the unit test a_synopsis_citing_a_retired_or_absent_decision_is_a_violation_and_the_live_suite_synopsis_is_not. Live probe on the wired guard: the suite citation edited to D0353 in commands.sysml -> keel guard cli-surface-declared FAIL 107 scanned 2 violations (the mirror drift and the retired citation, naming d0356); restored -> PASS 107 scanned 0 violations. D0412 records the change (process-change, proposed for the human); guards.md says the rule in the same words."; }
        // RAN: cargo test --release -p keel-cli --lib -> 438 passed (probe pair: fixture citing D0353 -> violation naming d0356; live suite synopsis citing D0356 -> none); keel guard cli-surface-declared . -> PASS 107 scanned 0 violations; live probe with suite edited to D0353 -> FAIL 2 violations naming d0356, restored -> PASS; cargo clippy --workspace --all-targets -- -D warnings -> Finished
        part storySynopsisCitesLiveDecisionsDoDR1 : TestResult { :>> id = "8d4b2de7-7dbf-48d7-9043-898a778301e8"; :>> outcome = VerdictKind::pass; :>> judgedAgainst = "70ce93c"; :>> judgedAt = "2026-09-09"; :>> judgedBy = "claudeOpus5"; }
    }

    verification synopsisCitesLiveDecisionsRefineGate : Test { :>> id = "22907524-233d-4a44-abba-c1afafec0105"; :>> title = "Sprint 633 refine gate (DoR)"; :>> createdAt = "2026-09-09"; :>> createdBy = "claudeOpus5"; :>> method = VerificationMethod::inspect; :>> procedureText = "Definition of Ready: dcSynopsisCitesLiveDecisions at the head of keel whats-next . after 70ce93c; its DoD names the property (retired or absent citation fails in either home), the DO (extract tokens, resolve against decision files and the Supersede set) and the VERIFY (the probe pair named in the receipt, guard green on the real tree); no fork - the guard is the only home for the check; 2 points - two source files, three tests, a guards.md row and a Decision."; }
    // RAN: sprint633 Refine: see the record's section; cargo test --release -p keel-cli --lib -> 438 passed (probe pair: fixture citing D0353 -> violation naming d0356; live suite synopsis citing D0356 -> none); keel guard cli-surface-declared . -> PASS 107 scanned 0 violations; live probe with suite edited to D0353 -> FAIL 2 violations naming d0356, restored -> PASS; cargo clippy --workspace --all-targets -- -D warnings -> Finished
    part synopsisCitesLiveDecisionsRefineGateR1 : TestResult { :>> id = "1e557dec-4d06-4fa3-8dc1-edc49d463c8f"; :>> outcome = VerdictKind::pass; :>> judgedAgainst = "70ce93c"; :>> judgedAt = "2026-09-09"; :>> judgedBy = "claudeOpus5"; }
    verification synopsisCitesLiveDecisionsStandupGate : Test { :>> id = "08f25eb2-ad7a-4204-9c92-ee221bbef5da"; :>> title = "Sprint 633 standup gate"; :>> createdAt = "2026-09-09"; :>> createdBy = "claudeOpus5"; :>> method = VerificationMethod::inspect; :>> procedureText = "No blocker. One design point settled by reading: supersede_targets returns the target alone, and a violation that cannot name the superseder makes the fix a search - so the scan is generalised to supersede_edges and the target set becomes its projection, leaving every existing caller unchanged."; }
    // RAN: sprint633 Standup: see the record's section; cargo test --release -p keel-cli --lib -> 438 passed (probe pair: fixture citing D0353 -> violation naming d0356; live suite synopsis citing D0356 -> none); keel guard cli-surface-declared . -> PASS 107 scanned 0 violations; live probe with suite edited to D0353 -> FAIL 2 violations naming d0356, restored -> PASS; cargo clippy --workspace --all-targets -- -D warnings -> Finished
    part synopsisCitesLiveDecisionsStandupGateR1 : TestResult { :>> id = "c48c07b8-e3d4-4a40-9884-b4260cea21b7"; :>> outcome = VerdictKind::pass; :>> judgedAgainst = "70ce93c"; :>> judgedAt = "2026-09-09"; :>> judgedBy = "claudeOpus5"; }
    verification synopsisCitesLiveDecisionsImplementGate : Test { :>> id = "39888c6d-7b95-4bab-8b20-06c4cacb838c"; :>> title = "Sprint 633 implement gate"; :>> createdAt = "2026-09-09"; :>> createdBy = "claudeOpus5"; :>> method = VerificationMethod::test; :>> procedureText = "guards.rs and lib.rs patched through textpatch (guard633.py, clippy633.py); cargo test --release -p keel-cli --lib -> 438 passed; cargo clippy --workspace --all-targets -- -D warnings -> Finished after three pedantic findings (implicit hasher -> BTreeSet, single-item into_iter -> iter::once, doc paragraph and backticks); keel guard cli-surface-declared . -> PASS 107 scanned 0 violations on the real tree; live probe FAIL/PASS as the DoD names; keel record decision D0412 --process-change -> proposed, OUTSIDE standing consent."; }
    // RAN: sprint633 Implement: see the record's section; cargo test --release -p keel-cli --lib -> 438 passed (probe pair: fixture citing D0353 -> violation naming d0356; live suite synopsis citing D0356 -> none); keel guard cli-surface-declared . -> PASS 107 scanned 0 violations; live probe with suite edited to D0353 -> FAIL 2 violations naming d0356, restored -> PASS; cargo clippy --workspace --all-targets -- -D warnings -> Finished
    part synopsisCitesLiveDecisionsImplementGateR1 : TestResult { :>> id = "b0421bb6-651f-4c6e-be67-37f5a3c35bf1"; :>> outcome = VerdictKind::pass; :>> judgedAgainst = "70ce93c"; :>> judgedAt = "2026-09-09"; :>> judgedBy = "claudeOpus5"; }
    verification synopsisCitesLiveDecisionsReviewGate : Test { :>> id = "57dd065e-fc15-4360-9c2f-a069d9df7404"; :>> title = "Sprint 633 review gate — three passes per D0172"; :>> createdAt = "2026-09-09"; :>> createdBy = "claudeOpus5"; :>> method = VerificationMethod::inspect; :>> procedureText = "Three passes per D0172: (1) the token rule is tested at its edges - a lowercase id, a repeated id, an item name beginning with d, a five-digit run, a run inside an identifier, a bare D035, and the (D0201 B) form; (2) the violation text names the home, the command, the id and the superseder, and the test asserts on each of those words, not on the count alone; (3) the live tree is asserted green by a test that first asserts the retired set holds d0353, so a green result cannot come from an empty retired set."; }
    // RAN: sprint633 Review: see the record's section; cargo test --release -p keel-cli --lib -> 438 passed (probe pair: fixture citing D0353 -> violation naming d0356; live suite synopsis citing D0356 -> none); keel guard cli-surface-declared . -> PASS 107 scanned 0 violations; live probe with suite edited to D0353 -> FAIL 2 violations naming d0356, restored -> PASS; cargo clippy --workspace --all-targets -- -D warnings -> Finished
    part synopsisCitesLiveDecisionsReviewGateR1 : TestResult { :>> id = "c0f60115-2dd2-498f-8c20-7e1ec4e9bec5"; :>> outcome = VerdictKind::pass; :>> judgedAgainst = "70ce93c"; :>> judgedAt = "2026-09-09"; :>> judgedBy = "claudeOpus5"; }
    verification synopsisCitesLiveDecisionsCloseOutGate : Test { :>> id = "4657bd1a-113f-4540-9838-4a42229abdab"; :>> title = "Sprint 633 closeOut gate (autonomous, D0049)"; :>> createdAt = "2026-09-09"; :>> createdBy = "claudeOpus5"; :>> method = VerificationMethod::inspect; :>> procedureText = "keel validate . clean, keel check-engine . clean, keel gate --fast clean; dcSynopsisCitesLiveDecisions DoD stamped with the probe pair and the live FAIL/PASS named."; }
    // RAN: sprint633 CloseOut: see the record's section; cargo test --release -p keel-cli --lib -> 438 passed (probe pair: fixture citing D0353 -> violation naming d0356; live suite synopsis citing D0356 -> none); keel guard cli-surface-declared . -> PASS 107 scanned 0 violations; live probe with suite edited to D0353 -> FAIL 2 violations naming d0356, restored -> PASS; cargo clippy --workspace --all-targets -- -D warnings -> Finished
    part synopsisCitesLiveDecisionsCloseOutGateR1 : TestResult { :>> id = "4d8f97fd-e627-43be-98e8-f116915ebde5"; :>> outcome = VerdictKind::pass; :>> judgedAgainst = "70ce93c"; :>> judgedAt = "2026-09-09"; :>> judgedBy = "claudeOpus5"; }
    verification synopsisCitesLiveDecisionsRetroGate : Test { :>> id = "254219e7-236d-48e6-a0e1-4d7a852e94de"; :>> title = "Sprint 633 retro gate (autonomous, D0049)"; :>> createdAt = "2026-09-09"; :>> createdBy = "claudeOpus5"; :>> method = VerificationMethod::analyze; :>> procedureText = "Avoidable-issue scan: the defect was a citation held equal to its copy but not to what it cited; the check that would have caught it read two homes and never the tree. The same shape - a mirror check that compares copies and not the referent - is dcGuardWarningsAreActionable's neighbour on the frontier and already tracked; no new item is needed beyond issue423's resolver, which this sprint delivers."; }
    // RAN: sprint633 Retro: see the record's section; cargo test --release -p keel-cli --lib -> 438 passed (probe pair: fixture citing D0353 -> violation naming d0356; live suite synopsis citing D0356 -> none); keel guard cli-surface-declared . -> PASS 107 scanned 0 violations; live probe with suite edited to D0353 -> FAIL 2 violations naming d0356, restored -> PASS; cargo clippy --workspace --all-targets -- -D warnings -> Finished
    part synopsisCitesLiveDecisionsRetroGateR1 : TestResult { :>> id = "605cc405-70c7-40c8-b692-4822b8afc772"; :>> outcome = VerdictKind::pass; :>> judgedAgainst = "70ce93c"; :>> judgedAt = "2026-09-09"; :>> judgedBy = "claudeOpus5"; }
}
