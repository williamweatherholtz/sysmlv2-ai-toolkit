// ProjectDeliveryS392 — Sprint 392: the ambient-actor audit: every agent-callable write surface swept for actors resolved from ambient state; the class closed at the endpoints. EXECUTE. 2 pts.
package ProjectDeliveryS392 {
    private import EngineElement::*;
    private import EngineWork::*;
    private import EngineVerification::*;
    private import EngineRelationships::*;

    #CharteredBy dependency from ambientActorAuditStory to d0178;

    part ambientActorAuditStory : Story {
        :>> id = "101b9903-4c33-472d-8d61-89f8f1017e70";
        :>> title = "Sprint 392: no write surface resolves its judge (2 pts)";
        :>> createdAt = "2026-08-21"; :>> createdBy = "claudeFable5"; :>> kind = WorkKind::code; :>> priority = WorkPriority::p0; :>> owner = "claudeFable5"; :>> estimatedPoints = 2;
    }

    action def DeliveryRunS392 {
        action storyAmbientActorAudit;
        verification storyAmbientActorAuditDoD : Test { :>> id = "bbc0ef3c-c0c0-4b0e-88c7-384265a13549"; :>> method = VerificationMethod::test; :>> procedureText = "DELIVERED: the WRITE_OPS-anchored sweep sprint 390's review gate named. AUDIT TABLE (all 16 declared write endpoints + the console page + the deck): CLEAN BY CONSTRUCTION - /api/deck/sitting (Person-verified `by`), /api/commit (attribution reasoning recorded, D0182 note 3), /api/launch/form + /api/run/ask + /api/run/asks (no attestation), /api/item /api/edge /api/resolver /api/item/attr /api/project /api/testresult /api/decision-author (mechanical or authoring writes where the session binding IS the correct actor). DEFECTS FOUND AND FIXED: (1) /api/disposition, /api/decision/accept, /api/decision/reject, /api/gate-result resolved an omitted judged_by from the machine binding - the issue197/199 vector - and now REFUSE without it; (2) /api/run/answer took no actor at all and an allow left no record (issue200): `by` is now required + registered-Person-verified, the poll returns it, an ALLOW records a tracked obligation naming the approver (mirroring the override tier's K7 consumption record), and a human DENY is recorded as THEIR judgment while expiry stays attributed to the run; (3) console.html hardcoded judged_by='wweatherholtz' on test results and defaulted CANCELLED prompts to the human's name - a cancelled dialog forged an attestation - now one judgedBy() helper that records nothing without a name, fed by the new GET /api/persons so no page ships a hardcoded human; (4) the ask queue had NO surface (issue201, doc claimed 'console renders it') - the console now polls /api/run/asks and answers with the named human. KEEL_API_VERSION 1.17.0 -> 2.0.0 (breaking: required fields). VERIFIED live on a scratch instance: all four refusals return 400 with the rule named; ask round-trip returns answer+by; /api/persons lists the one registered Person; cargo test 277 passed, clippy pedantic+nursery clean."; }
        part storyAmbientActorAuditDoDR1 : TestResult { :>> id = "b017b423-3d04-4350-9e21-b1049b8e41df"; :>> outcome = VerdictKind::pass; :>> judgedAgainst = "7aa0779"; :>> judgedAt = "2026-08-21"; :>> judgedBy = "claudeFable5"; }
    }

    verification ambientActorAuditRefineGate : Test { :>> id = "fec4c7fe-23a9-44bd-b71e-42cb2df65008"; :>> title = "Sprint 392 refine gate (DoR)"; :>> createdAt = "2026-08-21"; :>> createdBy = "claudeFable5"; :>> method = VerificationMethod::inspect; :>> procedureText = "DoR. Chartered by d0178 (K6: human-judgment writes are human-channel-only); the sweep was named as the next control in sprint 390's review gate, anchored on the WRITE_OPS table. Scope: audit first, fix what the audit finds, record what it clears. 2 points."; }
    part ambientActorAuditRefineGateR1 : TestResult { :>> id = "0181f73c-ec45-4053-b32a-155022c8194a"; :>> outcome = VerdictKind::pass; :>> judgedAgainst = "7aa0779"; :>> judgedAt = "2026-08-21"; :>> judgedBy = "claudeFable5"; }
    verification ambientActorAuditStandupGate : Test { :>> id = "118dfbb3-530b-4161-853d-fe54ea2dea3b"; :>> title = "Sprint 392 standup gate"; :>> createdAt = "2026-08-21"; :>> createdBy = "claudeFable5"; :>> method = VerificationMethod::inspect; :>> procedureText = "Approach: enumerate KEEL_API_WRITE_ENDPOINTS, read each handler's actor sourcing, classify attestation-grade (judge must arrive in the gesture) vs mechanical (session binding is the actor), fix the former, leave the latter with recorded reasoning. Then sweep the CLIENTS (console page, deck) for baked-in or defaulted names. No blockers."; }
    part ambientActorAuditStandupGateR1 : TestResult { :>> id = "970656dc-759c-402b-8e76-1cea5af3081b"; :>> outcome = VerdictKind::pass; :>> judgedAgainst = "7aa0779"; :>> judgedAt = "2026-08-21"; :>> judgedBy = "claudeFable5"; }
    verification ambientActorAuditImplementGate : Test { :>> id = "f8e010a8-fa36-4756-89c4-11b0af39eb8c"; :>> title = "Sprint 392 implement gate"; :>> createdAt = "2026-08-21"; :>> createdBy = "claudeFable5"; :>> method = VerificationMethod::test; :>> procedureText = "Fixes verified by live probes against a scratch serve on port 7779, not by reading the diff: POST /api/disposition|decision/accept|gate-result without judged_by -> 400 naming the rule; POST /api/run/answer with by=claudeFable5 -> 400 (not a registered Person); ask round-trip: register -> answer as wweatherholtz -> poll returns {answer:allow, by:wweatherholtz} -> asks list carries state+by. grep confirms zero occurrences of the human's name left in console.html. cargo test 277 passed 0 failed; clippy clean under deny(pedantic,nursery)."; }
    part ambientActorAuditImplementGateR1 : TestResult { :>> id = "1bebd870-0fb8-488d-9571-1b81cf766419"; :>> outcome = VerdictKind::pass; :>> judgedAgainst = "7aa0779"; :>> judgedAt = "2026-08-21"; :>> judgedBy = "claudeFable5"; }
    verification ambientActorAuditReviewGate : Test { :>> id = "48c9577c-60de-4347-b1d8-f2321c6eb7ea"; :>> title = "Sprint 392 review gate — three passes per D0172"; :>> createdAt = "2026-08-21"; :>> createdBy = "claudeFable5"; :>> method = VerificationMethod::inspect; :>> procedureText = "PASS 1, CLAIMS: every refusal claim is a live HTTP probe transcript, every count from the tool output. PASS 2, BOUNDARY: the deliberately-kept fallbacks are the boundary - /api/testresult et al. still resolve the binding, so an agent recording its own mechanical evidence is unaffected; probed that the SAME body without judged_by that fails on /api/disposition is the shape automation legitimately sends elsewhere. PASS 3, OWN DIFF: the addTestResult replacement initially referenced `by` without defining it - a page that would have thrown on every test-result click - caught by re-reading the emitted function, fixed by adding the judgedBy() call; the clippy option_if_let_else rewrite in headless_ask was machine-caught. WHAT A REVIEWER SHOULD ATTACK: the allow-record is written by the HOOK from the poll response rather than by the server at answer time, so a hook killed between allow and record loses the record - accepted for now because the hook is the only consumer and the ask evaporates with the server process either way; if runs ever multiplex consumers, move the record server-side."; }
    part ambientActorAuditReviewGateR1 : TestResult { :>> id = "eeb6ef1a-5b92-498a-acba-fda3580f635b"; :>> outcome = VerdictKind::pass; :>> judgedAgainst = "7aa0779"; :>> judgedAt = "2026-08-21"; :>> judgedBy = "claudeFable5"; }
    verification ambientActorAuditCloseOutGate : Test { :>> id = "24610bc8-7323-4ad0-984f-43ee9054bd8b"; :>> title = "Sprint 392 closeOut gate (autonomous, D0049)"; :>> createdAt = "2026-08-21"; :>> createdBy = "claudeFable5"; :>> method = VerificationMethod::inspect; :>> procedureText = "Autonomous closeOut (D0049). issue200 + issue201 recorded with this story as resolver before the fix landed; story DoD flipped at HEAD after live verification; validate + all 42 guards green; the human's console restarted on the new binary so the fixes are live on their lens."; }
    part ambientActorAuditCloseOutGateR1 : TestResult { :>> id = "c5d3e1d4-c3dd-4ce4-8212-4f0df82c7661"; :>> outcome = VerdictKind::pass; :>> judgedAgainst = "7aa0779"; :>> judgedAt = "2026-08-21"; :>> judgedBy = "claudeFable5"; }
    verification ambientActorAuditRetroGate : Test { :>> id = "af8f9ef2-9bf8-4872-a541-220cea501996"; :>> title = "Sprint 392 retro gate (autonomous, D0049)"; :>> createdAt = "2026-08-21"; :>> createdBy = "claudeFable5"; :>> method = VerificationMethod::analyze; :>> procedureText = "Autonomous retro (D0049). AVOIDABLE-ISSUE SCAN under rcRecurrence: THIRD+ occurrence of the ambient-actor class (issue197 inbox, issue199 local deck, now four endpoints + two client forgery-defaults + one unattributed channel) - the preventing change is structural this time: the endpoints REFUSE, so a future client cannot recreate the class against them; the residual risk is NEW write surfaces authored without the rule, and the WRITE_OPS table + this sprint's audit table are where the next reviewer anchors. WELL: auditing before fixing found two defects (issue200/201) that were not in the sprint-390 finding at all - the sweep earned its cost. Estimate 2 pts, delivered 2."; }
    part ambientActorAuditRetroGateR1 : TestResult { :>> id = "8cd4f159-cf75-48ef-a9a6-761a62d07633"; :>> outcome = VerdictKind::pass; :>> judgedAgainst = "7aa0779"; :>> judgedAt = "2026-08-21"; :>> judgedBy = "claudeFable5"; }
}
