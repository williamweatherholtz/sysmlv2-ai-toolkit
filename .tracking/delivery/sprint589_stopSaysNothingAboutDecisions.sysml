// ProjectDeliveryS589 — Sprint 589: the turn boundary stops talking about outstanding decisions, and the queue becomes a page that is refreshed when it moves. EXECUTE. 1 pts.
package ProjectDeliveryS589 {
    private import EngineElement::*;
    private import EngineWork::*;
    private import EngineVerification::*;
    private import EngineRelationships::*;

    #CharteredBy dependency from stopSaysNothingAboutDecisionsStory to d0359;

    part stopSaysNothingAboutDecisionsStory : Story {
        :>> id = "32a878fd-15a8-4539-9db9-3cd3e7a28130";
        :>> title = "Sprint 589: the turn boundary stops talking about outstanding decisions, and the queue becomes a page that is refreshed when it moves (1 pts)";
        :>> createdAt = "2026-09-06"; :>> createdBy = "claudeOpus5"; :>> kind = WorkKind::code; :>> priority = WorkPriority::p0; :>> owner = "claudeOpus5"; :>> estimatedPoints = 1;
    }

    action def DeliveryRunS589 {
        action storyStopSaysNothingAboutDecisions;
        verification storyStopSaysNothingAboutDecisionsDoD : Test { :>> id = "0ca6a341-9833-4e2a-a04b-b054ac725212"; :>> method = VerificationMethod::test; :>> procedureText = "DELIVERED BACKLOG ITEM: dcStopSaysNothingAboutDecisions, chartered by D0359 and accepted on the owner's quoted words. DONE: the Stop hook's green branch returns silently whether or not Decisions wait; its one-line helper, the now-unused decision short-name reader, and serve::obligations_total are DELETED rather than disabled, since each existed only to feed that line. keel show authority-queue carries each row's shortName, so the decision page can be built from one lens. The decision-surfacing process and skill are reshaped from re-surface-every-turn into a post-analysis with a STATE TEST: read the lens, compare with the ids last published, and produce nothing at all when they match. The brief's computed-facts script and its two chart modules move from a session scratchpad into scripts/exec_brief/. CLAUDE.md stops describing a line the binary no longer emits. VERIFIED: keel suite 562 passed 0 failed; stop_says_nothing_about_decisions 3/3 including the case with two Decisions pending; the rebound property test 1/1; facts.py 51 facts with none null; validate 668; guard ALL PASS; clippy -D warnings clean."; }
        // RAN: keel suite . = 562 passed 0 failed (receipt 95df485b038f); keel validate 668; keel guard ALL PASS; clippy -D warnings clean
        part storyStopSaysNothingAboutDecisionsDoDR1 : TestResult { :>> id = "5636163e-1735-4f19-8014-dc4617ad09ef"; :>> outcome = VerdictKind::pass; :>> judgedAgainst = "HEAD"; :>> judgedAt = "2026-09-06"; :>> judgedBy = "claudeOpus5"; }
    }

    verification stopSaysNothingAboutDecisionsRefineGate : Test { :>> id = "978656be-141f-478f-ae21-5cb5c414ab4d"; :>> title = "Sprint 589 refine gate (DoR)"; :>> createdAt = "2026-09-06"; :>> createdBy = "claudeOpus5"; :>> method = VerificationMethod::inspect; :>> procedureText = "READY: the owner's instruction was two things - remove the stop text, and replace it with a post-analysis that publishes rather than narrates. The one design question was what makes silence honest rather than forgetful, and the answer is a state test against what was last published, not a habit of remembering."; }
    // RAN: keel suite . = 562 passed 0 failed (receipt 95df485b038f)
    part stopSaysNothingAboutDecisionsRefineGateR1 : TestResult { :>> id = "23942f7f-db7d-44e2-b140-c5a44e3f599d"; :>> outcome = VerdictKind::pass; :>> judgedAgainst = "HEAD"; :>> judgedAt = "2026-09-06"; :>> judgedBy = "claudeOpus5"; }
    verification stopSaysNothingAboutDecisionsStandupGate : Test { :>> id = "d22a7561-0092-4b6f-b926-689ea36ff903"; :>> title = "Sprint 589 standup gate"; :>> createdAt = "2026-09-06"; :>> createdBy = "claudeOpus5"; :>> method = VerificationMethod::inspect; :>> procedureText = "THE SKILL I WAS REPLACING TOLD ME TO REPEAT. decision-surfacing's own step 6 said re-surface the link every turn and lead every response with it. So both surfaces were repeating, and only one of them could actually be decided from. That is why this change edits the process, not just the hook."; }
    // RAN: keel suite . = 562 passed 0 failed (receipt 95df485b038f)
    part stopSaysNothingAboutDecisionsStandupGateR1 : TestResult { :>> id = "de9d910c-f13a-4fe1-b32b-b9ebf2ee840e"; :>> outcome = VerdictKind::pass; :>> judgedAgainst = "HEAD"; :>> judgedAt = "2026-09-06"; :>> judgedBy = "claudeOpus5"; }
    verification stopSaysNothingAboutDecisionsImplementGate : Test { :>> id = "5b9a2dbd-5a3c-4656-823e-f7ffc144b843"; :>> title = "Sprint 589 implement gate"; :>> createdAt = "2026-09-06"; :>> createdBy = "claudeOpus5"; :>> method = VerificationMethod::test; :>> procedureText = "RAN: the green branch reduced to a silent return and the helper deleted; authority-queue rows given a shortName and read back through the lens; the process's detect, lead and carry steps rewritten; the skill rewritten around the state test; scripts/exec_brief/ populated and facts.py run from the repository root; cargo clippy -D warnings clean; keel suite twice - the first run caught a test asserting the SOURCE TEXT of the removed branch."; }
    // RAN: keel suite . = 562 passed 0 failed (receipt 95df485b038f)
    part stopSaysNothingAboutDecisionsImplementGateR1 : TestResult { :>> id = "2bff8f26-3599-45a8-9cb9-2f12e3e71c49"; :>> outcome = VerdictKind::pass; :>> judgedAgainst = "HEAD"; :>> judgedAt = "2026-09-06"; :>> judgedBy = "claudeOpus5"; }
    verification stopSaysNothingAboutDecisionsReviewGate : Test { :>> id = "3f3cfd40-8de8-4872-beaa-cbf992ba1f0c"; :>> title = "Sprint 589 review gate — three passes per D0172"; :>> createdAt = "2026-09-06"; :>> createdBy = "claudeOpus5"; :>> method = VerificationMethod::inspect; :>> procedureText = "THREE PASSES. (1) IS ANYTHING LEFT THAT ONLY EXISTED FOR THE LINE: yes, two things, and both are now deleted - the console-parity count and its test. (2) DOES THE REPLACEMENT HAVE A CONTROL: no, and it is stated as a residual in the skill and in the Decision rather than implied - no gate reads conversational output, so what keeps this honest is that the assessment is one command anyone can re-run against the published page. (3) DOES ANY DOC STILL DESCRIBE THE OLD BEHAVIOUR: CLAUDE.md did; corrected in the same commit."; }
    // RAN: keel suite . = 562 passed 0 failed (receipt 95df485b038f)
    part stopSaysNothingAboutDecisionsReviewGateR1 : TestResult { :>> id = "392a9b5d-9198-4f02-9652-563e37cbd97a"; :>> outcome = VerdictKind::pass; :>> judgedAgainst = "HEAD"; :>> judgedAt = "2026-09-06"; :>> judgedBy = "claudeOpus5"; }
    verification stopSaysNothingAboutDecisionsCloseOutGate : Test { :>> id = "2f082f89-d671-4e6c-b78c-fd2b89aed48d"; :>> title = "Sprint 589 closeOut gate (autonomous, D0049)"; :>> createdAt = "2026-09-06"; :>> createdBy = "claudeOpus5"; :>> method = VerificationMethod::inspect; :>> procedureText = "CLOSED. A green turn ends silent, and what waits on the human is computable by anyone who asks and published when it changes."; }
    // RAN: keel suite . = 562 passed 0 failed (receipt 95df485b038f)
    part stopSaysNothingAboutDecisionsCloseOutGateR1 : TestResult { :>> id = "f0ee47c1-dc8d-4468-9c76-5b047a4b0c22"; :>> outcome = VerdictKind::pass; :>> judgedAgainst = "HEAD"; :>> judgedAt = "2026-09-06"; :>> judgedBy = "claudeOpus5"; }
    verification stopSaysNothingAboutDecisionsRetroGate : Test { :>> id = "0e6a018a-702f-4289-ab2a-c5cac1d2a5be"; :>> title = "Sprint 589 retro gate (autonomous, D0049)"; :>> createdAt = "2026-09-06"; :>> createdBy = "claudeOpus5"; :>> method = VerificationMethod::analyze; :>> procedureText = "AVOIDABLE-ISSUE SCAN HELD. The avoidable one: a test asserted the literal source text of the branch it was policing, so deleting the branch broke it - and its own doc comment described exactly that failure mode, having been written when its PREDECESSOR broke the same way. Twice now, in the same file, for the same reason. NEW ITEM dcTestsBindToPropertiesNotSource (issue388). I first wrote here that no guard was possible because a test that greps its own source cannot be forbidden mechanically. That was wrong and the retro-backlog guard is what made me look again: a test that reads program source with include_str! and asserts on substrings of it is perfectly detectable. What is genuinely undecided is the TIER, since several checks here read files on purpose - the doc-claim, guard-catalogue and CLI-surface tests - so a blanket refusal would break legitimate controls; that choice is the substance of the item rather than an excuse for not raising it. The unavoidable one: nothing forces a post-analysis to run, which is a residual of the channel and not a defect of this change."; }
    // RAN: keel suite . = 562 passed 0 failed (receipt 95df485b038f)
    part stopSaysNothingAboutDecisionsRetroGateR1 : TestResult { :>> id = "2d8b0ac4-8ff3-45c3-91ab-bc1632d6cce4"; :>> outcome = VerdictKind::pass; :>> judgedAgainst = "HEAD"; :>> judgedAt = "2026-09-06"; :>> judgedBy = "claudeOpus5"; }
}
