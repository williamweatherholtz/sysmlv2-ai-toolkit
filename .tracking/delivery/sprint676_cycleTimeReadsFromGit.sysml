// ProjectDeliveryS676 — Sprint 676: Cycle time and time per story point read from GIT, in minutes, not from judgedAt in days. The human's question this answers (st119, 2026-09-11): do story points predict how long a sprint takes? judgedAt could not say - every sprint judged on one day read 0 - and issue483/issue485 recorded that the flow report's velocity and cycle cards were therefore not measurements. Now `keel report flow` and the new lens `keel show flow --json` compute, per sprint, the wall minutes from the first commit adding its delivery file to the commit that records its retro result, carry the elapsed time from the preceding repository commit beside it, and say on which basis the point-calibration verdict stands (D0448).. EXECUTE. 3 pts.
package ProjectDeliveryS676 {
    private import EngineElement::*;
    private import EngineWork::*;
    private import EngineVerification::*;
    private import EngineRelationships::*;

    #CharteredBy dependency from cycleTimeReadsFromGitStory to d0448;

    part cycleTimeReadsFromGitStory : Story {
        :>> id = "4227c701-2844-41c9-a4d9-3e4de62c62ed";
        :>> title = "Sprint 676: Cycle time and time per story point read from GIT, in minutes, not from judgedAt in days. The human's question this answers (st119, 2026-09-11): do story points predict how long a sprint takes? judgedAt could not say - every sprint judged on one day read 0 - and issue483/issue485 recorded that the flow report's velocity and cycle cards were therefore not measurements. Now `keel report flow` and the new lens `keel show flow --json` compute, per sprint, the wall minutes from the first commit adding its delivery file to the commit that records its retro result, carry the elapsed time from the preceding repository commit beside it, and say on which basis the point-calibration verdict stands (D0448). (3 pts)";
        :>> createdAt = "2026-09-11"; :>> createdBy = "claudeOpus5"; :>> kind = WorkKind::code; :>> priority = WorkPriority::p0; :>> owner = "claudeOpus5"; :>> estimatedPoints = 3;
    }

    action def DeliveryRunS676 {
        action storyCycleTimeReadsFromGit;
        verification storyCycleTimeReadsFromGitDoD : Test { :>> id = "aab0fa38-ff96-4496-ab77-36f1afba164a"; :>> method = VerificationMethod::test; :>> procedureText = "keel-cli/src/view/flow.rs computes the per-sprint series from git (3 git logs and one batched cat-file): sprint, points, state (closed/open), minutes, elapsedMinutes, commits; a sprint with no recorded retro result (pass OR proposed, D0448) in any commit is open and never contributes a 0; a project outside git is reported unreadable, never 0. `keel report flow` cards: Cycle time (median first commit to retro landing, hours when under a day, with the one-commit count and the elapsed median), Time / story point (both bases), Inter-commit gap (median and p90 minutes, last 7 days against the 7 before), Point calibration (last 80 closed sprints, per-bucket median/p90 on both bases, verdict named on its basis; buckets under 3 sprints do not vote). `keel show flow [--json]` is a CliCommand (cli_facts.rs, commands.sysml, cli_surface.rs, main.rs dispatch). Tests: view::flow:: unit tests (10) and flow_cycle_time_from_git integration pair (30 and 90 minutes read 30 and 90; a retro with no landing commit is open with minutes null; a project outside git is an error, never a zero). usage.md's flow rows name both."; }
        // RAN: verifier receipt batch3 head=40190c5: keel suite --touched -> 710 passed 0 failed 700 s (touched-1789134894.log); keel show flow --json . -> sprints 674 closed 568 open 106 calibration predictive; flow_cycle_time_from_git in the touched set
        part storyCycleTimeReadsFromGitDoDR1 : TestResult { :>> id = "55cf7123-fd05-4d01-9dad-462ea5cb8984"; :>> outcome = VerdictKind::pass; :>> judgedAgainst = "40190c5"; :>> judgedAt = "2026-09-11"; :>> judgedBy = "claudeOpus5"; }
    }

    verification cycleTimeReadsFromGitRefineGate : Test { :>> id = "5af451d5-01be-4c6e-9dd4-e17f1529a683"; :>> title = "Sprint 676 refine gate (DoR)"; :>> createdAt = "2026-09-11"; :>> createdBy = "claudeOpus5"; :>> method = VerificationMethod::inspect; :>> procedureText = "Chartered by D0448 (accepted under standing consent; NOT A PROCESS CHANGE - it fixes the meaning of one computed view; NOT A FORK). Resolves issue483 and issue485. Built by a parallel implementer in a worktree, integrated by the manager. 3 points: a new lens with its facts and dispatch, one report reworked, two test tiers, and the git reading measured (report 5.6 s, lens 3.8 s on this tree)."; }
    // RAN: verifier receipt batch3 head=40190c5: keel suite --touched -> 710 passed 0 failed 700 s (touched-1789134894.log); validate exit 0; check-engine exit 0; guard ALL PASS exit 0; chartered by d0448 (accepted under standing consent); 3 points; task dcCycleTimeReadsFromGit; resolves issue483 issue485
    part cycleTimeReadsFromGitRefineGateR1 : TestResult { :>> id = "bc6db5bf-4b09-4d18-baed-8cc97316262e"; :>> outcome = VerdictKind::proposed; :>> judgedAgainst = "40190c5"; :>> judgedAt = "2026-09-11"; :>> judgedBy = "claudeOpus5"; }
    verification cycleTimeReadsFromGitStandupGate : Test { :>> id = "c37f3e5b-2fca-4978-b51d-e2508db77122"; :>> title = "Sprint 676 standup gate"; :>> createdAt = "2026-09-11"; :>> createdBy = "claudeOpus5"; :>> method = VerificationMethod::inspect; :>> procedureText = "Order: flow.rs (series, buckets, calibration) then reports.rs (cards) then main.rs/cli_surface.rs/cli_facts.rs/commands.sysml (the lens) then usage.md then the tests. Blockers met and fixed in the build: the p90 index read floor((n-1)*0.9) and gave 10 for [10,60]; fixed to nearest-rank ceil(0.9n). Two test-side failures (report flow takes --root, the lens pretty-prints) fixed in the tests; the engine's answers were 30 / 90 / open / null throughout. Integration blocker: usage.md's report row conflicted with the controls row from sprint 674 in the same table; resolved by keeping both rows and the new flow row."; }
    // RAN: verifier receipt batch3 head=40190c5: keel suite --touched -> 710 passed 0 failed 700 s (touched-1789134894.log); validate exit 0; check-engine exit 0; guard ALL PASS exit 0; p90 index fixed to nearest-rank in the build; usage.md row conflict resolved keeping all three rows
    part cycleTimeReadsFromGitStandupGateR1 : TestResult { :>> id = "9f57e75e-20e8-4023-bb32-2953b5125ed1"; :>> outcome = VerdictKind::proposed; :>> judgedAgainst = "40190c5"; :>> judgedAt = "2026-09-11"; :>> judgedBy = "claudeOpus5"; }
    verification cycleTimeReadsFromGitImplementGate : Test { :>> id = "7a7fbfb9-e890-40c4-bcc2-064a620821a6"; :>> title = "Sprint 676 implement gate"; :>> createdAt = "2026-09-11"; :>> createdBy = "claudeOpus5"; :>> method = VerificationMethod::test; :>> procedureText = "keel-cli/src/view/flow.rs (new): FlowSeries, the git reads, the retro-landing rule (pass or proposed), elapsed companion, buckets and the nearest-rank p90. keel-cli/src/view/reports.rs: the four cards and their basis wording. keel-cli/src/view/mod.rs, keel-cli/src/main.rs, keel-cli/src/cli_surface.rs, keel-cli/src/cli_facts.rs, .engine/cli/commands.sysml:110 (cliFlow): `keel show flow`. .engine/docs/usage.md: the report row and the flow row. keel-cli/tests/flow_cycle_time_from_git.rs: three tests."; }
    // RAN: verifier receipt batch3 head=40190c5: keel suite --touched -> 710 passed 0 failed 700 s (touched-1789134894.log); validate exit 0; check-engine exit 0; guard ALL PASS exit 0; flow_cycle_time_from_git 3 tests and view::flow unit tests in the touched set
    part cycleTimeReadsFromGitImplementGateR1 : TestResult { :>> id = "a11041ad-998f-4ce4-8ea4-2abc0e2b3802"; :>> outcome = VerdictKind::pass; :>> judgedAgainst = "40190c5"; :>> judgedAt = "2026-09-11"; :>> judgedBy = "claudeOpus5"; }
    verification cycleTimeReadsFromGitReviewGate : Test { :>> id = "7ad007f1-6ac0-466c-9149-3706a65a815f"; :>> title = "Sprint 676 review gate — three passes per D0172"; :>> createdAt = "2026-09-11"; :>> createdBy = "claudeOpus5"; :>> method = VerificationMethod::inspect; :>> procedureText = "Delivered, on this tree at the receipt: 568 closed sprints, 538 of them born and closed in one commit, so the DoD-literal interval is 0 for 80 of the last 80 and points predict nothing on that basis; on the elapsed basis the medians order by points - 1 pt 18 min, 2 pt 29, 3 pt 39, 5 pt 98 - and the card says `predictive` on that basis, naming it. That is the answer to st119: the estimates are not noise, and the reason the old cards could not show it was the clock, not the points. Inter-commit gap for the last 7 days: 31 min median (p90 114) against 4 min (p90 117) the week before, tone warn - the slowdown the human named is on the card as a number. Residual: elapsedMinutes is an upper bound (it counts unrelated work between the preceding commit and the sprint's birth); lead time, predictability, throughput and aging WIP still read day-granular dates."; }
    // RAN: verifier receipt batch3 head=40190c5: keel suite --touched -> 710 passed 0 failed 700 s (touched-1789134894.log); validate exit 0; check-engine exit 0; guard ALL PASS exit 0; keel show flow --json . -> 1 pt 18 min 2 pt 29 3 pt 39 5 pt 98 elapsed basis; inter-commit gap 31 vs 4 min
    part cycleTimeReadsFromGitReviewGateR1 : TestResult { :>> id = "4851c7f8-2c3f-4fdf-a38b-a6fd947cd450"; :>> outcome = VerdictKind::proposed; :>> judgedAgainst = "40190c5"; :>> judgedAt = "2026-09-11"; :>> judgedBy = "claudeOpus5"; }
    verification cycleTimeReadsFromGitCloseOutGate : Test { :>> id = "ac9a63a6-c425-42f7-9850-3c3e0b13c3e1"; :>> title = "Sprint 676 closeOut gate (autonomous, D0049)"; :>> createdAt = "2026-09-11"; :>> createdBy = "claudeOpus5"; :>> method = VerificationMethod::inspect; :>> procedureText = "Sprint 676 closes on the verifier's receipt only (D0425). dcCycleTimeReadsFromGit gets its DoD result; issue483 and issue485 resolve through it (computed). D0448 is accepted at record time under standing consent."; }
    // RAN: verifier receipt batch3 head=40190c5: keel suite --touched -> 710 passed 0 failed 700 s (touched-1789134894.log); validate exit 0; check-engine exit 0; guard ALL PASS exit 0; dcCycleTimeReadsFromGitDoDR1 recorded at 40190c5; issue483 issue485 resolve through it
    part cycleTimeReadsFromGitCloseOutGateR1 : TestResult { :>> id = "cd458c4e-0468-4a4f-882f-6f88cccc0811"; :>> outcome = VerdictKind::proposed; :>> judgedAgainst = "40190c5"; :>> judgedAt = "2026-09-11"; :>> judgedBy = "claudeOpus5"; }
    verification cycleTimeReadsFromGitRetroGate : Test { :>> id = "6880ba62-6ec8-4a26-9240-552e9334c248"; :>> title = "Sprint 676 retro gate (autonomous, D0049)"; :>> createdAt = "2026-09-11"; :>> createdBy = "claudeOpus5"; :>> method = VerificationMethod::analyze; :>> procedureText = "AVOIDABLE-ISSUE SCAN: No new item - already tracked: issue490 (this batch's verifier typed DISCREPANCIES: NONE over a failed run; resolver dcVerifierReceiptOutcomeIsRenderedNotTyped, recorded this commit) and issue491 (hook ran the wrong tree's binary). FINDING: one-commit sprints are 95 percent of this project's history, so the measure the DoD literally asked for is 0 almost everywhere; the implementer measured that before coding, drafted the Decision that names the companion interval, and stated NOT A PROCESS CHANGE so it could land under standing consent - the D0388 order applied to a metric's definition."; }
    // RAN: verifier receipt batch3 head=40190c5: keel suite --touched -> 710 passed 0 failed 700 s (touched-1789134894.log); validate exit 0; check-engine exit 0; guard ALL PASS exit 0; retro names issue490 and issue491 (already tracked); no new item
    part cycleTimeReadsFromGitRetroGateR1 : TestResult { :>> id = "43c6e93d-9b5f-4d6b-b4d4-d8191931e7dd"; :>> outcome = VerdictKind::proposed; :>> judgedAgainst = "40190c5"; :>> judgedAt = "2026-09-11"; :>> judgedBy = "claudeOpus5"; }
}
