// ProjectDeliveryS301 — Sprint 301: D0148 applied — the EngineCodeAudit module ships, and the six
// `keel arch` views compute over a real authored registry. CHANGE + EXECUTE. 13 pts.
package ProjectDeliveryS301 {
    private import EngineElement::*;
    private import EngineWork::*;
    private import EngineVerification::*;
    private import EngineRelationships::*;

    #CharteredBy dependency from archViewsStory to d0148;

    part archViewsStory : Story {
        :>> id = "0d800280-0814-6280-9b3e-000000300280";
        :>> title = "Sprint 301: ship EngineCodeAudit + the six keel arch views (13 pts)";
        :>> createdAt = "2026-08-15"; :>> createdBy = "claudeOpus5"; :>> kind = WorkKind::code; :>> priority = WorkPriority::p0; :>> owner = "claudeOpus5"; :>> estimatedPoints = 13;
    }

    action def DeliveryRunS301 {
        action storyArchViews;
        verification storyArchViewsDoD : Test { :>> id = "0d800281-0814-6281-9b3e-000000300281"; :>> method = VerificationMethod::test; :>> procedureText = "Applies D0148 (accepted by wweatherholtz 2026-08-15) and delivers keelArchViews. SHIPPED: (1) `.engine/schema/codeaudit/codeelement.sysml` as a third schema module beside `core` and `safety` — CodeElement + RiskClass/InvariantSafety/StpaRole/DesignPattern + the #Controls/#Feedback/#Restructure markers. Kernel-checked 16/16. The markers are declared IN THE MODULE, not in frozen core: a module ships its own vocabulary (D0136) and the marker-vocabulary guard reads `metadata def` from any engine file, so no core edit was needed. `keel init` ships it automatically because `.engine` is embedded wholesale. (2) `keel arch elements|criticality|coupling|drift|stpa-inputs|coverage`, all COMPUTED, from ONE model build. (3) Six Viewpoints declared in the registry, which the viewpoint-renderer guard then required be real commands. VERIFIED ON REAL DATA — see the review gate for why it is keel's own code and not SelfSync's: criticality ranks the four dataLoss elements and the one security element above every correctness element; coupling computes Ca=4/Ce=1/I=0.20 for view.rs, which is the module the registry independently marks #Restructure; drift reports 3 current, then flags `claims (holder rule)` as DRIFTED when its body is changed and returns to current when reverted, on real source; stpa-inputs prints the captured control loop and flags a controller with no #Feedback return path; coverage reports module-level coverage honestly. A coverage-floored test per command plus a wrong-root test. clippy clean; 200 tests; validate 326 clean; check-engine clean; 32 guards green."; }
        part storyArchViewsDoDR1 : TestResult { :>> id = "0d800282-0814-6282-9b3e-000000300282"; :>> outcome = VerdictKind::pass; :>> judgedAgainst = "4bf8906"; :>> judgedAt = "2026-08-15"; :>> judgedBy = "claudeOpus5"; }
    }

    verification avRefineGate : Test { :>> id = "0d800283-0814-6283-9b3e-000000300283"; :>> title = "Sprint 301 refine gate (DoR)"; :>> createdAt = "2026-08-15"; :>> createdBy = "claudeOpus5"; :>> method = VerificationMethod::inspect; :>> procedureText = "DoR, with ONE CLAUSE OF THE ITEM DELIBERATELY NOT MET AS WRITTEN. keelArchViewsDoD says to verify 'on SelfSync's authored registry' — a different project's data this repo does not hold, which D0148's own consequences flagged as making the acceptance criterion unreachable from here. Re-scoped to keel's own source, recorded as issue117. That is the alternative D0148 accepted and NOT the one it rejected: the rejected option was a synthetic probe registry, which would demonstrate the commands run rather than that they compute anything true. keel's modules are real code with real consequences, so every riskClass in the registry is a judgment someone can disagree with — which is the property a probe cannot have. CONSUMER CHECK (dorConsumer, D0144): the consumer of `arch` is a maintainer deciding what to audit next, so `criticality` had to produce a defensible ORDER over real elements, not a list. estimatedPoints=13. DoR met."; }
    part avRefineGateR1 : TestResult { :>> id = "0d800284-0814-6284-9b3e-000000300284"; :>> outcome = VerdictKind::pass; :>> judgedAgainst = "4bf8906"; :>> judgedAt = "2026-08-15"; :>> judgedBy = "claudeOpus5"; }

    verification avStandupGate : Test { :>> id = "0d800285-0814-6285-9b3e-000000300285"; :>> title = "Sprint 301 standup gate"; :>> createdAt = "2026-08-15"; :>> createdBy = "claudeOpus5"; :>> method = VerificationMethod::inspect; :>> procedureText = "Approach: schema first and kernel-checked before anything reads it (issue097 — the Rust parser's acceptance is not conformance), then the views, then a real registry, then verification against it. No blockers."; }
    part avStandupGateR1 : TestResult { :>> id = "0d800286-0814-6286-9b3e-000000300286"; :>> outcome = VerdictKind::pass; :>> judgedAgainst = "4bf8906"; :>> judgedAt = "2026-08-15"; :>> judgedBy = "claudeOpus5"; }

    verification avImplementGate : Test { :>> id = "0d800287-0814-6287-9b3e-000000300287"; :>> title = "Sprint 301 implement gate"; :>> createdAt = "2026-08-15"; :>> createdBy = "claudeOpus5"; :>> method = VerificationMethod::test; :>> procedureText = "THREE DEFECTS, EACH OF WHICH PRODUCED A CONFIDENT WRONG ANSWER RATHER THAN AN ERROR. (1) `keel arch elements .` resolved its ROOT to `./elements`, because the shared `repo_arg` takes the first non-flag argument and the subcommand is one; the empty model then printed 'no CodeElement instances authored' — a confident empty answer about a directory that does not exist. Fixed at both ends: the arm skips the subcommand, and `load` now REFUSES a root with no `.tracking/`, because a wrong path and an empty registry must never print the same thing. (2) Edge kinds are LOWERCASED at ingest (view.rs edge_kind_from_marker), so matching `\"DependsOn\"` and `\"DerivedFrom\"` found nothing: coupling reported 0 edges over 10 authored ones and the criticality bump never fired. Both read as legitimate results. (3) `arch coverage` counted every top-level def in a file as an un-catalogued gap even when a `module` element takes responsibility for the whole file — 220 gaps reported against view.rs, mixing granularities so the number meant nothing. Now a module-covered file reports its def count as CONTEXT and only element-by-element files get a gap. ALSO: `abstractness` is String, not Real, following `Measurement.value` — the parser has no float token, and rather than teach it one for a single attribute, the engine's settled convention for a numeric datapoint was followed. A second convention would have made `0.2` legal in exactly one place."; }
    part avImplementGateR1 : TestResult { :>> id = "0d800288-0814-6288-9b3e-000000300288"; :>> outcome = VerdictKind::pass; :>> judgedAgainst = "4bf8906"; :>> judgedAt = "2026-08-15"; :>> judgedBy = "claudeOpus5"; }

    verification avReviewGate : Test { :>> id = "0d800289-0814-6289-9b3e-000000300289"; :>> title = "Sprint 301 review gate"; :>> createdAt = "2026-08-15"; :>> createdBy = "claudeOpus5"; :>> method = VerificationMethod::inspect; :>> procedureText = "Reviewed. THE REGISTRY IS 12 ELEMENTS AND THAT IS NOT COVERAGE — `arch coverage` says so in its own output, including the line that it can only look where the registry already points and therefore under-reports exactly where coverage is worst. Shipping the view without that sentence would have let a registry covering ten files read as a codebase of ten files. Two design refusals worth recording: distance-from-main-sequence prints `-` rather than deriving abstractness from `kind`, because a guess presented in a measurement column is indistinguishable from a measurement; and `stpa-inputs` hands over the captured control structure and stops, because inferring unsafe control actions from a recorded role would be an analysis wearing a view's clothes, carrying none of the human judgment STPA requires. The drift hash is FNV-1a, not `DefaultHasher`, which is explicitly unstable across Rust releases and would have made every element report as drifted after a toolchain upgrade."; }
    part avReviewGateR1 : TestResult { :>> id = "0d80028a-0814-628a-9b3e-00000030028a"; :>> outcome = VerdictKind::pass; :>> judgedAgainst = "4bf8906"; :>> judgedAt = "2026-08-15"; :>> judgedBy = "claudeOpus5"; }

    verification avCloseOutGate : Test { :>> id = "0d80028b-0814-628b-9b3e-00000030028b"; :>> title = "Sprint 301 closeOut gate (autonomous, D0049)"; :>> createdAt = "2026-08-15"; :>> createdBy = "claudeOpus5"; :>> method = VerificationMethod::inspect; :>> procedureText = "Autonomous closeOut (D0049); the frozen-core module it ships carries wweatherholtz's explicit sign-off as D0148. Doc-sync rides the commit: `_schema_files.py` registers the new module (a control caught its absence on the first kernel run), the viewpoint registry declares all six views, and the viewpoint-renderer guard's known-command list learned `arch` — which it demanded, correctly, by failing on six viewpoints naming a command it did not know. keelArchViews is re-scoped rather than met as written; issue117 records that. clippy clean; 200 tests; validate 326 clean; check-engine clean; validate_schema 16/16 kernel-side; 32 guards green. No gate bypassed."; }
    part avCloseOutGateR1 : TestResult { :>> id = "0d80028c-0814-628c-9b3e-00000030028c"; :>> outcome = VerdictKind::pass; :>> judgedAgainst = "4bf8906"; :>> judgedAt = "2026-08-15"; :>> judgedBy = "claudeOpus5"; }

    verification avRetroGate : Test { :>> id = "0d80028d-0814-628d-9b3e-00000030028d"; :>> title = "Sprint 301 retro gate (autonomous, D0049)"; :>> createdAt = "2026-08-15"; :>> createdBy = "claudeOpus5"; :>> method = VerificationMethod::analyze; :>> procedureText = "Autonomous retro (D0049) under D0131's retroTrack. WELL: (1) three separate CONTROLS caught my errors before I did — validate_schema refused an unregistered schema file, the in-loop edit gate refused a registry with bare float literals, and the viewpoint-renderer guard refused six viewpoints naming a command it did not know. None was manual vigilance; each was a control that already existed doing exactly its job, which is what D0047 is for. (2) The registry was authored against keel's own real code rather than a probe, and that alone surfaced the coverage-granularity defect, which a uniform synthetic fixture would have hidden. AVOIDABLE-ISSUE 1: THE RECURRING SHAPE THIS SPRINT IS A WRONG ANSWER THAT LOOKS LIKE A RIGHT ONE — a bad root printing 'no elements authored', a case-mismatched edge kind printing '0 edges', a granularity mismatch printing '220 un-catalogued'. All three were plausible outputs, so none announced itself; each was caught only by checking the number against something I already knew to be true (12 elements exist, 10 edges were authored, view.rs is one catalogued module). The generalisable control is that a view's first run must be checked against a known-value expectation, not read for plausibility. NO NEW ITEM: the coverage-floored tests now encode exactly those known values (a dataLoss element exists; #DependsOn edges exist), so the next regression fails a test rather than printing a believable zero. AVOIDABLE-ISSUE 2: I wrote a heredoc to git-bash `/tmp` then read it from Windows python, which cannot see it. Same host-adaptation class as issue065; the remedy is already recorded and I did not apply it. Estimate 13 pts, delivered."; }
    part avRetroGateR1 : TestResult { :>> id = "0d80028e-0814-628e-9b3e-00000030028e"; :>> outcome = VerdictKind::pass; :>> judgedAgainst = "4bf8906"; :>> judgedAt = "2026-08-15"; :>> judgedBy = "claudeOpus5"; }
}
