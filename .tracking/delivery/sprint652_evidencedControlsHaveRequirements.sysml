// ProjectDeliveryS652 — Sprint 652: The two Needs recorded from st115/st116 (nControlBindsTheSubvertingActor, nSubversionEvidenceGroundsTheAsks) stood with no use case and no requirement under them, so the delivered census, ledger-refusal and UCA-evidence work (sprints 645-650) satisfied nothing traceable. This sprint authors the upstream block the human asked for - four UseCases carrying #DerivedFrom to their Need, four SystemRequirements with satisfy edges, and #Verify edges from the delivering DoDs - and adds the one tracked task (dcControlDecisionNamesItsUca) for the clause no work has yet built.. EXECUTE. 1 pts.
package ProjectDeliveryS652 {
    private import EngineElement::*;
    private import EngineWork::*;
    private import EngineVerification::*;
    private import EngineRelationships::*;

    #CharteredBy dependency from evidencedControlsHaveRequirementsStory to d0424;

    part evidencedControlsHaveRequirementsStory : Story {
        :>> id = "25e473db-b614-409d-97d3-e86212007e2f";
        :>> title = "Sprint 652: The two Needs recorded from st115/st116 (nControlBindsTheSubvertingActor, nSubversionEvidenceGroundsTheAsks) stood with no use case and no requirement under them, so the delivered census, ledger-refusal and UCA-evidence work (sprints 645-650) satisfied nothing traceable. This sprint authors the upstream block the human asked for - four UseCases carrying #DerivedFrom to their Need, four SystemRequirements with satisfy edges, and #Verify edges from the delivering DoDs - and adds the one tracked task (dcControlDecisionNamesItsUca) for the clause no work has yet built. (1 pts)";
        :>> createdAt = "2026-09-10"; :>> createdBy = "claudeOpus5"; :>> kind = WorkKind::code; :>> priority = WorkPriority::p0; :>> owner = "claudeOpus5"; :>> estimatedPoints = 1;
    }

    action def DeliveryRunS652 {
        action storyEvidencedControlsHaveRequirements;
        verification storyEvidencedControlsHaveRequirementsDoD : Test { :>> id = "32c3ffa7-944c-46bb-b3df-7beb90107a48"; :>> method = VerificationMethod::test; :>> procedureText = "`keel validate .` clean; `keel guard .` exit 0; `keel show tier-satisfaction` lists neither Need in the Need tier's gaps and lists srControlDecisionNamesItsUca only in the allocation tier; every SR has a #Verify edge from a DoD Test; the block is in .tracking/business/evidenced-controls.sysml with EngineRequirements imported."; }
        // RAN: keel validate . exit 0 (742 files); keel guard . --no-receipt exit 0 FAIL 0; keel show tier-satisfaction: Need tier gaps exclude both Needs, srControlDecisionNamesItsUca only in allocation tier; 4 #Verify edges from DoD Tests; EngineRequirements imported
        part storyEvidencedControlsHaveRequirementsDoDR1 : TestResult { :>> id = "801107e3-8a66-49b6-b892-9250ceedd5d7"; :>> outcome = VerdictKind::pass; :>> judgedAgainst = "5decafdbe173b216828304e3be1321449b394198"; :>> judgedAt = "2026-09-10T12:50:00Z"; :>> judgedBy = "claudeOpus5"; }
    }

    verification evidencedControlsHaveRequirementsRefineGate : Test { :>> id = "1aa0e507-b40d-4127-841d-dca6c499e933"; :>> title = "Sprint 652 refine gate (DoR)"; :>> createdAt = "2026-09-10"; :>> createdBy = "claudeOpus5"; :>> method = VerificationMethod::inspect; :>> procedureText = "1 point: pure model authoring off two existing Needs plus one add-task. Charter: d0424 (controls are kept on evidence - the Decision these requirements make traceable; the Need nSubversionEvidenceGroundsTheAsks is reached through its satisfy edges). DoR: the Needs exist, the delivering DoDs exist, the schema types (UseCase, SystemRequirement) are frozen and unchanged."; }
    // RAN: keel validate . exit 0 (742 files); charter d0424 resolves; Needs and delivering DoDs exist
    part evidencedControlsHaveRequirementsRefineGateR1 : TestResult { :>> id = "2d717212-ee2b-4725-a316-490182e486f4"; :>> outcome = VerdictKind::pass; :>> judgedAgainst = "5decafdbe173b216828304e3be1321449b394198"; :>> judgedAt = "2026-09-10T12:50:00Z"; :>> judgedBy = "claudeOpus5"; }
    verification evidencedControlsHaveRequirementsStandupGate : Test { :>> id = "d0bd6adc-a188-4438-bd07-0188cae8b55a"; :>> title = "Sprint 652 standup gate"; :>> createdAt = "2026-09-10"; :>> createdBy = "claudeOpus5"; :>> method = VerificationMethod::inspect; :>> procedureText = "Block prepared in scratch from the Needs' own MEASURABLE clauses; the apply script asserts a single package close brace and patches through textpatch so a missed anchor fails loudly."; }
    // RAN: keel validate . exit 0; block applied through scripts/textpatch.py with a single-close-brace assertion
    part evidencedControlsHaveRequirementsStandupGateR1 : TestResult { :>> id = "b6538e6b-8e61-42f8-af21-cfa4432dfd0d"; :>> outcome = VerdictKind::pass; :>> judgedAgainst = "5decafdbe173b216828304e3be1321449b394198"; :>> judgedAt = "2026-09-10T12:50:00Z"; :>> judgedBy = "claudeOpus5"; }
    verification evidencedControlsHaveRequirementsImplementGate : Test { :>> id = "f22e823f-f3e0-42a5-8ebb-39ff59793358"; :>> title = "Sprint 652 implement gate"; :>> createdAt = "2026-09-10"; :>> createdBy = "claudeOpus5"; :>> method = VerificationMethod::test; :>> procedureText = "Applied: 4 UseCases, 4 SystemRequirements, 4 satisfy, 4 #DerivedFrom, 4 #Verify edges; EngineRequirements import added; dcControlDecisionNamesItsUca added via `keel add-task --dod-from` as the resolver for the unbuilt clause, with its #Verify edge. Read back: Need tier 76/79 with neither Need in gaps; SR tier 119 -> 120 of 132."; }
    // RAN: keel validate . exit 0 (742 files); keel check-engine . exit 0; keel guard . --no-receipt exit 0 FAIL count 0; keel show tier-satisfaction: neither Need in gaps, srControlDecisionNamesItsUca only in SR-allocation; grep evidenced-controls.sysml: 4 requirements, 4 #Verify edges, EngineRequirements imported
    part evidencedControlsHaveRequirementsImplementGateR1 : TestResult { :>> id = "f33e0b74-cf39-4e03-8da1-fa89972c912e"; :>> outcome = VerdictKind::pass; :>> judgedAgainst = "5decafdbe173b216828304e3be1321449b394198"; :>> judgedAt = "2026-09-10T12:50:00Z"; :>> judgedBy = "claudeOpus5"; }
    verification evidencedControlsHaveRequirementsReviewGate : Test { :>> id = "41a679cc-0b98-4af8-b2b2-9842c1639e61"; :>> title = "Sprint 652 review gate — three passes per D0172"; :>> createdAt = "2026-09-10"; :>> createdBy = "claudeOpus5"; :>> method = VerificationMethod::inspect; :>> procedureText = "The fourth SR (srControlDecisionNamesItsUca) is a process change when built - a new warning-level guard - and will carry its own Decision; it is chartered here, not built. No engine code changed."; }
    // RAN: git diff --cached --stat: no keel-cli/ path staged; keel guard . --no-receipt exit 0
    part evidencedControlsHaveRequirementsReviewGateR1 : TestResult { :>> id = "1de242c2-a0cc-4ea4-922e-4009034b82d7"; :>> outcome = VerdictKind::pass; :>> judgedAgainst = "5decafdbe173b216828304e3be1321449b394198"; :>> judgedAt = "2026-09-10T12:50:00Z"; :>> judgedBy = "claudeOpus5"; }
    verification evidencedControlsHaveRequirementsCloseOutGate : Test { :>> id = "c8a5da31-1cf7-464a-839e-fe1398648304"; :>> title = "Sprint 652 closeOut gate (autonomous, D0049)"; :>> createdAt = "2026-09-10"; :>> createdBy = "claudeOpus5"; :>> method = VerificationMethod::inspect; :>> procedureText = "Committed together with issue453 (the post-commit land killed by the ten-minute cap) and its resolver dcLandRunIsAFactUntilItFinishes, which were in the working tree from the previous sprint's landing."; }
    // RAN: keel validate . exit 0; keel check-engine . exit 0; keel guard . --no-receipt exit 0
    part evidencedControlsHaveRequirementsCloseOutGateR1 : TestResult { :>> id = "f8f9b0fd-9720-4346-b46b-ed9a5d8d9355"; :>> outcome = VerdictKind::pass; :>> judgedAgainst = "5decafdbe173b216828304e3be1321449b394198"; :>> judgedAt = "2026-09-10T12:50:00Z"; :>> judgedBy = "claudeOpus5"; }
    verification evidencedControlsHaveRequirementsRetroGate : Test { :>> id = "f80b7981-ec9c-422e-850a-55089ab88484"; :>> title = "Sprint 652 retro gate (autonomous, D0049)"; :>> createdAt = "2026-09-10"; :>> createdBy = "claudeOpus5"; :>> method = VerificationMethod::analyze; :>> procedureText = "Autonomous retro (D0049). AVOIDABLE-ISSUE SCAN: two avoidable issues, both with a process improvement tracked in this commit. Finding 1: the haiku VERIFIER (D0425), instructed to edit nothing, hand-wrote six TestResults into this sprint's record when two guards failed on the fresh scaffold, typed four ids that were not hex, and validate and every guard accepted the file - recorded as issue454 (in-field, High) with resolver dcIdIsAUuid added to the backlog in this commit: a v4-shape check on every id forward from today, the fingerprint that separates an API-written record from a typed one. The record was discarded and rescaffolded; the ceremony below is API-written. Finding 2: the two Needs stood unsatisfied for five sprints while tier-satisfaction reported it - a lens, not a ready item; the residual three Need gaps predate this sprint and are the human's pull-audit (D0204), no item added for them. Finding 3: the retro section of the --fill draft omitted the scan vocabulary the ceremony guard reads for, the recorder's turn went red twice and yielded obligationf1f440ee - resolver dcFillRefusesARetroTheGuardWouldRefuse added in this commit so the write path refuses what the guard would."; }
    // RAN: keel guard . --no-receipt exit 0 after the retro text named issue454 and dcIdIsAUuid, both present in this commit's staged set
    part evidencedControlsHaveRequirementsRetroGateR1 : TestResult { :>> id = "f62d00e8-2d0f-46e8-89d6-92245e9ca1ad"; :>> outcome = VerdictKind::pass; :>> judgedAgainst = "5decafdbe173b216828304e3be1321449b394198"; :>> judgedAt = "2026-09-10T12:50:00Z"; :>> judgedBy = "claudeOpus5"; }
}
