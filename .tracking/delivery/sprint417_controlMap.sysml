// ProjectDeliveryS417 — Sprint 417: D0195 delivered, all eight clauses: the hazard/control trace computes - zero uncovered hazards - and the bare vanilla dependency became a first-class parsed statement. EXECUTE. 3 pts.
package ProjectDeliveryS417 {
    private import EngineElement::*;
    private import EngineWork::*;
    private import EngineVerification::*;
    private import EngineRelationships::*;

    #CharteredBy dependency from controlMapStory to d0195;

    part controlMapStory : Story {
        :>> id = "4694f442-7a51-4056-b2f3-82e460751ae9";
        :>> title = "Sprint 417: controls become computable (3 pts)";
        :>> createdAt = "2026-08-22"; :>> createdBy = "claudeFable5"; :>> kind = WorkKind::code; :>> priority = WorkPriority::p0; :>> owner = "claudeFable5"; :>> estimatedPoints = 3;
    }

    action def DeliveryRunS417 {
        action storyControlMap;
        verification storyControlMapDoD : Test { :>> id = "b1c708bb-fdfd-48f5-a8b1-3e7cd14b0d2e"; :>> method = VerificationMethod::test; :>> procedureText = "DELIVERED: dcControlMapView (D0195, accepted on their 'looks great. proceed to implement'; resolves issues 221 and the AERO flip-2 lineage). ALL EIGHT CLAUSES: (1) every guard has a constraint-def identity (29 added to guard-constraints.sysml, completing the 45). (2) control-map.sysml - 54 SystemSafetyConstraint instances (45 guards + 9 non-guard controls: audit-history, branch protection, pre-push, write-lock, pre-write tiers, commit gate, release gate, fire-ledger, reverify), 55 plain-dependency discharge edges to the hazards. (3) keel controls - the two-way diff, READ BACK LIVE: uncoveredHazards EMPTY (every failure condition carries 2-12 computable controls), 7 process-quality constraints honestly reported unanchored. (5) eight #Controls/#Feedback edges complete the registry's control loops and disposition the stpa-inputs flag (the merged-tree gate verdict IS land's feedback). (6) every enforcement-point row now carries a one-word failMode classification (fail-closed / fail-open-announced / fail-open) derived from its own absent-behavior text. (7) the view lists High/Critical Issues since D0195's acceptance that reference no hazard - forward-only, currently empty. (8) srK16OutwardPublishGated authored (SR 103), verified against sprint 409's both-ways live-pipeline evidence, #DerivedFrom-edged to ehz9, allocated to ceLandGate/ceSyncIntegration - the release gate's removal is now a recorded violation. THE SPRINT'S OWN DISCOVERY: the bare vanilla `dependency from X to Y;` statement - the D0196 traceability form - was SILENTLY SKIPPED by the Rust parser (issue097's trap mirrored: kernel-conformant, invisible to every keel view; caught when the map's edges computed as absent). The parser now recognizes it as a first-class statement mapping to edge kind `dependency`, which also brought the knowledge record's 16 traces into the model."; }
        part storyControlMapDoDR1 : TestResult { :>> id = "841c9145-9829-4594-ab7d-3ef8d8eb9d94"; :>> outcome = VerdictKind::pass; :>> judgedAgainst = "cf3f25d"; :>> judgedAt = "2026-08-22"; :>> judgedBy = "claudeFable5"; }
    }

    verification controlMapRefineGate : Test { :>> id = "78b75bdf-4a76-4a45-9e54-a7d4201776f7"; :>> title = "Sprint 417 refine gate (DoR)"; :>> createdAt = "2026-08-22"; :>> createdBy = "claudeFable5"; :>> method = VerificationMethod::inspect; :>> procedureText = "DoR. Chartered by d0195 with its round-2 clauses 5-8 folded in pre-signature. 3 points."; }
    part controlMapRefineGateR1 : TestResult { :>> id = "9a734b1f-3c60-48c6-b43d-2690bd3e9b55"; :>> outcome = VerdictKind::pass; :>> judgedAgainst = "cf3f25d"; :>> judgedAt = "2026-08-22"; :>> judgedBy = "claudeFable5"; }
    verification controlMapStandupGate : Test { :>> id = "bcce7ffd-9532-440e-83d7-81e9ceb0d3a0"; :>> title = "Sprint 417 standup gate"; :>> createdAt = "2026-08-22"; :>> createdBy = "claudeFable5"; :>> method = VerificationMethod::inspect; :>> procedureText = "Approach: instances over defs for the map (SystemSafetyConstraint IS the constraint a control enforces - honest STPA typing), plain dependencies for discharge edges (no lens needed a marker), the view over exactly those two files, and read-back before recording. No blockers - one parser gap found and fixed mid-sprint."; }
    part controlMapStandupGateR1 : TestResult { :>> id = "0f5ca740-cc19-4f29-a55c-0fe165097c9c"; :>> outcome = VerdictKind::pass; :>> judgedAgainst = "cf3f25d"; :>> judgedAt = "2026-08-22"; :>> judgedBy = "claudeFable5"; }
    verification controlMapImplementGate : Test { :>> id = "648d9f4b-518f-4d29-8ec9-432a59c0b1f9"; :>> title = "Sprint 417 implement gate"; :>> createdAt = "2026-08-22"; :>> createdBy = "claudeFable5"; :>> method = VerificationMethod::test; :>> procedureText = "Verified by running: keel controls returns uncoveredHazards=[] with per-hazard control counts (ehz1:3 ... ehz4:12 ... ehz9:2) and 7 unanchored; tier-satisfaction reads 103/103 verified and 20/103 allocated after srK16; validate 460 clean; edge-endpoints green over the 55 new edges; the parser change is covered by the whole corpus re-parsing (460 files) plus clippy and the full suite green; check-engine clean."; }
    part controlMapImplementGateR1 : TestResult { :>> id = "d1c09444-435c-47cf-957c-0d6f3ba30930"; :>> outcome = VerdictKind::pass; :>> judgedAgainst = "cf3f25d"; :>> judgedAt = "2026-08-22"; :>> judgedBy = "claudeFable5"; }
    verification controlMapReviewGate : Test { :>> id = "ea020511-bf41-4db9-996f-8c7670d5016a"; :>> title = "Sprint 417 review gate — three passes per D0172"; :>> createdAt = "2026-08-22"; :>> createdBy = "claudeFable5"; :>> method = VerificationMethod::inspect; :>> procedureText = "PASS 1, CLAIMS: every number above is a live command read-back from this session. PASS 2, BOUNDARY: the first controls run returned ALL hazards uncovered - the honest reading was not 'authoring failed' but 'the edges never entered the model', and chasing that boundary found the silently-skipped-statement gap; a less suspicious reading would have shipped a view computing over nothing. PASS 3, OWN DIFF: the parser arm was first written inline and machine-caught by the too-many-lines lint into a helper; the failMode classifier is a text heuristic over the rows' own absent-behavior strings - stated as such, not sold as typed data. WHAT A REVIEWER SHOULD ATTACK: the guard-to-hazard mapping is 54 one-line judgments (the file invites per-line dispute); and parser-coverage's skipped-statement census shrank with the new arm - anyone auditing that number should know why."; }
    part controlMapReviewGateR1 : TestResult { :>> id = "cbff14c9-344b-4499-baf1-7a0d101c1e48"; :>> outcome = VerdictKind::pass; :>> judgedAgainst = "cf3f25d"; :>> judgedAt = "2026-08-22"; :>> judgedBy = "claudeFable5"; }
    verification controlMapCloseOutGate : Test { :>> id = "34f9f839-9d68-4ec8-904f-b3cd81e8ebda"; :>> title = "Sprint 417 closeOut gate (autonomous, D0049)"; :>> createdAt = "2026-08-22"; :>> createdBy = "claudeFable5"; :>> method = VerificationMethod::inspect; :>> procedureText = "Autonomous closeOut (D0049). DoD flipped on the live read-backs; issue221 resolves via clause 8; the AERO partial from round 2 completes (the prose control trace is now typed and computable); validate + all 45 guards green."; }
    part controlMapCloseOutGateR1 : TestResult { :>> id = "6e33c598-d681-401e-8f8c-9c56e6eae00f"; :>> outcome = VerdictKind::pass; :>> judgedAgainst = "cf3f25d"; :>> judgedAt = "2026-08-22"; :>> judgedBy = "claudeFable5"; }
    verification controlMapRetroGate : Test { :>> id = "a82ea12c-8bbf-4622-a7f8-a18d4944fd91"; :>> title = "Sprint 417 retro gate (autonomous, D0049)"; :>> createdAt = "2026-08-22"; :>> createdBy = "claudeFable5"; :>> method = VerificationMethod::analyze; :>> procedureText = "Autonomous retro (D0049). AVOIDABLE-ISSUE SCAN under rcRecurrence: the silently-skipped-statement class recurred exactly as parser-coverage's own doc predicts - the preventing practice applied here: READ BACK the computed view immediately after authoring model content, so an ingestion gap surfaces as an absurd result (all-uncovered) rather than a quiet lie. WELL: the D0196 vanilla-first choice PAID - forcing plain dependencies flushed a parser gap that markered edges had been papering over; and the two-way diff's first honest output (7 unanchored process-quality controls) is exactly the shape the decision promised. Estimate 3 pts, delivered 3."; }
    part controlMapRetroGateR1 : TestResult { :>> id = "74aed164-2981-4e7a-a530-7f54c51d494b"; :>> outcome = VerdictKind::pass; :>> judgedAgainst = "cf3f25d"; :>> judgedAt = "2026-08-22"; :>> judgedBy = "claudeFable5"; }
}
