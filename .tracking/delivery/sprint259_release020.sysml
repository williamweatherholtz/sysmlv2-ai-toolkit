// ProjectDeliveryS259 — Sprint 259: operationalise the Deploy workflow, cut v0.2.0, and trim CLAUDE.md
// to the behaviour-changing core (D0135). First real run of a workflow defined ~250 sprints ago
// and never executed. EXECUTE. 5 pts.
package ProjectDeliveryS259 {
    private import EngineElement::*;
    private import EngineWork::*;
    private import EngineVerification::*;
    private import EngineRelationships::*;

    #CharteredBy dependency from release020Story to d0135;

    part release020Story : Story {
        :>> id = "0d760001-0814-5601-9b3e-000000260001";
        :>> title = "Sprint 259: deploy process + skill, v0.2.0 published, CLAUDE.md 522 -> 184 lines (5 pts)";
        :>> createdAt = "2026-08-14"; :>> createdBy = "claudeOpus5"; :>> kind = WorkKind::code; :>> priority = WorkPriority::p0; :>> owner = "claudeOpus5"; :>> estimatedPoints = 5;
    }

    action def DeliveryRunS259 {
        action storyRelease020;
        verification storyRelease020DoD : Test { :>> id = "0d760002-0814-5602-9b3e-000000260002"; :>> method = VerificationMethod::demo; :>> procedureText = "Delivers keelReleaseProcess (issue070/D0135) and dcContractDedup (issue086/D0135). RELEASE: added .engine/processes/deploy.sysml (reconcile version -> gate the exact tree -> tag so CI publishes -> record the Release) with its deploying `release` skill (D0059); per-milestone cadence. 'Reconcile' is defined explicitly as each version surface being DELIBERATE, not equal — the crate version tracks the shipped binary, KEEL_API_VERSION is a separate contract a downstream viewer pins. Crate 0.1.0 -> 0.2.0. VERIFIED END-TO-END, not asserted: CI green at e2c812f BEFORE tagging (the process's own precondition); annotated tag v0.2.0 pushed; the release workflow built natively on three platforms and ATTACHED all three assets — keel-linux-x86_64 (7,815,760 bytes), keel-macos-aarch64 (6,911,184), keel-windows-x86_64.exe (6,562,304) — checked via `gh release view`, because a tag whose build failed is worse than no tag; the v0.2.0 `Release` item is recorded with version/commit/purpose while CONTENTS stay a computed view over git ancestry. This makes the portable-gate guarantee real for D0129: a contributor now obtains a matching gate by DOWNLOAD rather than by installing a Rust toolchain. DOCS: CLAUDE.md 522 -> 184 lines, 45,690 -> 12,352 bytes (73% fewer bytes), reorganised to invariants / orient / routing table / working rules / validation commands / environment. The 120-line guard catalogue MOVED to .engine/docs/guards.md; the restated response contract REMOVED outright, which resolves issue086 by making the output style the single home in fact rather than in principle; a pre-existing broken doc reference (keel-syntax-notes -> sysmlv2-syntax-notes) fixed; every .engine path referenced in CLAUDE.md verified to resolve. VERIFY: validate 280 files clean; all 23 guards green; check-engine clean; clippy clean; process-skill green at 17 processes."; }
        part storyRelease020DoDR1 : TestResult { :>> id = "0d760003-0814-5603-9b3e-000000260003"; :>> outcome = VerdictKind::pass; :>> judgedAgainst = "e2c812f"; :>> judgedAt = "2026-08-14"; :>> judgedBy = "claudeOpus5"; }
    }

    verification rlRefineGate : Test { :>> id = "0d760004-0814-5604-9b3e-000000260004"; :>> title = "Sprint 259 refine gate (DoR)"; :>> createdAt = "2026-08-14"; :>> createdBy = "claudeOpus5"; :>> method = VerificationMethod::inspect; :>> procedureText = "DoR: the human asked to take process creation-and-sharing to a new project and, if ready, to cut a release with trimmed docs. READINESS WAS ANSWERED FIRST AND NEGATIVELY: nProcessPortability has three SRs and zero delivered work — no `keel process list/import/export/activate`, no activation manifest; `keel init` is all-or-nothing. That answer shaped the scope: release what EXISTS, and say plainly what does not, since the release was wanted for precisely the unbuilt feature. Scope: deploy process + skill, version, tag, Release item, doc trim. EXCLUDED: building process portability itself (three SRs, a multi-sprint subsystem). estimatedPoints=5. DoR met."; }
    part rlRefineGateR1 : TestResult { :>> id = "0d760005-0814-5605-9b3e-000000260005"; :>> outcome = VerdictKind::pass; :>> judgedAgainst = "e2c812f"; :>> judgedAt = "2026-08-14"; :>> judgedBy = "claudeOpus5"; }

    verification rlStandupGate : Test { :>> id = "0d760006-0814-5606-9b3e-000000260006"; :>> title = "Sprint 259 standup gate"; :>> createdAt = "2026-08-14"; :>> createdBy = "claudeOpus5"; :>> method = VerificationMethod::inspect; :>> procedureText = "Approach: check what already exists before building — the release WORKFLOW turned out to be complete and cross-platform already, so the gap was the process, the cadence, the record and the first run, not the pipeline. For the doc trim, MOVE the catalogue rather than delete it, and treat CLAUDE.md's size as a recurring per-turn tax rather than a tidiness question. No blockers."; }
    part rlStandupGateR1 : TestResult { :>> id = "0d760007-0814-5607-9b3e-000000260007"; :>> outcome = VerdictKind::pass; :>> judgedAgainst = "e2c812f"; :>> judgedAt = "2026-08-14"; :>> judgedBy = "claudeOpus5"; }

    verification rlImplementGate : Test { :>> id = "0d760008-0814-5608-9b3e-000000260008"; :>> title = "Sprint 259 implement gate"; :>> createdAt = "2026-08-14"; :>> createdBy = "claudeOpus5"; :>> method = VerificationMethod::demo; :>> procedureText = "Implemented at e2c812f, tag v0.2.0. The gate BLOCKED my first attempt at the release commit: sprint-coverage failed because I had marked keelReleaseProcess done before the release existed. That is the guard doing exactly its job against its own author — the premature results were removed and re-recorded only AFTER the assets were verified published, which is the order deploy.sysml prescribes. Assets confirmed by `gh release view`, not assumed from a green workflow badge."; }
    part rlImplementGateR1 : TestResult { :>> id = "0d760009-0814-5609-9b3e-000000260009"; :>> outcome = VerdictKind::pass; :>> judgedAgainst = "e2c812f"; :>> judgedAt = "2026-08-14"; :>> judgedBy = "claudeOpus5"; }

    verification rlReviewGate : Test { :>> id = "0d76000a-0814-560a-9b3e-00000026000a"; :>> title = "Sprint 259 review gate"; :>> createdAt = "2026-08-14"; :>> createdBy = "claudeOpus5"; :>> method = VerificationMethod::inspect; :>> procedureText = "Reviewed. The most important output is not the tag but the honest NO: the human wanted the release in order to use process creation-and-sharing on a new project, and that feature is unbuilt, so the release notes, the Release item and D0135 all say so explicitly. A release that let them discover it downstream would have been the real failure. Second: the doc trim is the highest-leverage change for a NEW project — 45KB injected every turn competes with the task itself, and moving the catalogue keeps the information while removing the recurring cost. Weakness accepted: the release commit's MESSAGE is guard output, because I passed the failed run's log file to `git commit -F`. It was already pushed, and D0129 forbids amend/force-push, so it stands; the substance lives in D0135, and the engine's own rule is that commit messages are not decision records (§4)."; }
    part rlReviewGateR1 : TestResult { :>> id = "0d76000b-0814-560b-9b3e-00000026000b"; :>> outcome = VerdictKind::pass; :>> judgedAgainst = "e2c812f"; :>> judgedAt = "2026-08-14"; :>> judgedBy = "claudeOpus5"; }

    verification rlCloseOutGate : Test { :>> id = "0d76000c-0814-560c-9b3e-00000026000c"; :>> title = "Sprint 259 closeOut gate (autonomous, D0049)"; :>> createdAt = "2026-08-14"; :>> createdBy = "claudeOpus5"; :>> method = VerificationMethod::inspect; :>> procedureText = "Autonomous closeOut (D0049). keelReleaseProcess and dcContractDedup carry passing DoD TestResults at e2c812f; issue070 and issue086 RESOLVE. v0.2.0 is published with three platform binaries. All three D0128 directions now have delivered work: governance (D0130/D0134 + the tiered gates), release (this), portability (still unbuilt — three SRs open). validate + all 23 guards + check-engine green; clippy clean."; }
    part rlCloseOutGateR1 : TestResult { :>> id = "0d76000d-0814-560d-9b3e-00000026000d"; :>> outcome = VerdictKind::pass; :>> judgedAgainst = "e2c812f"; :>> judgedAt = "2026-08-14"; :>> judgedBy = "claudeOpus5"; }

    verification rlRetroGate : Test { :>> id = "0d76000e-0814-560e-9b3e-00000026000e"; :>> title = "Sprint 259 retro gate (autonomous, D0049)"; :>> createdAt = "2026-08-14"; :>> createdBy = "claudeOpus5"; :>> method = VerificationMethod::analyze; :>> procedureText = "Autonomous retro (D0049) under D0131's retroTrack. WELL: (1) the readiness question was answered NEGATIVELY and prominently, before any work, because the release existed to serve a feature that does not; (2) checking what already existed found a complete release workflow and reduced the sprint to the parts genuinely missing; (3) published assets were VERIFIED via `gh release view` rather than inferred from a green run. AVOIDABLE-ISSUE 1: I marked keelReleaseProcess done BEFORE the release existed, and the sprint-coverage guard blocked the commit. NO NEW ITEM — the control caught it at the right moment and the deploy process now states the record-last ordering explicitly; recorded here because the slip was mine and the guard's catch is the reason it never landed. AVOIDABLE-ISSUE 2: I passed the FAILED run's log file to `git commit -F`, so the release commit's message is guard output; it was already pushed and D0129 forbids amending, so it stands uncorrected. NO NEW ITEM: the substance lives in D0135 and §4 already holds that commit messages are not decision records — but this is the fifth recorded instance this sitting of acting on an unverified intermediate, and the count is the point. Estimate 5 pts, delivered."; }
    part rlRetroGateR1 : TestResult { :>> id = "0d76000f-0814-560f-9b3e-00000026000f"; :>> outcome = VerdictKind::pass; :>> judgedAgainst = "e2c812f"; :>> judgedAt = "2026-08-14"; :>> judgedBy = "claudeOpus5"; }
}
