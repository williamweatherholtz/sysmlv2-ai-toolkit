// ProjectDeliveryS644 — Sprint 644: Sprint 644: the reduction the D0414 attribution pointed at and nobody owned (issue439) - the priority-inversion guard paid orient::compute whole to read one field. orient's frontier half becomes orient::ready, shared by whats-next and the priority lens, and skips the SHA validation and landing-commit binding when neither can change the list. On the way, the git-facts changed section was found holding every past HEAD's rows (issue440): it now keeps one head's. 3 pts.. EXECUTE. 3 pts.
package ProjectDeliveryS644 {
    private import EngineElement::*;
    private import EngineWork::*;
    private import EngineVerification::*;
    private import EngineRelationships::*;

    #CharteredBy dependency from frontierReadCheaplyStory to d0414;

    part frontierReadCheaplyStory : Story {
        :>> id = "4220d62b-d39c-4030-afa4-b969e5553a8d";
        :>> title = "Sprint 644: Sprint 644: the reduction the D0414 attribution pointed at and nobody owned (issue439) - the priority-inversion guard paid orient::compute whole to read one field. orient's frontier half becomes orient::ready, shared by whats-next and the priority lens, and skips the SHA validation and landing-commit binding when neither can change the list. On the way, the git-facts changed section was found holding every past HEAD's rows (issue440): it now keeps one head's. 3 pts. (3 pts)";
        :>> createdAt = "2026-09-10"; :>> createdBy = "claudeOpus5"; :>> kind = WorkKind::code; :>> priority = WorkPriority::p0; :>> owner = "claudeOpus5"; :>> estimatedPoints = 3;
    }

    action def DeliveryRunS644 {
        action storyFrontierReadCheaply;
        verification storyFrontierReadCheaplyDoD : Test { :>> id = "c7af270e-cd4f-4c34-b780-725b352c7cd7"; :>> method = VerificationMethod::test; :>> procedureText = "DELIVERED: dcPriorityGuardReadsTheFrontierCheaply resolves issue439 - orient::ready computes the frontier alone, whats-next and priority_signals read it, valid_commits and binding::bind run only when evidence is read or the clone can judge; dcChangedCacheKeepsOneHead resolves issue440 - remember_changed retains the current head's rows only. VERIFY: show priority, whats-next and orient byte-identical old versus new binary on this tree; whats-next 3.1 s to 1.55 s standalone; KEEL_PERF=1 keel guard --no-receipt names verification-trace as the critical path on three runs (4318, 4289, 4385 ms) with priority-inversion at 4042-4102 ms under parallel load, set wall clock 6573 to 5940 ms; lib 452 passed; orient_bdd and no_green_over_nothing pass; the new gitfacts test probed to fail with the retention removed; clippy clean."; }
        // RAN: the two resolver results above; clippy --workspace --all-targets -D warnings clean; orient_bdd + no_green_over_nothing 2 passed
        part storyFrontierReadCheaplyDoDR1 : TestResult { :>> id = "76867c92-ac87-4f4f-85a6-419fb00a7867"; :>> outcome = VerdictKind::pass; :>> judgedAgainst = "a6bc47b"; :>> judgedAt = "2026-09-09T20:30:00-06:00"; :>> judgedBy = "claudeOpus5"; }
    }

    verification frontierReadCheaplyRefineGate : Test { :>> id = "ea2582e9-a029-45a6-8b3a-33c4aca58973"; :>> title = "Sprint 644 refine gate (DoR)"; :>> createdAt = "2026-09-10"; :>> createdBy = "claudeOpus5"; :>> method = VerificationMethod::inspect; :>> procedureText = "Definition of Ready: issue439 High, recorded 2026-09-09 with resolver dcPriorityGuardReadsTheFrontierCheaply ranked at the frontier head and read back; the change is bounded to orient.rs, one call site each in view/mod.rs and main.rs, and remember_changed in gitfacts.rs; 3 points for the refactor of compute_orient into two halves."; }
    // RAN: sprint 644 ceremony step Refine, recorded against the fill text
    part frontierReadCheaplyRefineGateR1 : TestResult { :>> id = "01caa8ae-792f-481b-a6b8-d32e88873948"; :>> outcome = VerdictKind::pass; :>> judgedAgainst = "a6bc47b"; :>> judgedAt = "2026-09-09T20:30:00-06:00"; :>> judgedBy = "claudeOpus5"; }
    verification frontierReadCheaplyStandupGate : Test { :>> id = "c7df1a85-af33-4534-bfaf-aaa5dc09456e"; :>> title = "Sprint 644 standup gate"; :>> createdAt = "2026-09-10"; :>> createdBy = "claudeOpus5"; :>> method = VerificationMethod::inspect; :>> procedureText = "No blocker. The first split saved 600 ms and left the critical path where it was; only phase attribution (frontier:valid-commits 808 ms, gitfacts:load 416 ms, frontier:bind 188 ms) found the two git spawns that could not change the answer in the guard's state."; }
    // RAN: sprint 644 ceremony step Standup, recorded against the fill text
    part frontierReadCheaplyStandupGateR1 : TestResult { :>> id = "c37babb3-9bc9-487b-a13e-1b6958714ea3"; :>> outcome = VerdictKind::pass; :>> judgedAgainst = "a6bc47b"; :>> judgedAt = "2026-09-09T20:30:00-06:00"; :>> judgedBy = "claudeOpus5"; }
    verification frontierReadCheaplyImplementGate : Test { :>> id = "47fa9346-f288-49a6-9cee-3b9fcce2f1bd"; :>> title = "Sprint 644 implement gate"; :>> createdAt = "2026-09-10"; :>> createdBy = "claudeOpus5"; :>> method = VerificationMethod::test; :>> procedureText = "frontier644.py (Frontier struct, orient::ready, compute_orient over it, priority_signals and whats-next call sites), phases644.py (perf phases on the frontier), frontier644b.py (skip valid_commits and bind when !evidence && !clone_can_judge; remember_changed one-head retention), gftest644.py (the gitfacts retention test), one doc-paragraph split for clippy."; }
    // RAN: sprint 644 ceremony step Implement, recorded against the fill text
    part frontierReadCheaplyImplementGateR1 : TestResult { :>> id = "073f531b-930a-496e-938c-850ecfd8aa84"; :>> outcome = VerdictKind::pass; :>> judgedAgainst = "a6bc47b"; :>> judgedAt = "2026-09-09T20:30:00-06:00"; :>> judgedBy = "claudeOpus5"; }
    verification frontierReadCheaplyReviewGate : Test { :>> id = "cf7d3a1c-c558-4178-8f14-cccb6632d21d"; :>> title = "Sprint 644 review gate — three passes per D0172"; :>> createdAt = "2026-09-10"; :>> createdBy = "claudeOpus5"; :>> method = VerificationMethod::inspect; :>> procedureText = "Three passes per D0172: (1) ready is identical by construction - with clone_can_judge false every anchor already read as valid through unwrap_or(true), so skipping the check changes no done bit, and the three lenses were compared byte for byte; (2) the changed-section retention drops only rows keyed by a head that is not HEAD, which D0129 says is never asked again; a checkout of an older commit misses and recomputes; (3) the wall-clock gain is 633 ms, not 5.7 s, because verification-trace at 4.3 s sat just behind the guard that was cut - recorded as issue441 with its resolver ranked next."; }
    // RAN: sprint 644 ceremony step Review, recorded against the fill text
    part frontierReadCheaplyReviewGateR1 : TestResult { :>> id = "ef95a825-b78c-4dfc-bf22-3bec54f41899"; :>> outcome = VerdictKind::pass; :>> judgedAgainst = "a6bc47b"; :>> judgedAt = "2026-09-09T20:30:00-06:00"; :>> judgedBy = "claudeOpus5"; }
    verification frontierReadCheaplyCloseOutGate : Test { :>> id = "2d0db2e0-602c-4f61-988d-b45b92349cfa"; :>> title = "Sprint 644 closeOut gate (autonomous, D0049)"; :>> createdAt = "2026-09-10"; :>> createdBy = "claudeOpus5"; :>> method = VerificationMethod::inspect; :>> procedureText = "validate clean, check-engine clean, guard ALL PASS exit 0; both resolvers stamped at the pre-commit tree a6bc47b; issue439/440 triaged through them; issue441 recorded with resolver dcVerificationTraceIsAttributedAndCut, ranked third from the frontier head; keel-serve.exe refreshed from the new build."; }
    // RAN: sprint 644 ceremony step CloseOut, recorded against the fill text
    part frontierReadCheaplyCloseOutGateR1 : TestResult { :>> id = "b5d7b1ca-e867-4e12-aa3e-b7d996415ebe"; :>> outcome = VerdictKind::pass; :>> judgedAgainst = "a6bc47b"; :>> judgedAt = "2026-09-09T20:30:00-06:00"; :>> judgedBy = "claudeOpus5"; }
    verification frontierReadCheaplyRetroGate : Test { :>> id = "4b981c87-8990-4f5e-88fc-1a605cacdb8c"; :>> title = "Sprint 644 retro gate (autonomous, D0049)"; :>> createdAt = "2026-09-10"; :>> createdBy = "claudeOpus5"; :>> method = VerificationMethod::analyze; :>> procedureText = "Avoidable-issue scan: the cache growth (issue440) had been visible in the file's size for fourteen commits and in every hook fire's gitfacts:load phase; nothing reads the cache's size, so nothing owned it. The same shape as issue439: an indicator that exists, is measured, and has no threshold. Item: the git-facts file size and the guard critical path are candidates for indicator-triggers.toml thresholds (D0333) - folded into dcVerificationTraceIsAttributedAndCut's work rather than a fourth item, since attribution comes before a threshold."; }
    // RAN: sprint 644 ceremony step Retro, recorded against the fill text
    part frontierReadCheaplyRetroGateR1 : TestResult { :>> id = "8caf5bfb-ae6e-4ccc-9652-ecdb55e9ea58"; :>> outcome = VerdictKind::pass; :>> judgedAgainst = "a6bc47b"; :>> judgedAt = "2026-09-09T20:30:00-06:00"; :>> judgedBy = "claudeOpus5"; }
}
