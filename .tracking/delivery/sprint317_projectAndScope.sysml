// ProjectDeliveryS317 — Sprint 317: several projects in one surface, and the model in view is never
// in doubt. All six console requirements are now built. EXECUTE. 8 pts.
package ProjectDeliveryS317 {
    private import EngineElement::*;
    private import EngineWork::*;
    private import EngineVerification::*;
    private import EngineRelationships::*;

    #CharteredBy dependency from projectScopeStory to d0152;

    part projectScopeStory : Story {
        :>> id = "0d800380-0814-6380-9b3e-000000300380";
        :>> title = "Sprint 317: project rebind + resolved model scope (8 pts)";
        :>> createdAt = "2026-08-17"; :>> createdBy = "claudeOpus5"; :>> kind = WorkKind::code; :>> priority = WorkPriority::p0; :>> owner = "claudeOpus5"; :>> estimatedPoints = 8;
    }

    action def DeliveryRunS317 {
        action storyProjectScope;
        verification storyProjectScopeDoD : Test { :>> id = "0d800381-0814-6381-9b3e-000000300381"; :>> method = VerificationMethod::demo; :>> procedureText = "Builds srConsoleProjectRebind (N-C4) and srConsoleModelScopeResolved (N-C3), the last two of the six console requirements. DELIVERED (1): the active root became switchable — `Arc<Mutex<PathBuf>>` behind a `rootpath()` accessor, so all 46 call sites moved mechanically — plus `/api/projects` (discovered, never configured: the active root and any sibling that is itself a keel project) and `POST /api/project` to rebind. A rebind CLEARS the view cache, because every view is computed against the root and a stale cache would show the new project the old project's numbers. DELIVERED (2): `/api/scope`, answering the repo-level question first — this repository builds the engine itself, so its tracked work and its deliverable's are the same programme, and the surface SAYS so rather than leaving it to be inferred — then each item's scope from its authoring file, with anything outside `.engine/` or `.tracking/` reported UNSCOPED and never defaulted. VERIFIED LIVE, all four paths: five projects discovered with the active one named; a real switch to obsidian-livesync succeeded; THE REFUSAL PATH refused a non-existent root with the reason and left the active project unchanged; a subsequent valid switch still worked. clippy clean; 225 tests; validate 344 clean; check-engine clean; 33 guards green."; }
        part storyProjectScopeDoDR1 : TestResult { :>> id = "0d800382-0814-6382-9b3e-000000300382"; :>> outcome = VerdictKind::pass; :>> judgedAgainst = "8d8694f"; :>> judgedAt = "2026-08-17"; :>> judgedBy = "claudeOpus5"; }
    }

    verification psRefineGate : Test { :>> id = "0d800383-0814-6383-9b3e-000000300383"; :>> title = "Sprint 317 refine gate (DoR)"; :>> createdAt = "2026-08-17"; :>> createdBy = "claudeOpus5"; :>> method = VerificationMethod::inspect; :>> procedureText = "DoR. Taken in this order because the declared `#DependsOn` says so: srConsoleModelScopeResolved depends on srConsoleProjectRebind, since scope is a question ABOUT the project in view and answering it for a fixed single root would have to be rewritten the moment the root could move. estimatedPoints=8."; }
    part psRefineGateR1 : TestResult { :>> id = "0d800384-0814-6384-9b3e-000000300384"; :>> outcome = VerdictKind::pass; :>> judgedAgainst = "8d8694f"; :>> judgedAt = "2026-08-17"; :>> judgedBy = "claudeOpus5"; }

    verification psStandupGate : Test { :>> id = "0d800385-0814-6385-9b3e-000000300385"; :>> title = "Sprint 317 standup gate"; :>> createdAt = "2026-08-17"; :>> createdBy = "claudeOpus5"; :>> method = VerificationMethod::inspect; :>> procedureText = "Approach: one accessor behind the lock so the 46 root call sites move mechanically rather than by hand; discover projects from the filesystem rather than adding a config file that becomes a second place to keep the list true; verify every path against a running server including the refusal. No blockers."; }
    part psStandupGateR1 : TestResult { :>> id = "0d800386-0814-6386-9b3e-000000300386"; :>> outcome = VerdictKind::pass; :>> judgedAgainst = "8d8694f"; :>> judgedAt = "2026-08-17"; :>> judgedBy = "claudeOpus5"; }

    verification psImplementGate : Test { :>> id = "0d800387-0814-6387-9b3e-000000300387"; :>> title = "Sprint 317 implement gate"; :>> createdAt = "2026-08-17"; :>> createdBy = "claudeOpus5"; :>> method = VerificationMethod::test; :>> procedureText = "THE REFUSAL PATH WAS BROKEN AND THE TEST FOUND IT — the one path N-C2 leans on hardest. `with_status` splices its stamp into a JSON object, and on an EMPTY `{}` body the separating comma became trailing: `{\"viewStatus\":\"failed\",\"reason\":\"...\",}`, invalid JSON. So every refusal was unparseable, and a console asking why would have got a parse error instead of the reason — a failure whose explanation never reaches the reader, which is worse than the failure it reports. Fixed and covered by a regression test asserting the exact output. TWO MORE THINGS THE RUNNING SERVER EXPOSED that reading the diff never would: `/api/projects` initially reported the active project as `.` with an EMPTY name, because the root was served exactly as given on the command line — N-C4 requires the active project always be named, and `.` is a path rather than an identity, so the root is now canonicalised at startup; and the first refusal test ran against a STALE BINARY because the build had failed with 'Access is denied' while a serve process held keel.exe. That is the identical trap recorded as sprint 315's lesson, one sprint later, and the reason it recurred is precise: the remedy I recorded was 'confirm the rebuild', but the command still had the kill AFTER the build. The order is the control — kill, then build, then serve."; }
    part psImplementGateR1 : TestResult { :>> id = "0d800388-0814-6388-9b3e-000000300388"; :>> outcome = VerdictKind::pass; :>> judgedAgainst = "8d8694f"; :>> judgedAt = "2026-08-17"; :>> judgedBy = "claudeOpus5"; }

    verification psReviewGate : Test { :>> id = "0d800389-0814-6389-9b3e-000000300389"; :>> title = "Sprint 317 review gate"; :>> createdAt = "2026-08-17"; :>> createdBy = "claudeOpus5"; :>> method = VerificationMethod::inspect; :>> procedureText = "Reviewed, and THE VERIFICATION LIMIT ON srConsoleModelScopeResolved IS NOW GONE. That requirement was authored with an explicit caveat that it could not be fully verified here, because this repository is the one place the engine and its deliverable coincide — only COINCIDENT and UNSCOPED were demonstrable, and the ENGINE/DELIVERABLE distinction needed a downstream project, the same limit issue117 recorded for the arch views. Rebinding to obsidian-livesync closed it in the same sprint: that project reports activeScope=distinct with modelsCoincide=false and its own 353 engine / 1752 deliverable items, while this repository reports coincident with 689 / 8005. The two halves of the requirement are each demonstrated on the repository where they are true, which is only possible because rebind came first. The no-silent-fallback clause is the other load-bearing one and it holds: a refused switch leaves the previous project active and says why, rather than leaving the reader believing they are looking at a project they are not."; }
    part psReviewGateR1 : TestResult { :>> id = "0d80038a-0814-638a-9b3e-00000030038a"; :>> outcome = VerdictKind::pass; :>> judgedAgainst = "8d8694f"; :>> judgedAt = "2026-08-17"; :>> judgedBy = "claudeOpus5"; }

    verification psCloseOutGate : Test { :>> id = "0d80038b-0814-638b-9b3e-00000030038b"; :>> title = "Sprint 317 closeOut gate (autonomous, D0049)"; :>> createdAt = "2026-08-17"; :>> createdBy = "claudeOpus5"; :>> method = VerificationMethod::inspect; :>> procedureText = "Autonomous closeOut (D0049). ALL SIX console SystemRequirements are now built and verified against a running server: navigation derived, arrival bounded, obligations on arrival, explicit view status, project rebind, model scope resolved. The console's own UI for switching project and scope is NOT built — the endpoints are, and the nav does not yet expose them, which is stated rather than implied. clippy clean; 225 tests; validate 344 clean; check-engine clean; 33 guards green. Serve processes stopped."; }
    part psCloseOutGateR1 : TestResult { :>> id = "0d80038c-0814-638c-9b3e-00000030038c"; :>> outcome = VerdictKind::pass; :>> judgedAgainst = "8d8694f"; :>> judgedAt = "2026-08-17"; :>> judgedBy = "claudeOpus5"; }

    verification psRetroGate : Test { :>> id = "0d80038d-0814-638d-9b3e-00000030038d"; :>> title = "Sprint 317 retro gate (autonomous, D0049)"; :>> createdAt = "2026-08-17"; :>> createdBy = "claudeOpus5"; :>> method = VerificationMethod::analyze; :>> procedureText = "Autonomous retro (D0049) under D0131's retroTrack. WELL: (1) building rebind BEFORE scope, because the declared #DependsOn said so, is what let scope be verified properly — the distinction the requirement admitted it could not demonstrate here was demonstrated on a real downstream project in the same sprint, and building them in the other order would have left that caveat standing; (2) every path was exercised against a running server, and all three defects this sprint found were invisible in the diff — a trailing comma on the refusal path, an unnamed active project, and a stale binary; (3) the refusal test is the one that mattered, because a broken failure path is exactly the defect that hides every other failure behind it. AVOIDABLE-ISSUE, AND IT IS A REPEAT: I tested against a stale binary because the build failed while a server held keel.exe — the identical trap recorded as sprint 315's lesson one sprint earlier. The recorded remedy was 'confirm the rebuild', which is a check rather than a fix, and I performed the check only after the result looked wrong. The actual control is ORDERING: kill, then build, then serve — a lock cannot be held by a process that is already dead. That is worth more than another reminder to verify. NO NEW ITEM: it is a shell-discipline lesson and the concrete ordering is now written here, where the next reader of this sprint will find it. Estimate 8 pts, delivered."; }
    part psRetroGateR1 : TestResult { :>> id = "0d80038e-0814-638e-9b3e-00000030038e"; :>> outcome = VerdictKind::pass; :>> judgedAgainst = "8d8694f"; :>> judgedAt = "2026-08-17"; :>> judgedBy = "claudeOpus5"; }
}
