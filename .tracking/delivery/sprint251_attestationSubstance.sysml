// ProjectDeliveryS251 — Sprint 251: the attestation-substance guard (issue083, D0130 accepted).
// A passing method=confirmation must actually attest something. Found in the human's own acceptance
// record. Taken from the top of the ranked frontier per D0052. EXECUTE. 2 pts.
package ProjectDeliveryS251 {
    private import EngineElement::*;
    private import EngineWork::*;
    private import EngineVerification::*;
    private import EngineRelationships::*;

    #CharteredBy dependency from attestationSubstanceStory to d0130;

    part attestationSubstanceStory : Story {
        :>> id = "0d690001-0813-4901-9b3e-000000190001";
        :>> title = "Sprint 251: attestation-substance guard — a passing confirmation must attest something (2 pts)";
        :>> createdAt = "2026-08-13"; :>> createdBy = "claudeOpus5"; :>> kind = WorkKind::code; :>> priority = WorkPriority::p0; :>> owner = "claudeOpus5"; :>> estimatedPoints = 2;
    }

    action def DeliveryRunS251 {
        action storyAttestationSubstance;
        verification storyAttestationSubstanceDoD : Test { :>> id = "0d690002-0813-4902-9b3e-000000190002"; :>> method = VerificationMethod::test; :>> procedureText = "Delivers dcAttestationSubstance (issue083/D0130). DEFECT CLOSED: d0129Accept was authored with an EMPTY procedureText and passed EVERY enforced guard, because acceptance-events (D0066) and confirmation-authenticity (D0106) verify that an acceptance EXISTS and is HUMAN-judged, never that it SAYS anything — and for method=confirmation the attestation text IS the evidence (D0016). decision-rationale (D0103) already applied this substantive-field test to a Decision's WHY; it had never been applied to the event that makes the Decision binding. BUILT: guard `attestation-substance`, HARD-blocking (20 guards; 17 hard + 3 warning-only) to match decision-rationale, since a contentless attestation is ill-formed STATE rather than incomplete work (D0098). THREE INDEPENDENT REASONS because length alone is the wrong test: empty; a bare actor NAME (id or display name — it restates judgedBy instead of evidencing the attestation), which matters because d0128Accept is 'william weatherholtz' at EXACTLY 20 chars and would have passed a <20 length test; a stock affirmation (7x 'accepted'); or under 25 chars. The 25 threshold is DERIVED FROM THE CORPUS, not taste — of 234 confirmations the non-substantive ones cluster at 0-20 and the next genuine attestation is 33 chars, so it sits in the gap rather than splitting either population. FORWARD-ONLY (issue068): the 9 pre-existing thin attestations warn; anything NEW hard-fails. VERIFY (measured, not asserted): injected a new 'ok' attestation -> 1 violation and guard exit 1; probe removed -> 9 warnings, 0 violations; an UNANSWERED confirmation is ignored (a pending human sign-off is an obligation, not a defect) and thin text on a method=test verification is ignored (a test carries its own evidence); a dead grandfather entry (firstTaskDoD, in the .engine template, can never carry a passing result) was dropped so the list holds only real items. clippy clean; 152 tests incl. two new pure-function tests; validate + all 20 guards + check-engine green at 336cec5."; }
        part storyAttestationSubstanceDoDR1 : TestResult { :>> id = "0d690003-0813-4903-9b3e-000000190003"; :>> outcome = VerdictKind::pass; :>> judgedAgainst = "336cec5"; :>> judgedAt = "2026-08-13"; :>> judgedBy = "claudeOpus5"; }
    }

    verification asRefineGate : Test { :>> id = "0d690004-0813-4904-9b3e-000000190004"; :>> title = "Sprint 251 refine gate (DoR)"; :>> createdAt = "2026-08-13"; :>> createdBy = "claudeOpus5"; :>> method = VerificationMethod::inspect; :>> procedureText = "DoR: dcAttestationSubstance sat at the top of the ranked frontier and was taken by ORDER (D0052). Chartered by d0130, ACCEPTED earlier the same day. Scope: the guard + forward-only grandfathering. EXCLUDED: rewriting the 9 grandfathered attestations — those are the humans' and prior threads' records to restate (D0108 owner-of-record), and the guard's message asks for it when each is next touched. estimatedPoints=2. DoR met."; }
    part asRefineGateR1 : TestResult { :>> id = "0d690005-0813-4905-9b3e-000000190005"; :>> outcome = VerdictKind::pass; :>> judgedAgainst = "336cec5"; :>> judgedAt = "2026-08-13"; :>> judgedBy = "claudeOpus5"; }

    verification asStandupGate : Test { :>> id = "0d690006-0813-4906-9b3e-000000190006"; :>> title = "Sprint 251 standup gate"; :>> createdAt = "2026-08-13"; :>> createdBy = "claudeOpus5"; :>> method = VerificationMethod::inspect; :>> procedureText = "Approach: MEASURE THE CORPUS before choosing a predicate, having been wrong by an order of magnitude the previous sprint by reasoning from a single instance. The measurement immediately paid off twice — it revealed the bare-name case ('william weatherholtz' at exactly 20 chars, which a naive <20 rule would pass) and it produced a defensible threshold from the natural 20-to-33 gap instead of a guessed number. Mirror decision-rationale (D0103) for the hard-vs-warning decision. No blockers."; }
    part asStandupGateR1 : TestResult { :>> id = "0d690007-0813-4907-9b3e-000000190007"; :>> outcome = VerdictKind::pass; :>> judgedAgainst = "336cec5"; :>> judgedAt = "2026-08-13"; :>> judgedBy = "claudeOpus5"; }

    verification asImplementGate : Test { :>> id = "0d690008-0813-4908-9b3e-000000190008"; :>> title = "Sprint 251 implement gate"; :>> createdAt = "2026-08-13"; :>> createdBy = "claudeOpus5"; :>> method = VerificationMethod::test; :>> procedureText = "Implemented at 336cec5. The hard-fail path was PROVEN by probe rather than reasoned about: a new 'ok' attestation produced a violation and exit 1, then the probe file was removed and the clean state re-verified. This matters more than usual here — a guard that only ever warns is indistinguishable from one that is broken, and this one's whole purpose is to hard-fail NEW records while sparing old ones."; }
    part asImplementGateR1 : TestResult { :>> id = "0d690009-0813-4909-9b3e-000000190009"; :>> outcome = VerdictKind::pass; :>> judgedAgainst = "336cec5"; :>> judgedAt = "2026-08-13"; :>> judgedBy = "claudeOpus5"; }

    verification asReviewGate : Test { :>> id = "0d69000a-0813-490a-9b3e-00000019000a"; :>> title = "Sprint 251 review gate"; :>> createdAt = "2026-08-13"; :>> createdBy = "claudeOpus5"; :>> method = VerificationMethod::inspect; :>> procedureText = "Reviewed. The guard was applied to ITSELF before it existed: d0130's own acceptance event was authored this sitting with a substantive procedureText that records the human's exact words, the fact that they were given immediately after the human requested and read d0130's full text, the caveats the acceptance covers, and explicitly WHY an earlier 'agreed, proceed' was NOT treated as acceptance. That record would pass this guard on merit. Scope discipline: the 9 grandfathered attestations were left for their owners to restate rather than rewritten by this thread (D0108) — rewriting another actor's attestation would be a worse defect than a thin one. Weakness accepted: the stock-affirmation list and the 25-char floor are heuristics; they are hard-blocking only for NEW records, where the cost of a false positive is a one-line rewrite by the author who is already present."; }
    part asReviewGateR1 : TestResult { :>> id = "0d69000b-0813-490b-9b3e-00000019000b"; :>> outcome = VerdictKind::pass; :>> judgedAgainst = "336cec5"; :>> judgedAt = "2026-08-13"; :>> judgedBy = "claudeOpus5"; }

    verification asCloseOutGate : Test { :>> id = "0d69000c-0813-490c-9b3e-00000019000c"; :>> title = "Sprint 251 closeOut gate (autonomous, D0049)"; :>> createdAt = "2026-08-13"; :>> createdBy = "claudeOpus5"; :>> method = VerificationMethod::inspect; :>> procedureText = "Autonomous closeOut (D0049). dcAttestationSubstance carries a passing DoD TestResult at 336cec5; validate + all 20 guards + check-engine green; 152 tests; clippy clean. D0130 is now ACCEPTED (d0130Accept, judgedBy wweatherholtz), so the response contract and the in-loop Stop gate are in force rather than proposed. Frontier advanced by order to dcPriorityInversion. Awaiting the human's per-sitting review."; }
    part asCloseOutGateR1 : TestResult { :>> id = "0d69000d-0813-490d-9b3e-00000019000d"; :>> outcome = VerdictKind::pass; :>> judgedAgainst = "336cec5"; :>> judgedAt = "2026-08-13"; :>> judgedBy = "claudeOpus5"; }

    verification asRetroGate : Test { :>> id = "0d69000e-0813-490e-9b3e-00000019000e"; :>> title = "Sprint 251 retro gate (autonomous, D0049)"; :>> createdAt = "2026-08-13"; :>> createdBy = "claudeOpus5"; :>> method = VerificationMethod::analyze; :>> procedureText = "Autonomous retro (D0049), under the issue085 obligation. WELL: (1) the previous sprint's retro lesson was ACTED ON rather than merely recorded — I measured the corpus before choosing a predicate, and it immediately caught the bare-name case a naive length rule would have passed, and gave a threshold derived from a real 20-to-33 gap instead of a guess; this is the first time this sitting that a recorded lesson changed the NEXT sprint's method; (2) the hard-fail path was proven by probe, since a guard that only ever warns is indistinguishable from a broken one; (3) a dead grandfather entry was found and removed, keeping the exemption list honest — an exemption list that lists non-existent items quietly overstates the debt. AVOIDABLE-ISSUE 1: I made a malformed edit while authoring d0130's acceptance (inserted a placeholder attribute instead of appending the acceptance event), caught immediately and reverted before validating. Cause: editing a structured file by anchor without re-reading the surrounding block. No new item — the existing gate caught nothing because I caught it first, and the practice (re-read before an anchored edit into a structured region) is already implied by the verify-don't-assert clause of the accepted response contract; recorded here as its first observed violation so a recurrence is visible. NO OTHER FINDINGS: this sprint produced no new tracked items, which is the correct outcome for a small, well-scoped control and not a failure to look. Estimate 2 pts, delivered."; }
    part asRetroGateR1 : TestResult { :>> id = "0d69000f-0813-490f-9b3e-00000019000f"; :>> outcome = VerdictKind::pass; :>> judgedAgainst = "336cec5"; :>> judgedAt = "2026-08-13"; :>> judgedBy = "claudeOpus5"; }
}
