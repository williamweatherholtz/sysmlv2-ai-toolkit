// ProjectDeliveryS665 — Sprint 665: Standing consent reads the Decision's text, not only its marker line (D0439, resolving issue460). On 2026-09-10 D0432's consequences said 'Process-change (D0337)' in words while its draft carried no marker: line, and it auto-accepted with a confirmation result judged by the human for a process change they never saw. The write path holds that shape proposed and says why in the record's header; guard 71 consent-scope reads every auto-accepted Decision with the same classifier so a hand-edited file cannot pass what the write path holds.. EXECUTE. 3 pts.
package ProjectDeliveryS665 {
    private import EngineElement::*;
    private import EngineWork::*;
    private import EngineVerification::*;
    private import EngineRelationships::*;

    #CharteredBy dependency from markerTextWithoutMarkerHoldsStory to d0439;

    part markerTextWithoutMarkerHoldsStory : Story {
        :>> id = "43efc160-d631-4dc5-8b53-ea61729c7f6a";
        :>> title = "Sprint 665: Standing consent reads the Decision's text, not only its marker line (D0439, resolving issue460). On 2026-09-10 D0432's consequences said 'Process-change (D0337)' in words while its draft carried no marker: line, and it auto-accepted with a confirmation result judged by the human for a process change they never saw. The write path holds that shape proposed and says why in the record's header; guard 71 consent-scope reads every auto-accepted Decision with the same classifier so a hand-edited file cannot pass what the write path holds. (3 pts)";
        :>> createdAt = "2026-09-11"; :>> createdBy = "claudeOpus5"; :>> kind = WorkKind::code; :>> priority = WorkPriority::p0; :>> owner = "claudeOpus5"; :>> estimatedPoints = 3;
    }

    action def DeliveryRunS665 {
        action storyMarkerTextWithoutMarkerHolds;
        verification storyMarkerTextWithoutMarkerHoldsDoD : Test { :>> id = "66d93565-b5ff-45f1-829a-4b2324c9088f"; :>> method = VerificationMethod::test; :>> procedureText = "A Decision recorded through keel record decision whose context, decision, rationale or consequences name process-change, safety-change, ProspectiveChange or SafetyChange as a whole word while the draft carries no marker line is written PROPOSED with a '// HELD (D0337/issue460): ...' line under its header, the write path prints HELD naming the words, and no acceptance result is written; the same draft with marker: process-change takes the existing D0337 OUTSIDE path; a draft naming neither auto-accepts as before; 'NOT A PROCESS CHANGE: <why>' in a field clears a mention in passing. Guard consent-scope is in GUARD_NAMES with its constraint def, catalogue row and control-map row, passes on the self-build with 151 scanned and one counted-history line (104 pre-D0337 marker Decisions, 1 unmarked prose mention), and fails a synthetic auto-accepted record of either shape dated forward of its cutoff. D0388 pair: deck::marker_text_tests and guards::consent_scope_tests on the classifier (known-positive: the D0432 consequences text; known-negative: a plain text, a marked draft, a declared mention), write::marker_hold_tests on the hold line's lifecycle, and tests/marker_text_without_marker_holds.rs running all four shapes through the binary against a scaffold with one declared decider. DEVIATION from the backlog DoD, stated: the hold is written as a header comment line, not 'in the record's own acceptance test', because write::accept_decision writes {d}Accept : Test at acceptance and a hold-time Test of that name would collide with it; the header line is the one acceptance already rewrites, so the hold leaves with it."; }
        // RAN: keel suite --touched: 712 passed 0 failed 792 s, stems deck guards write + lib, at 1789100468 > launch 1789099676, head 0986b7a; probe pair: lib 9 passed (marker_text_tests consent_scope_tests marker_hold_tests atomic_write_tests), integration marker_text_without_marker_holds 4 passed; clippy -D warnings exit 0; validate 759 clean; check-engine clean; guard PASS with consent-scope 151 scanned 0 violations (HISTORY 104 + 1); sync-claude --check clean
        part storyMarkerTextWithoutMarkerHoldsDoDR1 : TestResult { :>> id = "1ad26591-218a-4a2f-87cd-fbd0ead4af72"; :>> outcome = VerdictKind::pass; :>> judgedAgainst = "0986b7a"; :>> judgedAt = "2026-09-10"; :>> judgedBy = "claudeOpus5"; }
    }

    verification markerTextWithoutMarkerHoldsRefineGate : Test { :>> id = "1a58c67d-fbfa-420b-b1bf-f49b884e46c3"; :>> title = "Sprint 665 refine gate (DoR)"; :>> createdAt = "2026-09-11"; :>> createdBy = "claudeOpus5"; :>> method = VerificationMethod::inspect; :>> procedureText = "Chartered by D0439 (proposed, process-change: a guard is added to the enforcement surface, so the commit carries the marked Decision and the human's word is what accepts it). Sized 3 points: one classifier in deck.rs shared by two readers, a write-path hold in cmd_record with a header line in write.rs, a new guard with three registry rows, and the probe pair as unit, write-path and end-to-end tests. Ready: issue460 names the shape exactly, and the tree's 151 auto-accepted Decisions were measured before the cutoffs were chosen (104 marker-part, 1 unmarked prose mention, all before 2026-09-06 and 2026-09-10 respectively)."; }
    part markerTextWithoutMarkerHoldsRefineGateR1 : TestResult { :>> id = "6d008d75-7476-46be-aec7-228e9369d054"; :>> outcome = VerdictKind::proposed; :>> judgedAgainst = "0986b7a"; :>> judgedAt = "2026-09-10"; :>> judgedBy = "claudeOpus5"; }
    verification markerTextWithoutMarkerHoldsStandupGate : Test { :>> id = "7c4ac00c-8280-4f96-96ff-bb82222deef2"; :>> title = "Sprint 665 standup gate"; :>> createdAt = "2026-09-11"; :>> createdBy = "claudeOpus5"; :>> method = VerificationMethod::inspect; :>> procedureText = "Order: measure the tree first so the cutoffs are chosen against what is there (measure460.py: 151 auto-accepted, 104 marker-part, 10 prose hits of which 9 also carry a marker part); write the classifier and its two unit tests in deck.rs; the hold in cmd_record after the plan-cover check and before the D0337 marker check, with the header line in write.rs and its removal in rewrite_proposed_header; guard consent-scope with a text-level classifier consent_scope_of so the known cases are unit-testable without a tree; register in GUARD_NAMES (70 -> 71), run_one, guard-constraints.sysml, guards.md, control-map.sysml (EHZ3, EHZ7); the integration test against a scaffold; CLAUDE.md sec 4 doc-sync; record D0439 with the marker; then the verifier and recorder."; }
    part markerTextWithoutMarkerHoldsStandupGateR1 : TestResult { :>> id = "1bf875aa-6365-425c-a01f-c41c56a1fc66"; :>> outcome = VerdictKind::proposed; :>> judgedAgainst = "0986b7a"; :>> judgedAt = "2026-09-10"; :>> judgedBy = "claudeOpus5"; }
    verification markerTextWithoutMarkerHoldsImplementGate : Test { :>> id = "8a50549c-9c7f-4884-93b2-1759ac196325"; :>> title = "Sprint 665 implement gate"; :>> createdAt = "2026-09-11"; :>> createdBy = "claudeOpus5"; :>> method = VerificationMethod::test; :>> procedureText = "keel-cli/src/deck.rs: MARKER_WORDS, NOT_A_PROCESS_CHANGE, marker_words (whole-word, case-insensitive, distinct, vocabulary order), marker_text_without_marker, mod marker_text_tests (2). keel-cli/src/main.rs: the hold in cmd_record - marker_text_without_marker over the four fields; under standing consent returns marker_text_without_marker_hold (writes the header line, prints HELD proposed naming the words and the three fixes), without consent prints an advisory and continues. keel-cli/src/write.rs: MARKER_HOLD_PREFIX, note_marker_hold (under the file lock, idempotent, silent on a file with no scaffolded header), rewrite_proposed_header drops the hold line with the stale header, mod marker_hold_tests (1). keel-cli/src/guards.rs: ConsentScope, decision_field, consent_scope_of, consent_scope with MARKER_CUTOFF 2026-09-06 and WORDS_CUTOFF 2026-09-10 and counted history, mod consent_scope_tests (3: positive, negative, the self-build), GUARD_NAMES 71, run_one. keel-cli/tests/marker_text_without_marker_holds.rs (4 end-to-end runs). Rows: guard-constraints.sysml consentScope, guards.md consent-scope, control-map.sysml gConsentScope -> ehz3, ehz7. CLAUDE.md sec 4. The guard's first live run on the tree: 151 scanned, 0 violations, HISTORY 104 and 1 - which corrected the primary's own count of 105 and ten, made before the guard was run; the doc rows carry the guard's numbers."; }
    // RAN: keel suite --touched: 712 passed 0 failed 792 s, stems deck guards write + lib, at 1789100468 > launch 1789099676, head 0986b7a; probe pair: lib 9 passed (marker_text_tests consent_scope_tests marker_hold_tests atomic_write_tests), integration marker_text_without_marker_holds 4 passed; clippy -D warnings exit 0; validate 759 clean; check-engine clean; guard PASS with consent-scope 151 scanned 0 violations (HISTORY 104 + 1); sync-claude --check clean
    part markerTextWithoutMarkerHoldsImplementGateR1 : TestResult { :>> id = "a6872309-a2e3-42b0-a70a-45c9d2aceb2e"; :>> outcome = VerdictKind::pass; :>> judgedAgainst = "0986b7a"; :>> judgedAt = "2026-09-10"; :>> judgedBy = "claudeOpus5"; }
    verification markerTextWithoutMarkerHoldsReviewGate : Test { :>> id = "7dc194a4-495f-493a-ac05-039220470905"; :>> title = "Sprint 665 review gate — three passes per D0172"; :>> createdAt = "2026-09-11"; :>> createdBy = "claudeOpus5"; :>> method = VerificationMethod::inspect; :>> procedureText = "Delivered: the consent's boundary is read from the text the human would read, the hold is stated in the record itself and dies with acceptance, and the gate reads the file with the write path's own words. Verified by the verifier's receipt only (D0425): validate, check-engine, guard --no-receipt with consent-scope PASS 151 scanned, sync-claude --check, clippy, the touched run (lib tests included, keel-cli/src moved) read from its receipt after exit. Held back: nothing. Not in scope: the older issue346 shape (D0425's own record) is history under the same cutoff and is counted, not re-litigated."; }
    part markerTextWithoutMarkerHoldsReviewGateR1 : TestResult { :>> id = "6acce3dd-a705-4fc6-9250-b24e7737b470"; :>> outcome = VerdictKind::proposed; :>> judgedAgainst = "0986b7a"; :>> judgedAt = "2026-09-10"; :>> judgedBy = "claudeOpus5"; }
    verification markerTextWithoutMarkerHoldsCloseOutGate : Test { :>> id = "9223a518-a8aa-4e1a-a63b-bbb5ddc5de9e"; :>> title = "Sprint 665 closeOut gate (autonomous, D0049)"; :>> createdAt = "2026-09-11"; :>> createdBy = "claudeOpus5"; :>> method = VerificationMethod::inspect; :>> procedureText = "Sprint 665 closes on the verifier's receipt only (D0425): validate, check-engine, guard --no-receipt (consent-scope PASS, 151 scanned, one HISTORY line reading 104 and 1), sync-claude --check clean, clippy clean, the D0388 pair - cargo test on marker_text_tests, consent_scope_tests, marker_hold_tests and the marker_text_without_marker_holds binary (4 passed) - and the touched receipt with outcome pass, at after the launch epoch and stems naming deck, guards, main, write. The recorder writes the six gates and the DoD from that receipt; the backlog item dcMarkerTextWithoutMarkerHolds gets its own DoD result and issue460 resolves through the #Resolves edge already authored."; }
    part markerTextWithoutMarkerHoldsCloseOutGateR1 : TestResult { :>> id = "c3aef856-aede-498c-835d-e70c01887e8e"; :>> outcome = VerdictKind::proposed; :>> judgedAgainst = "0986b7a"; :>> judgedAt = "2026-09-10"; :>> judgedBy = "claudeOpus5"; }
    verification markerTextWithoutMarkerHoldsRetroGate : Test { :>> id = "39bfb9be-fa5f-4b42-93ef-807c288d4160"; :>> title = "Sprint 665 retro gate (autonomous, D0049)"; :>> createdAt = "2026-09-11"; :>> createdBy = "claudeOpus5"; :>> method = VerificationMethod::analyze; :>> procedureText = "AVOIDABLE-ISSUE SCAN: no new Issue this sprint. FINDING 1: the primary stated the history counts (105 marker Decisions, ten prose mentions) in the guard's doc comment and catalogue row BEFORE running the guard; the guard's first run read 104 and 1 - the measurement list had 104 entries and nine of the ten prose hits also carry a marker part, which the guard classifies first. Caught by D0388 applied late: the number a doc states is the number the check printed, never the primary's reading of a script's output. Corrected in the same sprint; no control added because the guard IS the control - the doc numbers are re-read against it here and the self-build test asserts the single history line. FINDING 2: the integration test's first run failed on decision-rationale (a fixture context of one letter), not on the guard under test; the fixture now carries real text and the test asserts the consent-scope row alone, since the other guards' verdicts on a bare scaffold are not this sprint's claim. FINDING 3: the backlog DoD's 'in the record's own acceptance test' was not implemented as written - the header line was chosen because accept_decision owns the {d}Accept Test name - and the deviation is stated in the DoD text above rather than silently absorbed. FINDING 4: the first verifier receipt was RED - clippy 5 errors (doc-comment shape in deck.rs and write.rs) and the lib's own write::atomic_write_tests::no_public_write_reads_outside_the_lock, which read note_marker_hold's read_to_string inside a closure as a public write reading outside the lock; the fix is the module's own idiom (pub fn takes the lock, a private _locked fn reads and writes), which is also what the line-based lint can see. The primary's pre-verifier run had covered neither clippy nor the lib's lint tests - the D0425 split did its job. A sixth lint (too_many_lines on cmd_record, at exactly 100 before the sprint) was masked behind the five and surfaced only once they were fixed; folded with the D0337 marker check into one consent_scope_gate helper, no suppression. FINDING 5: the primary ran cargo fmt on the crate, which this repo does not format with rustfmt (no rustfmt.toml), rewriting 137 files (+28937/-6442); nothing landed - git status showed it before any commit. Recovery: git checkout on the 133 untouched files, then the four sprint files restored from HEAD and the sprint's textpatch scripts replayed, with rustfmt(replayed) == the formatted copy byte-for-byte as the check that every edit was recovered (cmp equal on all five files). Tracked as issue473 with a resolver in the backlog."; }
    part markerTextWithoutMarkerHoldsRetroGateR1 : TestResult { :>> id = "1107ded6-79ad-4d63-8e95-59ec49e4b67e"; :>> outcome = VerdictKind::proposed; :>> judgedAgainst = "0986b7a"; :>> judgedAt = "2026-09-10"; :>> judgedBy = "claudeOpus5"; }
}
