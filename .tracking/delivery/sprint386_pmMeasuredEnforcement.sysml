// ProjectDeliveryS386 — Sprint 386: PM - the enforcement is measured: the ledger schema frozen, the analysis computed. EXECUTE. 3 pts.
package ProjectDeliveryS386 {
    private import EngineElement::*;
    private import EngineWork::*;
    private import EngineVerification::*;
    private import EngineRelationships::*;

    #CharteredBy dependency from pmMeasuredEnforcementStory to d0180;

    part pmMeasuredEnforcementStory : Story {
        :>> id = "a223fb47-0a53-497f-9661-0bc83c8cc569";
        :>> title = "Sprint 386: PM - keel enforcement-report, the D0180 evidence surface (3 pts)";
        :>> createdAt = "2026-08-21"; :>> createdBy = "claudeFable5"; :>> kind = WorkKind::code; :>> priority = WorkPriority::p0; :>> owner = "claudeFable5"; :>> estimatedPoints = 3;
    }

    action def DeliveryRunS386 {
        action storyPmMeasuredEnforcement;
        verification storyPmMeasuredEnforcementDoD : Test { :>> id = "5b1857aa-80b2-4a1c-9c7e-8528b840593f"; :>> method = VerificationMethod::test; :>> procedureText = "DELIVERED BACKLOG ITEMS: pmMeasure. `keel enforcement-report` (keel-cli/src/pm.rs, also served at /api/computed/enforcement-report) computes fires and blocks per hook event, sessions seen, red-yields, override ledger events, unsynced vs tracked override obligations, and the adherence trend from #ProcessDefect-marked issues - all from the machine-local fire-ledger whose SCHEMA IS FROZEN in pm.rs (ts, session, event, decision, exit, ms) and BOUND BY TEST: the fixture is the frozen field set, and a malformed line is COUNTED as malformed, never silently skipped (K2 applied to evidence). Rows whose data source is P5 (launcher fraction, dirty-tree-refusal rate - the PESS-2 watch item) say unavailable-and-why rather than reading as zero (the issue183 rule). Everything machine-local per the resolved fork B: no tracked summaries until a consumer is named (D0144). FIRST REAL RUN over this session's own ledger: 126 lines, 2 sessions, six event kinds - the D0180 evidence window opened itself the moment P0's plumbing landed. 221 tests; clippy 0."; }
        part storyPmMeasuredEnforcementDoDR1 : TestResult { :>> id = "bf52bd8a-bdff-4dc5-89d3-ffaa4a3fe2b2"; :>> outcome = VerdictKind::pass; :>> judgedAgainst = "7f7df2c"; :>> judgedAt = "2026-08-21"; :>> judgedBy = "claudeFable5"; }
    }

    verification pmMeasuredEnforcementRefineGate : Test { :>> id = "41ccb315-9fa5-4aad-abe3-a49fd2fa806c"; :>> title = "Sprint 386 refine gate (DoR)"; :>> createdAt = "2026-08-21"; :>> createdBy = "claudeFable5"; :>> method = VerificationMethod::inspect; :>> procedureText = "DoR. PM is small and parallel with P1 by design (the proposal); the emit plumbing shipped in P0, so this sprint is schema freeze + capture breadth + analysis only. estimatedPoints=3."; }
    part pmMeasuredEnforcementRefineGateR1 : TestResult { :>> id = "072f0796-7a7b-482c-821d-c3cf61e3f65c"; :>> outcome = VerdictKind::pass; :>> judgedAgainst = "7f7df2c"; :>> judgedAt = "2026-08-21"; :>> judgedBy = "claudeFable5"; }
    verification pmMeasuredEnforcementStandupGate : Test { :>> id = "fd097bf1-3a50-4fb7-905b-e093d797e42c"; :>> title = "Sprint 386 standup gate"; :>> createdAt = "2026-08-21"; :>> createdBy = "claudeFable5"; :>> method = VerificationMethod::inspect; :>> procedureText = "Approach: ONE reader over ONE emitter, both bound to the frozen field set by the same test - the no-second-drift-surface rule from sync-claude applied to evidence. The report is a computed view served through the existing cache, so the console renders it with no new machinery. No blockers."; }
    part pmMeasuredEnforcementStandupGateR1 : TestResult { :>> id = "17cc6646-f2db-414e-8131-802ccf1bd916"; :>> outcome = VerdictKind::pass; :>> judgedAgainst = "7f7df2c"; :>> judgedAt = "2026-08-21"; :>> judgedBy = "claudeFable5"; }
    verification pmMeasuredEnforcementImplementGate : Test { :>> id = "ad6a14bc-796f-45c4-aba7-8a8e732c0f2e"; :>> title = "Sprint 386 implement gate"; :>> createdAt = "2026-08-21"; :>> createdBy = "claudeFable5"; :>> method = VerificationMethod::test; :>> procedureText = "Run, not read: the report executed over the REAL ledger (126 lines accrued by this session's own hooks since P0 landed - the instrument measured its own construction); the schema test asserts field-set equality both ways and the malformed-line visibility; clippy caught the doc-paragraph and map_or lints."; }
    part pmMeasuredEnforcementImplementGateR1 : TestResult { :>> id = "45d41300-63e9-467f-9049-e40a2018ae09"; :>> outcome = VerdictKind::pass; :>> judgedAgainst = "7f7df2c"; :>> judgedAt = "2026-08-21"; :>> judgedBy = "claudeFable5"; }
    verification pmMeasuredEnforcementReviewGate : Test { :>> id = "7f3ca7c7-288a-4e73-ba89-0f25180776ca"; :>> title = "Sprint 386 review gate — three passes per D0172"; :>> createdAt = "2026-08-21"; :>> createdBy = "claudeFable5"; :>> method = VerificationMethod::inspect; :>> procedureText = "PASS 1, CLAIMS vs computed: every number quoted above is from the report's own output over the real ledger. PASS 2, BOUNDARY: absent ledger = zero lines reported honestly (not an error); malformed lines counted; P5-dependent rows say unavailable-and-why. PASS 3, OWN DIFF: a stray edit fragment (a dangling entry() call) was left in the first draft and caught at compile - removed. WHAT A REVIEWER SHOULD ATTACK: per-sprint windowing is not yet computed (the report is cumulative); the promotion decision needs at-least-3-sprints framing, which today means comparing reports taken at sprint boundaries - acceptable for N=3 manual review, revisit if promotion cadence grows."; }
    part pmMeasuredEnforcementReviewGateR1 : TestResult { :>> id = "00977124-8f63-4807-b00b-06a071121165"; :>> outcome = VerdictKind::pass; :>> judgedAgainst = "7f7df2c"; :>> judgedAt = "2026-08-21"; :>> judgedBy = "claudeFable5"; }
    verification pmMeasuredEnforcementCloseOutGate : Test { :>> id = "d9b03afc-cf48-44b5-9f32-b98e1d7e0096"; :>> title = "Sprint 386 closeOut gate (autonomous, D0049)"; :>> createdAt = "2026-08-21"; :>> createdBy = "claudeFable5"; :>> method = VerificationMethod::inspect; :>> procedureText = "Autonomous closeOut (D0049). pmMeasure's DoD flipped at the judging HEAD; command in the catalogue under its coverage test; serve binding added. validate clean; 41 guards ALL PASS; 221 tests; clippy 0."; }
    part pmMeasuredEnforcementCloseOutGateR1 : TestResult { :>> id = "39ffd502-6166-4717-9ed7-4b7fd5d85f3f"; :>> outcome = VerdictKind::pass; :>> judgedAgainst = "7f7df2c"; :>> judgedAt = "2026-08-21"; :>> judgedBy = "claudeFable5"; }
    verification pmMeasuredEnforcementRetroGate : Test { :>> id = "4015bbd2-72c1-4b16-8df6-03b3ee7303b9"; :>> title = "Sprint 386 retro gate (autonomous, D0049)"; :>> createdAt = "2026-08-21"; :>> createdBy = "claudeFable5"; :>> method = VerificationMethod::analyze; :>> procedureText = "Autonomous retro (D0049). AVOIDABLE-ISSUE SCAN under rcRecurrence: the dangling-fragment-from-edit class appeared once before (deck v3's stray line, issue191's second syntax error) - THIS one was compiler-caught within seconds because it lives in Rust, not emitted JS; the existing rule (emitted text gets node --check) already covers the only variant that can escape. WELL: the instrument measuring its own construction session (126 lines before the analysis existed) is the right order - evidence first, analysis second, promotion third; and the unavailable-and-why rows carry issue183's lesson forward into a brand-new surface. Estimate 3 pts, delivered."; }
    part pmMeasuredEnforcementRetroGateR1 : TestResult { :>> id = "bca6f754-5e5f-431b-bb3f-d13b31b5611d"; :>> outcome = VerdictKind::pass; :>> judgedAgainst = "7f7df2c"; :>> judgedAt = "2026-08-21"; :>> judgedBy = "claudeFable5"; }
}
