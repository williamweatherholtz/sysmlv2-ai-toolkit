// ProjectDeliveryS257 — Sprint 257: Tier-2 per-edit in-loop gate; keelInLoopGates complete (D0128).
// The measurement D0128 conditioned Tier-1/Tier-2 on. EXECUTE. 3 pts.
package ProjectDeliveryS257 {
    private import EngineElement::*;
    private import EngineWork::*;
    private import EngineVerification::*;
    private import EngineRelationships::*;

    #CharteredBy dependency from inLoopTier2Story to d0128;

    part inLoopTier2Story : Story {
        :>> id = "0d710001-0814-5101-9b3e-000000210001";
        :>> title = "Sprint 257: keel gate --fast + Tier-2 PostToolUse gate; keelInLoopGates complete (3 pts)";
        :>> createdAt = "2026-08-14"; :>> createdBy = "claudeOpus5"; :>> kind = WorkKind::code; :>> priority = WorkPriority::p0; :>> owner = "claudeOpus5"; :>> estimatedPoints = 3;
    }

    action def DeliveryRunS257 {
        action storyInLoopTier2;
        verification storyInLoopTier2DoD : Test { :>> id = "0d710002-0814-5102-9b3e-000000210002"; :>> method = VerificationMethod::demo; :>> procedureText = "Completes keelInLoopGates (D0128/nAiGovernanceInLoop). MEASURED first, because D0128 made Tier-1/Tier-2 conditional on evidence: validate 208ms, duplicate-identity 145ms, marker-vocabulary 138ms, FULL guard suite 1899ms, and `keel gate --fast` 322-372ms warm (faster than the component sum — one process, one shared model cache). So a per-edit gate can afford validate plus the two EXACT guards; the full suite cannot, and therefore stays at the turn boundary (Tier-3) and commit. DELIVERED: `keel gate --fast` + a PostToolUse hook on Write|Edit that runs it after any .sysml edit and feeds violations back at the point of the edit. It deliberately excludes every heuristic/warning-level guard — a per-edit gate firing on a prose heuristic would block work mid-thought and train the agent to disable it, the issue076/issue081 dynamic that cost eight bypassed commits. WARRANT came from this sitting's own retros, not theory: three recorded avoidable issues were the same shape (an edit that was wrong and found much later) — a malformed anchored edit inserting a placeholder attribute (sprint 251), a doc-sync edit that silently did nothing because its anchor did not match (sprint 254), and a marker typo that validated clean and would blind a hard guard (issue077). Each is now caught in ~0.35s. TIER-1 (PreToolUse deny) NOT ADDED, which is the honest reading of 'as warranted': no clear-cut, PRE-action-detectable prose-as-truth pattern emerged — every observed violation was a POST-edit state, which Tier-2 catches exactly, so a content-pattern deny would carry real false-positive risk for no measured gain. VERIFY: four paths pipe-tested (non-.sysml silent; clean silent so a passing gate costs nothing; broken parse blocks with the diagnostic; marker typo blocks naming file/line/marker); cross-platform binary probing, unlike the Tier-3 prototype which shipped Windows-only; missing binary reports VISIBLY rather than no-opping. clippy clean; validate + all 23 guards + check-engine green at bb52d2a."; }
        part storyInLoopTier2DoDR1 : TestResult { :>> id = "0d710003-0814-5103-9b3e-000000210003"; :>> outcome = VerdictKind::pass; :>> judgedAgainst = "bb52d2a"; :>> judgedAt = "2026-08-14"; :>> judgedBy = "claudeOpus5"; }
    }

    verification t2RefineGate : Test { :>> id = "0d710004-0814-5104-9b3e-000000210004"; :>> title = "Sprint 257 refine gate (DoR)"; :>> createdAt = "2026-08-14"; :>> createdBy = "claudeOpus5"; :>> method = VerificationMethod::inspect; :>> procedureText = "DoR: top of the ranked frontier by ORDER (D0052), chartered by the accepted d0128. Scope: measure, then add only the tier the measurement warrants. estimatedPoints=3. DoR met."; }
    part t2RefineGateR1 : TestResult { :>> id = "0d710005-0814-5105-9b3e-000000210005"; :>> outcome = VerdictKind::pass; :>> judgedAgainst = "bb52d2a"; :>> judgedAt = "2026-08-14"; :>> judgedBy = "claudeOpus5"; }

    verification t2StandupGate : Test { :>> id = "0d710006-0814-5106-9b3e-000000210006"; :>> title = "Sprint 257 standup gate"; :>> createdAt = "2026-08-14"; :>> createdBy = "claudeOpus5"; :>> method = VerificationMethod::inspect; :>> procedureText = "Approach: measure the candidate checks before choosing the tier composition, and derive the warrant from THIS sitting's recorded retro findings rather than from a general argument about per-edit gating. Restrict the tier to EXACT checks so blocking is never a judgement call. No blockers."; }
    part t2StandupGateR1 : TestResult { :>> id = "0d710007-0814-5107-9b3e-000000210007"; :>> outcome = VerdictKind::pass; :>> judgedAgainst = "bb52d2a"; :>> judgedAt = "2026-08-14"; :>> judgedBy = "claudeOpus5"; }

    verification t2ImplementGate : Test { :>> id = "0d710008-0814-5108-9b3e-000000210008"; :>> title = "Sprint 257 implement gate"; :>> createdAt = "2026-08-14"; :>> createdBy = "claudeOpus5"; :>> method = VerificationMethod::demo; :>> procedureText = "Implemented at bb52d2a. The first timing run reported 20,768ms and I nearly recorded that as the cost; re-measuring warm gave 322-372ms, the 20s being a cold-start artefact of a freshly built binary. Caught only by re-measuring — the read-back-the-computed-answer rule doing real work on a number that would have killed the design."; }
    part t2ImplementGateR1 : TestResult { :>> id = "0d710009-0814-5109-9b3e-000000210009"; :>> outcome = VerdictKind::pass; :>> judgedAgainst = "bb52d2a"; :>> judgedAt = "2026-08-14"; :>> judgedBy = "claudeOpus5"; }

    verification t2ReviewGate : Test { :>> id = "0d71000a-0814-510a-9b3e-00000021000a"; :>> title = "Sprint 257 review gate"; :>> createdAt = "2026-08-14"; :>> createdBy = "claudeOpus5"; :>> method = VerificationMethod::inspect; :>> procedureText = "Reviewed. The valuable discipline here was DECLINING Tier-1: D0128 wrote 'as warranted', and the measurement warranted Tier-2 and not Tier-1, so the item closes with one tier deliberately unbuilt and the reason recorded. That is the difference between satisfying a DoD and satisfying its spirit. Weakness accepted: the per-edit gate re-validates the WHOLE model rather than the edited file, which is affordable only because validate is fast on this corpus; a much larger project would need incremental scoping."; }
    part t2ReviewGateR1 : TestResult { :>> id = "0d71000b-0814-510b-9b3e-00000021000b"; :>> outcome = VerdictKind::pass; :>> judgedAgainst = "bb52d2a"; :>> judgedAt = "2026-08-14"; :>> judgedBy = "claudeOpus5"; }

    verification t2CloseOutGate : Test { :>> id = "0d71000c-0814-510c-9b3e-00000021000c"; :>> title = "Sprint 257 closeOut gate (autonomous, D0049)"; :>> createdAt = "2026-08-14"; :>> createdBy = "claudeOpus5"; :>> method = VerificationMethod::inspect; :>> procedureText = "Autonomous closeOut (D0049). keelInLoopGates carries a passing DoD TestResult at bb52d2a; all three of D0128's directions now have delivered work (governance via D0130/D0134 + this; release next; portability still unbuilt). validate + all 23 guards + check-engine green."; }
    part t2CloseOutGateR1 : TestResult { :>> id = "0d71000d-0814-510d-9b3e-00000021000d"; :>> outcome = VerdictKind::pass; :>> judgedAgainst = "bb52d2a"; :>> judgedAt = "2026-08-14"; :>> judgedBy = "claudeOpus5"; }

    verification t2RetroGate : Test { :>> id = "0d71000e-0814-510e-9b3e-00000021000e"; :>> title = "Sprint 257 retro gate (autonomous, D0049)"; :>> createdAt = "2026-08-14"; :>> createdBy = "claudeOpus5"; :>> method = VerificationMethod::analyze; :>> procedureText = "Autonomous retro (D0049) under D0131's retroTrack. WELL: (1) measuring first produced a design decision (which checks fit a per-edit budget) rather than a justification for one already made; (2) Tier-1 was declined on evidence and the decline recorded, so the DoD's 'as warranted' was honoured rather than treated as licence to build everything. AVOIDABLE-ISSUE 1: I nearly recorded a 20,768ms cold-start timing as the per-edit cost, which would have made the whole tier look unaffordable and killed a correct design. Caught by re-measuring warm. NO NEW ITEM — this is the third recorded instance of the same read-back-the-computed-answer principle (after the sprint-248 false control total and the sprint-254 silent doc-sync edit) and it is already carried by the accepted response contract; recorded here so the count keeps rising visibly rather than resetting. Estimate 3 pts, delivered."; }
    part t2RetroGateR1 : TestResult { :>> id = "0d71000f-0814-510f-9b3e-00000021000f"; :>> outcome = VerdictKind::pass; :>> judgedAgainst = "bb52d2a"; :>> judgedAt = "2026-08-14"; :>> judgedBy = "claudeOpus5"; }
}
