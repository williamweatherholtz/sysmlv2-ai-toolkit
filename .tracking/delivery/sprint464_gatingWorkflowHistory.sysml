// ProjectDeliveryS464 — Sprint 464: the release gate actually runs, and a workflow that reports a pass it never verified is refused. EXECUTE. 2 pts.
package ProjectDeliveryS464 {
    private import EngineElement::*;
    private import EngineWork::*;
    private import EngineVerification::*;
    private import EngineRelationships::*;

    #CharteredBy dependency from gatingWorkflowHistoryStory to d0229;

    part gatingWorkflowHistoryStory : Story {
        :>> id = "0e482712-d4c2-4bb8-b0cc-cdd33f42bc8d";
        :>> title = "Sprint 464: the gate that had been red for weeks, found by using it (2 pts)";
        :>> createdAt = "2026-08-25"; :>> createdBy = "claudeFable5"; :>> kind = WorkKind::code; :>> priority = WorkPriority::p0; :>> owner = "claudeFable5"; :>> estimatedPoints = 2;
    }

    action def DeliveryRunS464 {
        action storyGatingWorkflowHistory;
        verification storyGatingWorkflowHistoryDoD : Test { :>> id = "9383a2ff-d072-414d-b6af-6bb1ad3ed2d2"; :>> method = VerificationMethod::test; :>> procedureText = "DELIVERED: dcGatingWorkflowHistory (resolves issue260, HIGH, discoveredInField; D0229) and v0.3.0, the release the author asked penumbra to pin to. Cutting the tag is what found the defect. The release workflow FAILED - not on anything in the release, but on the test asserting no guard reports a zero population. The guard was claim-ancestry, which skips loudly on a shallow clone because a depth-dependent verdict is the machine dependence K15 forbids, and actions/checkout defaults to depth 1. ci.yml carries fetch-depth 0 with a comment naming issue229: the exact fix, for the exact reason, already written down in this repo. release.yml never received it, so the release gate had been RED since guard 48 landed weeks ago and nothing could have revealed it, because v0.2.3 was tagged before that guard existed and no release had been cut since. THE AGGRAVATING DETAIL is that the fix had already SUCCEEDED once here and did not transfer - vigilance did not fail, it worked and failed to generalise, which is the strongest case for D0047 this project has produced. Built: the checkout fix, guard 51 refusing any workflow that RUNS the gate while checking out shallow, the scan-count test recording claim-ancestry's shallow-clone emptiness WITH its reason, and the guard's per-file-not-per-job limitation stated rather than left to be discovered. The tag was then deleted and re-cut against a passing commit, because a release is the one artifact whose gate must actually have run."; }
        part storyGatingWorkflowHistoryDoDR1 : TestResult { :>> id = "f709c176-a31f-42c2-b65f-43391d30bc93"; :>> outcome = VerdictKind::pass; :>> judgedAgainst = "c444ca5"; :>> judgedAt = "2026-08-24"; :>> judgedBy = "claudeFable5"; }
        part storyGatingWorkflowHistoryDoDR2 : TestResult { :>> id = "58e451cf-047b-4a73-a591-d0cacefe3bc8"; :>> outcome = VerdictKind::pass; :>> judgedAgainst = "c444ca562706e2645424c27e03c66d39419b1f98"; :>> judgedAt = "2026-08-24"; :>> judgedBy = "claudeFable5"; }
    }

    verification gatingWorkflowHistoryRefineGate : Test { :>> id = "49927fd5-29e9-4451-a3d6-ab001eda1e98"; :>> title = "Sprint 464 refine gate (DoR)"; :>> createdAt = "2026-08-25"; :>> createdBy = "claudeFable5"; :>> method = VerificationMethod::inspect; :>> procedureText = "DoR. Resolves issue260, found while executing the author's chosen option - pin penumbra to a release - which required a release to exist. v0.2.3 predates every change that makes the engine adoptable, so a fresh one was necessary and cutting it is what exposed the red gate. 2 points."; }
    part gatingWorkflowHistoryRefineGateR1 : TestResult { :>> id = "f0c74ed1-0f11-441b-a2cb-f3b13314dad6"; :>> outcome = VerdictKind::pass; :>> judgedAgainst = "c444ca5"; :>> judgedAt = "2026-08-24"; :>> judgedBy = "claudeFable5"; }
    part gatingWorkflowHistoryRefineGateR2 : TestResult { :>> id = "e404f870-cc80-4a88-b955-d0e26913d74e"; :>> outcome = VerdictKind::pass; :>> judgedAgainst = "c444ca562706e2645424c27e03c66d39419b1f98"; :>> judgedAt = "2026-08-24"; :>> judgedBy = "claudeFable5"; }
    verification gatingWorkflowHistoryStandupGate : Test { :>> id = "1252fc78-5279-42cc-8941-e5d100186968"; :>> title = "Sprint 464 standup gate"; :>> createdAt = "2026-08-25"; :>> createdBy = "claudeFable5"; :>> method = VerificationMethod::inspect; :>> procedureText = "Approach: diagnose from the actual failure log rather than guessing which guard was empty; the first assumption was that my own new guard 50 had failed, and reading the message showed it was claim-ancestry. Then compare all four workflows rather than fixing the one that broke - the same-fix-in-N-places class says the question is never whether ONE file is wrong. .github/workflows/ and guards.rs are both keystone-locked, so D0229 co-commits as a SafetyChange. No blockers."; }
    part gatingWorkflowHistoryStandupGateR1 : TestResult { :>> id = "d8187632-126b-45dd-911c-74a42676607e"; :>> outcome = VerdictKind::pass; :>> judgedAgainst = "c444ca5"; :>> judgedAt = "2026-08-24"; :>> judgedBy = "claudeFable5"; }
    part gatingWorkflowHistoryStandupGateR2 : TestResult { :>> id = "3da98f57-189d-4e20-a246-72f16ac6ebba"; :>> outcome = VerdictKind::pass; :>> judgedAgainst = "c444ca562706e2645424c27e03c66d39419b1f98"; :>> judgedAt = "2026-08-24"; :>> judgedBy = "claudeFable5"; }
    verification gatingWorkflowHistoryImplementGate : Test { :>> id = "d924e876-041d-4d50-9908-fbaf0bfa5252"; :>> title = "Sprint 464 implement gate"; :>> createdAt = "2026-08-25"; :>> createdBy = "claudeFable5"; :>> method = VerificationMethod::test; :>> procedureText = "Probed BOTH directions rather than trusting the pass: guard 51 reports 3 scanned and PASS on the real tree, and FAILS with the precise message when release.yml's depth is flipped to 1. Guard count reads 51 from the binary. The re-cut release run completed SUCCESS and published three platform binaries (keel-linux-x86_64, keel-macos-aarch64, keel-windows-x86_64.exe). release-recorded passes 6 scanned with the Release item recording c444ca5, the tag's own commit. validate 516 + all 51 guards + clippy + 268 + 9 + 1 + 32 tests."; }
    part gatingWorkflowHistoryImplementGateR1 : TestResult { :>> id = "02901a9f-4659-425e-bf43-9c79c0250fd2"; :>> outcome = VerdictKind::pass; :>> judgedAgainst = "c444ca5"; :>> judgedAt = "2026-08-24"; :>> judgedBy = "claudeFable5"; }
    part gatingWorkflowHistoryImplementGateR2 : TestResult { :>> id = "d5c15f82-8295-42ff-a600-36ca5f3def7e"; :>> outcome = VerdictKind::pass; :>> judgedAgainst = "c444ca562706e2645424c27e03c66d39419b1f98"; :>> judgedAt = "2026-08-24"; :>> judgedBy = "claudeFable5"; }
    verification gatingWorkflowHistoryReviewGate : Test { :>> id = "f49df1a5-af59-410e-8496-69489c852249"; :>> title = "Sprint 464 review gate — three passes per D0172"; :>> createdAt = "2026-08-25"; :>> createdBy = "claudeFable5"; :>> method = VerificationMethod::inspect; :>> procedureText = "PASS 1, CLAIMS: the failure diagnosis is quoted from the run log, the guard verdicts from both probe directions, the asset list from the published release. PASS 2, BOUNDARY: (i) the check is per-FILE, not per-job, because there is no YAML parser here - a two-job workflow whose non-gating job alone sets the flag would pass, which is the shape release.yml legitimately has, and that hole is recorded in the guard doc and guards.md rather than left to be found; (ii) 'runs the gate' is judged by string-matching what the workflow invokes, so a gate reached through an indirection the guard does not know would be missed; (iii) the guard cannot tell that a workflow's gate is MEANINGFUL, only that history was available to it. PASS 3, OWN DIFF: my first instinct was that my own guard 50 had broken the release, and I nearly patched it before reading the message - the diagnosis came from the log, not the hypothesis. Also worth recording: I wrote the wrong Decision number into two source files before the recorder assigned the real one, and only a grep caught it. WHAT A REVIEWER SHOULD ATTACK: whether re-cutting a tag is acceptable at all, given this project forbids rewriting history - the defence is that a tag is a pointer and no commit was rewritten, but the reviewer is right to check that no evidence anchored to the deleted tag."; }
    part gatingWorkflowHistoryReviewGateR1 : TestResult { :>> id = "e05d5091-bcd2-4dc6-a46e-da088ca8f7ba"; :>> outcome = VerdictKind::pass; :>> judgedAgainst = "c444ca5"; :>> judgedAt = "2026-08-24"; :>> judgedBy = "claudeFable5"; }
    part gatingWorkflowHistoryReviewGateR2 : TestResult { :>> id = "82c74c23-e972-4761-bf93-24b140837f2f"; :>> outcome = VerdictKind::pass; :>> judgedAgainst = "c444ca562706e2645424c27e03c66d39419b1f98"; :>> judgedAt = "2026-08-24"; :>> judgedBy = "claudeFable5"; }
    verification gatingWorkflowHistoryCloseOutGate : Test { :>> id = "05922018-7a58-4a35-b371-3c6e4a9deffa"; :>> title = "Sprint 464 closeOut gate (autonomous, D0049)"; :>> createdAt = "2026-08-25"; :>> createdBy = "claudeFable5"; :>> method = VerificationMethod::inspect; :>> procedureText = "Autonomous closeOut (D0049). issue260 resolved and v0.3.0 published with a gate that actually ran. The author's pin option now has something to pin to. validate + all 51 guards + check-engine + rules green at c444ca5."; }
    part gatingWorkflowHistoryCloseOutGateR1 : TestResult { :>> id = "d27eea35-64aa-4665-8dd5-8af056b78019"; :>> outcome = VerdictKind::pass; :>> judgedAgainst = "c444ca5"; :>> judgedAt = "2026-08-24"; :>> judgedBy = "claudeFable5"; }
    part gatingWorkflowHistoryCloseOutGateR2 : TestResult { :>> id = "8bf313d7-0a5e-4d72-89f2-853d90616e85"; :>> outcome = VerdictKind::pass; :>> judgedAgainst = "c444ca562706e2645424c27e03c66d39419b1f98"; :>> judgedAt = "2026-08-24"; :>> judgedBy = "claudeFable5"; }
    verification gatingWorkflowHistoryRetroGate : Test { :>> id = "632af38d-2161-4e5b-96a1-bcbb0c8b2edf"; :>> title = "Sprint 464 retro gate (autonomous, D0049)"; :>> createdAt = "2026-08-25"; :>> createdBy = "claudeFable5"; :>> method = VerificationMethod::analyze; :>> procedureText = "Autonomous retro (D0049). AVOIDABLE-ISSUE SCAN under rcRecurrence: (1) THE SAME-FIX-IN-N-PLACES CLASS AGAIN, and this is its worst instance: the fix existed, carried its own issue number in a comment, and still did not reach the fourth file. Three sprints ago the retro said a bulk change must enumerate a shared fact's readers; the generalisation is broader - when a fix lands in a file, grep for every SIBLING of that file, not just every reader of the fact. (2) A gate that runs rarely can be red for weeks, so rarity should raise urgency rather than lower it; the release path had no other run that would notice. (3) Found by USING the thing, exactly like the last three defects - the author's request to pin a release is what ran the release gate. That is now four consecutive sprints where the defect was invisible to inspection and obvious on use. WELL: reading the failure log before acting on the hypothesis saved patching a guard that was working correctly. Estimate 2 pts, delivered 2."; }
    part gatingWorkflowHistoryRetroGateR1 : TestResult { :>> id = "6dc08453-d777-41e2-80a2-6c3dde31f9b0"; :>> outcome = VerdictKind::pass; :>> judgedAgainst = "c444ca5"; :>> judgedAt = "2026-08-24"; :>> judgedBy = "claudeFable5"; }
    part gatingWorkflowHistoryRetroGateR2 : TestResult { :>> id = "68e0c3ef-2068-4142-8bde-b85308a39b96"; :>> outcome = VerdictKind::pass; :>> judgedAgainst = "c444ca562706e2645424c27e03c66d39419b1f98"; :>> judgedAt = "2026-08-24"; :>> judgedBy = "claudeFable5"; }
}
