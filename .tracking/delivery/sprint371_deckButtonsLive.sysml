// ProjectDeliveryS371 — Sprint 371: the deck disabled its own sync at load. Fixed, and the learnings
// written into the skill that already forbade it. EXECUTE. 3 pts.
package ProjectDeliveryS371 {
    private import EngineElement::*;
    private import EngineWork::*;
    private import EngineVerification::*;
    private import EngineRelationships::*;

    #CharteredBy dependency from buttonsLiveStory to d0171;

    part buttonsLiveStory : Story {
        :>> id = "0d8006e0-0814-66e0-9b3e-0000003006e0";
        :>> title = "Sprint 371: a load-time DOM write killed the deck's sync — no write outside a gesture (3 pts)";
        :>> createdAt = "2026-08-20"; :>> createdBy = "claudeOpus5"; :>> kind = WorkKind::code; :>> priority = WorkPriority::p0; :>> owner = "claudeOpus5"; :>> estimatedPoints = 3;
    }

    action def DeliveryRunS371 {
        action storyButtonsLive;
        verification storyButtonsLiveDoD : Test { :>> id = "0d8006e1-0814-66e1-9b3e-0000003006e1"; :>> method = VerificationMethod::test; :>> procedureText = "DELIVERED BACKLOG ITEMS: dcDeckButtonsLive. Addresses issue188 under D0171. ROOT CAUSE: on a live doc the runtime switches a sync region OFF when script rather than a gesture changes its DOM. `count()` ran at the end of the script and set the bottom bar's textContent, so the body's region went off at load, and the `claude:sync-off` handler then set data-local-readonly=true - so the page declared itself unwritable before the human touched it, and every tap answered `not saved`. THREE FIXES: the initial count is RENDERED BY THE GENERATOR so nothing writes the DOM at load; read-only is concluded ONLY from a sync() rejection carrying not_writer or not_granted, and sync-off may now only REPORT; and the script's last statement sets a data-local marker that CSS renders as `script ok`, so its ABSENCE says the script threw. TWO MORE DEFECTS FROM THE PREVIOUS SPRINT, both mine: `var(--acc)` is not a declared property so the signature ribbon silently lost its colour, and the marker set an attribute nothing displayed. VERIFIED FROM THE EMITTED HTML, eight properties: zero top-level DOM mutations before the listener registers, count present as text, marker last, Sign occurring exactly as often as data-cls=acceptance, copy hidden by default, 44px tap targets, viewport meta, no undefined custom property. validate 403 clean; check-engine clean; 38 guards ALL PASS."; }
        part storyButtonsLiveDoDR1 : TestResult { :>> id = "0d8006e2-0814-66e2-9b3e-0000003006e2"; :>> outcome = VerdictKind::pass; :>> judgedAgainst = "02ea1af"; :>> judgedAt = "2026-08-20"; :>> judgedBy = "claudeOpus5"; }
    }

    verification blRefineGate : Test { :>> id = "0d8006e3-0814-66e3-9b3e-0000003006e3"; :>> title = "Sprint 371 refine gate (DoR)"; :>> createdAt = "2026-08-20"; :>> createdBy = "claudeOpus5"; :>> method = VerificationMethod::inspect; :>> procedureText = "DoR. THE DIAGNOSIS WAS DONE BY READING THE EMITTED SCRIPT, not by guessing at mobile browsers. My first three hypotheses were all wrong and all plausible - iOS click delegation, a `<dialog>.showModal` failure, unsupported syntax killing the script - and none survived reading the code. What settled it was listing every TOP-LEVEL statement that runs BEFORE the click listener registers: exactly one, `count()`, and it writes the DOM. That question is answerable in ten seconds and I should have asked it before publishing. estimatedPoints=3."; }
    part blRefineGateR1 : TestResult { :>> id = "0d8006e4-0814-66e4-9b3e-0000003006e4"; :>> outcome = VerdictKind::pass; :>> judgedAgainst = "02ea1af"; :>> judgedAt = "2026-08-20"; :>> judgedBy = "claudeOpus5"; }

    verification blStandupGate : Test { :>> id = "0d8006e5-0814-66e5-9b3e-0000003006e5"; :>> title = "Sprint 371 standup gate"; :>> createdAt = "2026-08-20"; :>> createdBy = "claudeOpus5"; :>> method = VerificationMethod::inspect; :>> procedureText = "Approach: fix the cause, then make the page able to REPORT this class of failure itself, because a page whose script died looks identical to a working page with nothing to do. The console already had that instrument - the `js ok` marker built for issue152 - and I did not carry it to the deck, which is why two publishes went out unverified. No blockers."; }
    part blStandupGateR1 : TestResult { :>> id = "0d8006e6-0814-66e6-9b3e-0000003006e6"; :>> outcome = VerdictKind::pass; :>> judgedAgainst = "02ea1af"; :>> judgedAt = "2026-08-20"; :>> judgedBy = "claudeOpus5"; }

    verification blImplementGate : Test { :>> id = "0d8006e7-0814-66e7-9b3e-0000003006e7"; :>> title = "Sprint 371 implement gate"; :>> createdAt = "2026-08-20"; :>> createdBy = "claudeOpus5"; :>> method = VerificationMethod::test; :>> procedureText = "I VIOLATED TWO ANTI-PATTERNS THAT ARE WRITTEN DOWN IN THE SKILL I WAS FOLLOWING. The canvas skill's list names them: number 4, script-built region content at load; number 3, an over-eager claude:sync-off handler. I hit both, in the same file, having read that list earlier in the session. Knowing a rule and applying it are different acts, and the difference is why the rule now lives in the obligation-review skill as a numbered section with the failure that produced each line - a rule with its scar attached is harder to skip than a rule in a list. FIVE HEREDOC AND ESCAPING FAILURES IN THIS ONE SPRINT while trying to edit the generator: a backslash-n became a real newline and split a string across two lines, twice; an implicit string concatenation broke when I appended a format operator to its first fragment; and an assertion on exact bytes failed because the heredoc had already altered them. I switched to writing the fix as a FILE with the Write tool and it worked first time. That remedy has now been recorded four times and this is the first time in the session I actually took it mid-task rather than in a retro. THE SELF-REPORT IS THE PART I WOULD KEEP: `script ok` in the header, absent if the script threw, written to a data-local attribute so the report cannot itself trip the region-off it exists to detect."; }
    part blImplementGateR1 : TestResult { :>> id = "0d8006e8-0814-66e8-9b3e-0000003006e8"; :>> outcome = VerdictKind::pass; :>> judgedAgainst = "02ea1af"; :>> judgedAt = "2026-08-20"; :>> judgedBy = "claudeOpus5"; }

    verification blReviewGate : Test { :>> id = "0d8006e9-0814-66e9-9b3e-0000003006e9"; :>> title = "Sprint 371 review gate"; :>> createdAt = "2026-08-20"; :>> createdBy = "claudeOpus5"; :>> method = VerificationMethod::inspect; :>> procedureText = "Reviewed. THE DoD IS method=demo AND STAYS OPEN UNTIL THEY SAY OTHERWISE. I cannot test a tap from here; I can verify eight properties of the emitted HTML and I have, but whether a finger on a phone turns a card is a demo only they can judge - and I have now twice reported these buttons as working on the strength of having written them. The sprint's own DoD result records the code fix; the human confirmation is a separate obligation and the deck itself carries it. WHAT A REVIEWER SHOULD ATTACK: I still have no way to exercise this page. The fix is correct by the contract and by inspection, and 'correct by inspection' is exactly what I said last time. The honest position is that the self-report marker now makes ONE look sufficient - if the header says `script ok` and a tap shows `saved`, it works, and if it does not, the page says which half failed. That is a real improvement over asking them to describe a symptom."; }
    part blReviewGateR1 : TestResult { :>> id = "0d8006ea-0814-66ea-9b3e-0000003006ea"; :>> outcome = VerdictKind::pass; :>> judgedAgainst = "02ea1af"; :>> judgedAt = "2026-08-20"; :>> judgedBy = "claudeOpus5"; }

    verification blCloseOutGate : Test { :>> id = "0d8006eb-0814-66eb-9b3e-0000003006eb"; :>> title = "Sprint 371 closeOut gate (autonomous, D0049)"; :>> createdAt = "2026-08-20"; :>> createdBy = "claudeOpus5"; :>> method = VerificationMethod::inspect; :>> procedureText = "Autonomous closeOut (D0049). issue188 recorded; the code fix is judged and the DEMO confirmation is theirs to give. The skill gains a numbered section, `The live doc switches itself off if script touches the DOM`, with five rules each carrying the failure that produced it, and the export section is retitled to say plainly that copy is a fallback rather than a route. Republished to the same URL so their link still works. validate 403 clean; check-engine clean; 38 guards ALL PASS."; }
    part blCloseOutGateR1 : TestResult { :>> id = "0d8006ec-0814-66ec-9b3e-0000003006ec"; :>> outcome = VerdictKind::pass; :>> judgedAgainst = "02ea1af"; :>> judgedAt = "2026-08-20"; :>> judgedBy = "claudeOpus5"; }

    verification blRetroGate : Test { :>> id = "0d8006ed-0814-66ed-9b3e-0000003006ed"; :>> title = "Sprint 371 retro gate (autonomous, D0049)"; :>> createdAt = "2026-08-20"; :>> createdBy = "claudeOpus5"; :>> method = VerificationMethod::analyze; :>> procedureText = "Autonomous retro (D0049) under D0131's retroTrack. WELL: (1) the diagnosis came from reading the emitted script rather than guessing, after three plausible hypotheses about mobile browsers all failed to survive contact with the code; (2) the question that settled it - which top-level statements run BEFORE the listener registers - is now a numbered check in the skill; (3) the page can now report its own script death, closing the gap that let two publishes go out unverified; (4) two further defects of mine were found and fixed in the same inspection rather than left for the human to hit; (5) the DoD is method=demo and stays open, because I have twice reported these buttons working on the strength of having written them. AVOIDABLE-ISSUE, THE PRIMARY ONE: I violated two anti-patterns that are written down in the skill I was following, having read that list earlier in this same session. The fix is not more rules - it is that each rule now carries the failure that produced it, because a rule with a scar attached is harder to skip than a bullet in a list. SECOND AVOIDABLE-ISSUE: five separate heredoc and escaping failures editing one file, and the remedy - author with the Write tool - has been recorded four times. I finally took it MID-TASK instead of in a retro, and it worked first time. The measurable lesson is that I reach for the shell when an edit feels mechanical, and mechanical is exactly when escaping bites. Estimate 3 pts, delivered."; }
    part blRetroGateR1 : TestResult { :>> id = "0d8006ee-0814-66ee-9b3e-0000003006ee"; :>> outcome = VerdictKind::pass; :>> judgedAgainst = "02ea1af"; :>> judgedAt = "2026-08-20"; :>> judgedBy = "claudeOpus5"; }
}
