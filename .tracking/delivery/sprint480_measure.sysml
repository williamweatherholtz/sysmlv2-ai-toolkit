// ProjectDeliveryS480 - Sprint 480: measure it against a control on a set nobody hand-picked. 48% vs 34%, so it ships - and the confidence bar I built was the thing hurting it. EXECUTE. 3 pts.
package ProjectDeliveryS480 {
    private import EngineElement::*;
    private import EngineWork::*;
    private import EngineVerification::*;
    private import EngineRelationships::*;

    #CharteredBy dependency from measureStory to d0242;

    part measureStory : Story {
        :>> id = "6bdb2d5e-e77c-4bab-9e8c-6ed88426ab79";
        :>> title = "Sprint 480: 50-case retrieval benchmark against a keyword-search control, and the reversal it forced (3 pts)";
        :>> createdAt = "2026-08-28"; :>> createdBy = "claudeOpus5"; :>> kind = WorkKind::code; :>> priority = WorkPriority::p1; :>> owner = "claudeOpus5"; :>> estimatedPoints = 3;
    }

    action def DeliveryRunS480 {
        action storyMeasure;
        verification storyMeasureDoD : Test { :>> id = "b13032dc-7a43-467d-ac81-7e0478b256a7"; :>> method = VerificationMethod::test; :>> procedureText = "DELIVERED: kgInjectionProvenOnTheTrap (D0242 part 4). Two committed, reproducible harnesses - recall_ab.py (8 hand-written cases, ground truth fixed before running) and recall_bench.py (50 cases derived mechanically from each target's body text, seeded). KG retrieval beats the naive keyword-search control 48% to 34% on the 50-case set, with median hit position 2, so injection SHIPS under the honest-outcome clause. The 8-case set forced a reversal of my own design: the confidence bar scored 2/8 against 5/8 for no bar at all, so it was REMOVED - it suppressed more right answers than wrong ones."; }
    // RAN: .engine/tools/recall_bench.py, 50 cases, seed 20260828, queries derived from each target's BODY text with its own name-words removed: KG 24/50 = 48%, naive keyword control 17/50 = 34%; overlap both 13, KG-only 11, grep-only 4, neither 22, union 28/50; KG hit position median 2 with top-3 in 14 of 24; latency mean 1009ms max 1256ms; pushed on 50/50 | earlier 8-case set, ground truth fixed BEFORE running and no prompt shared with the six used for tuning: no bar 5/8, bar-as-shipped 2/8, bar-without-name-match 2/8, injection off 0/8, 4 of 5 hits at position 1-2 | cargo test --release => 14 suites 0 failures; cargo clippy --release --all-targets => 0 errors.
        part storyMeasureDoDR1 : TestResult { :>> id = "2cc69a55-6e58-4736-9c4c-db6857949418"; :>> outcome = VerdictKind::pass; :>> judgedAgainst = "2bec54d"; :>> judgedAt = "2026-08-28"; :>> judgedBy = "claudeOpus5"; }
    }

    verification measureRefineGate : Test { :>> id = "0e8ad6bd-e2c2-492d-b78d-2a266ad0a6c0"; :>> title = "Sprint 480 refine gate (DoR)"; :>> createdAt = "2026-08-28"; :>> createdBy = "claudeOpus5"; :>> method = VerificationMethod::inspect; :>> procedureText = "DoR: the human asked for a 50-case with/without comparison. TWO DESIGN CORRECTIONS were made before measuring anything, and both change what the number means. First, the control is naive KEYWORD SEARCH, not silence: a model without recall does not sit in the dark, it greps, and scoring the control as zero would have rigged the comparison in favour of the feature I had just built. Second, the questions are DERIVED from each target's body text rather than written by me, because fifty hand-written questions would let me bias the set toward what recall happens to find. Resolver: kgInjectionProvenOnTheTrap. estimatedPoints=3. #CharteredBy d0242."; }
    part measureRefineGateR1 : TestResult { :>> id = "b8e8021b-ad18-499a-9862-0b0dd9ea0d73"; :>> outcome = VerdictKind::pass; :>> judgedAgainst = "2bec54d"; :>> judgedAt = "2026-08-28"; :>> judgedBy = "claudeOpus5"; }
    verification measureStandupGate : Test { :>> id = "2dc6818f-1615-4b70-ae52-f56cf3650027"; :>> title = "Sprint 480 standup gate"; :>> createdAt = "2026-08-28"; :>> createdBy = "claudeOpus5"; :>> method = VerificationMethod::inspect; :>> procedureText = "Approach: derive each query from the target element's BODY with its own name-words removed, so the test is not a string match against the thing being searched for; seed the sample so the number is re-derivable; commit both harnesses under .engine/tools/ so the claim is a measurement rather than a sentence in a commit message. Also corrected the DoD's own measure - it asked for tool-calls-to-first-correct-answer, which I cannot take honestly on myself because I already know the answers to questions about this corpus, so the count would measure my memory rather than the retrieval."; }
    part measureStandupGateR1 : TestResult { :>> id = "b655e7a7-54da-4f2b-bce9-3c812aa30b77"; :>> outcome = VerdictKind::pass; :>> judgedAgainst = "2bec54d"; :>> judgedAt = "2026-08-28"; :>> judgedBy = "claudeOpus5"; }
    verification measureImplementGate : Test { :>> id = "c82625e1-1db5-49b5-998e-1b7e0196925d"; :>> title = "Sprint 480 implement gate"; :>> createdAt = "2026-08-28"; :>> createdBy = "claudeOpus5"; :>> method = VerificationMethod::test; :>> procedureText = "Measured. KG 24/50 against the control's 17/50, median hit position 2, mean 1009ms. The COMPLEMENTARITY is the more useful cut than the headline: 13 cases both found, 11 KG-only, 4 GREP-ONLY, 22 neither. So traversal is better on average and NOT strictly dominant - four cases where a substring scan wins are four cases where segment matching is too strict, which is the same axis as issue294. The 44% neither-found figure is a property of a deliberately hard benchmark: stripping the target's own name-words is harsher than any real prompt, where a person usually names the subject. Treat 48% as a lower bound, and the 8-case natural-language set at 5/8 as the upper."; }
    // RAN: .engine/tools/recall_bench.py, 50 cases, seed 20260828, queries derived from each target's BODY text with its own name-words removed: KG 24/50 = 48%, naive keyword control 17/50 = 34%; overlap both 13, KG-only 11, grep-only 4, neither 22, union 28/50; KG hit position median 2 with top-3 in 14 of 24; latency mean 1009ms max 1256ms; pushed on 50/50 | earlier 8-case set, ground truth fixed BEFORE running and no prompt shared with the six used for tuning: no bar 5/8, bar-as-shipped 2/8, bar-without-name-match 2/8, injection off 0/8, 4 of 5 hits at position 1-2 | cargo test --release => 14 suites 0 failures; cargo clippy --release --all-targets => 0 errors.
    part measureImplementGateR1 : TestResult { :>> id = "7b35527c-363a-4c86-89f0-017b8c629467"; :>> outcome = VerdictKind::pass; :>> judgedAgainst = "2bec54d"; :>> judgedAt = "2026-08-28"; :>> judgedBy = "claudeOpus5"; }
    verification measureReviewGate : Test { :>> id = "0b72ba83-99df-409f-a1b3-2284c8f96733"; :>> title = "Sprint 480 review gate"; :>> createdAt = "2026-08-28"; :>> createdBy = "claudeOpus5"; :>> method = VerificationMethod::inspect; :>> procedureText = "Diff reviewed. The finding I did not expect and did not want is the one worth keeping: my confidence bar HURT, 2/8 against 5/8, and two attempts to tune it both landed at 2/8. Seed count is not a proxy for relevance - the wrongly silenced prompts had 13 to 53 seeds, the same range as the ones the bar admitted. It was removed rather than tuned a third time, and the tests were rewritten to carry that history rather than deleted. What survived is a different and correct check, upstream: a prompt of only filler and corpus-common words yields no tokens and pushes nothing."; }
    part measureReviewGateR1 : TestResult { :>> id = "a5e60bce-6cfa-4927-b04d-5caab5c2f46d"; :>> outcome = VerdictKind::pass; :>> judgedAgainst = "2bec54d"; :>> judgedAt = "2026-08-28"; :>> judgedBy = "claudeOpus5"; }
    verification measureCloseOutGate : Test { :>> id = "b88df6bc-2cf7-4a20-b91e-a9af09628612"; :>> title = "Sprint 480 closeOut gate (autonomous, D0049)"; :>> createdAt = "2026-08-28"; :>> createdBy = "claudeOpus5"; :>> method = VerificationMethod::inspect; :>> procedureText = "Autonomous closeOut (D0049): the DoD is recorded pass with its RAN receipt and its measure corrected in the record rather than quietly reinterpreted. Injection ships because it beat the control, which is the condition the honest-outcome clause named in advance. One item of the five D0242 parts remains: kgTravelsWithTheEngine. Self-evidencing (D0051): no human confirmation claimed."; }
    part measureCloseOutGateR1 : TestResult { :>> id = "52ec099d-99c9-4430-8fce-bce3adcd457c"; :>> outcome = VerdictKind::pass; :>> judgedAgainst = "2bec54d"; :>> judgedAt = "2026-08-28"; :>> judgedBy = "claudeOpus5"; }
    verification measureRetroGate : Test { :>> id = "9b06e2eb-0876-4f2c-9631-614fb0e8bfe8"; :>> title = "Sprint 480 retro gate (autonomous, D0049)"; :>> createdAt = "2026-08-28"; :>> createdBy = "claudeOpus5"; :>> method = VerificationMethod::analyze; :>> procedureText = "Autonomous retro (D0049). WELL: choosing the control BEFORE running anything is what makes this number mean something. Silence-as-control would have produced 48% against 0% and read as a triumph; grep-as-control produced 48% against 34% and reads as a real but modest gain, which is the truth. Deriving the questions mechanically did the same job for the other half of the bias. FINDING: three of my own designed safeguards have now been REVERSED BY MEASUREMENT in three sprints - the name-match requirement, the focused-seed threshold, and the confidence bar entirely. Each was reasoned from a real defect and each cost more than it saved. The pattern is that I reason well about individual failure cases and badly about their frequency, so a safeguard justified by one vivid example needs a set before it ships. AVOIDABLE-ISSUE SCAN: the DoD asked for a measure I could not honestly take, and I wrote it two days ago without noticing - a DoD that names an unobtainable measure will either be quietly reinterpreted at stamping time or block forever. Candidate forward control, stated not built: a DoD naming a measurement should name WHO or WHAT can take it. Estimate 3 pts held."; }
    part measureRetroGateR1 : TestResult { :>> id = "a56fb852-c029-40f2-b741-f5a784fc7c75"; :>> outcome = VerdictKind::pass; :>> judgedAgainst = "2bec54d"; :>> judgedAt = "2026-08-28"; :>> judgedBy = "claudeOpus5"; }
}
