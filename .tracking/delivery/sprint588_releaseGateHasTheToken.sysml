// ProjectDeliveryS588 — Sprint 588: the release that published nothing is diagnosed at its cause, the two gating workflows are held to one environment, and v0.4.1 ships for real. EXECUTE. 1 pts.
package ProjectDeliveryS588 {
    private import EngineElement::*;
    private import EngineWork::*;
    private import EngineVerification::*;
    private import EngineRelationships::*;

    #CharteredBy dependency from releaseGateHasTheTokenStory to d0358;

    part releaseGateHasTheTokenStory : Story {
        :>> id = "849c92c6-fc82-4bd9-ac1d-5314cef72c5c";
        :>> title = "Sprint 588: the release that published nothing is diagnosed at its cause, the two gating workflows are held to one environment, and v0.4.1 ships for real (1 pts)";
        :>> createdAt = "2026-09-06"; :>> createdBy = "claudeOpus5"; :>> kind = WorkKind::code; :>> priority = WorkPriority::p0; :>> owner = "claudeOpus5"; :>> estimatedPoints = 1;
    }

    action def DeliveryRunS588 {
        action storyReleaseGateHasTheToken;
        verification storyReleaseGateHasTheTokenDoD : Test { :>> id = "8f911b15-e114-4be2-8856-d32d6e77fd7f"; :>> method = VerificationMethod::test; :>> procedureText = "DELIVERED BACKLOG ITEM: dcReleaseGateHasTheToken (resolves issue385), chartered by D0358. DONE: the release workflow's test step is given the same repository token ci.yml already supplies, with the reason recorded beside it; guard 64 gate-environment-parity holds every workflow that runs the suite to the same environment, deriving its expectation from the tree so a project whose gate needs nothing is never accused; the guard carries a constraint-def identity and a catalogue row; v0.4.0 is left tagged where it is and its Release record states that it published nothing and why, while release041 carries the shipment bound to b171cd7. ALSO TRACKED, NOT FIXED: issue386, keel suite rebuilds the binary running it and reported a file lock as fail - 0 passed, 0 failed. VERIFIED BY THE PARTY I CANNOT WRITE TO: the release run for v0.4.1 concluded success on b171cd7, gate and all three build legs green, and the published release carries keel-linux-x86_64, keel-macos-aarch64 and keel-windows-x86_64.exe."; }
        // RAN: ci-run id=34048681892 workflow=release
        part storyReleaseGateHasTheTokenDoDR1 : TestResult { :>> id = "98e4c1b3-9bbe-42c6-b572-a519388d60b1"; :>> outcome = VerdictKind::pass; :>> judgedAgainst = "b171cd7"; :>> judgedAt = "2026-09-06"; :>> judgedBy = "claudeOpus5"; }
    }

    verification releaseGateHasTheTokenRefineGate : Test { :>> id = "8ebd1950-9223-4006-b30e-d9f7b4bc7537"; :>> title = "Sprint 588 refine gate (DoR)"; :>> createdAt = "2026-09-06"; :>> createdBy = "claudeOpus5"; :>> method = VerificationMethod::inspect; :>> procedureText = "READY: the owner's answer was Release now, and the release had already failed once without my noticing what it published. The scope was set by the failure itself - the token is the fix, the parity guard is the control, and the version number is the only thing the correction costs."; }
    // RAN: ci-run id=34048681892 workflow=release
    part releaseGateHasTheTokenRefineGateR1 : TestResult { :>> id = "57cb0acc-a07b-4437-bb2c-43f8aeb70987"; :>> outcome = VerdictKind::pass; :>> judgedAgainst = "b171cd7"; :>> judgedAt = "2026-09-06"; :>> judgedBy = "claudeOpus5"; }
    verification releaseGateHasTheTokenStandupGate : Test { :>> id = "f854cc74-5a44-458b-979f-ce642c24507f"; :>> title = "Sprint 588 standup gate"; :>> createdAt = "2026-09-06"; :>> createdBy = "claudeOpus5"; :>> method = VerificationMethod::inspect; :>> procedureText = "THE RELEASE I REPORTED AS CUT HAD PUBLISHED NOTHING. The tag went out on a locally green suite and its CI gate failed on one test whose precondition only ci.yml supplies. I had checked the workflow was in_progress and moved on; the run concluded failure and gh release view said release not found. What made it visible was going back to look rather than assuming."; }
    // RAN: ci-run id=34048681892 workflow=release
    part releaseGateHasTheTokenStandupGateR1 : TestResult { :>> id = "678c7e99-aa54-4036-a477-70c19bc2eb48"; :>> outcome = VerdictKind::pass; :>> judgedAgainst = "b171cd7"; :>> judgedAt = "2026-09-06"; :>> judgedBy = "claudeOpus5"; }
    verification releaseGateHasTheTokenImplementGate : Test { :>> id = "a6dbdbe2-5629-439e-9531-a56276b03d4f"; :>> title = "Sprint 588 implement gate"; :>> createdAt = "2026-09-06"; :>> createdBy = "claudeOpus5"; :>> method = VerificationMethod::test; :>> procedureText = "RAN: gh run view on the failed run, which named the cause verbatim - gh refuses inside Actions without GH_TOKEN; the token added to release.yml; guard 64 written, then SHOWN TO BITE - PASS 2 scanned on the fixed tree, FAIL 1 violation with the token stripped back out; keel validate 667 clean; keel check-engine clean; keel guard ALL PASS at 64 guards; cargo clippy --workspace --all-targets -D warnings clean; keel suite 562 passed 0 failed from a COPY of the binary; tag v0.4.1 on b171cd7; gh run watch to conclusion, gate success and three build legs success; gh release view v0.4.1 listing three assets with their sizes."; }
    // RAN: ci-run id=34048681892 workflow=release
    part releaseGateHasTheTokenImplementGateR1 : TestResult { :>> id = "a145d9d5-c3e6-4d30-8666-65e54be51706"; :>> outcome = VerdictKind::pass; :>> judgedAgainst = "b171cd7"; :>> judgedAt = "2026-09-06"; :>> judgedBy = "claudeOpus5"; }
    verification releaseGateHasTheTokenReviewGate : Test { :>> id = "3b7e5562-22ce-4e98-b3fd-391acdd9bb8e"; :>> title = "Sprint 588 review gate — three passes per D0172"; :>> createdAt = "2026-09-06"; :>> createdBy = "claudeOpus5"; :>> method = VerificationMethod::inspect; :>> procedureText = "THREE PASSES. (1) DID THE SUITE EARN ITS RUN: yes - it failed 561/1 on every_guard_has_a_constraint_def_identity, because the new guard had no identity in guard-constraints.sysml. Neither validate nor guard would have caught it; that test exists because twelve guards lacked one for weeks (issue370). (2) DID MY OWN EDIT CREATE A FALSE SIGNAL: yes - putting the string v0.4.1 in the v0.4.0 record's TITLE made release-recorded match the wrong record, since it matches a tag by substring in the title. Reworded, and the fragility is worth its own item. (3) IS ANYTHING CLAIMED THAT WAS NOT CHECKED: the publication is asserted from the run's own conclusion and the asset list, not from the tag existing - which is precisely the check that was missing last time."; }
    // RAN: ci-run id=34048681892 workflow=release
    part releaseGateHasTheTokenReviewGateR1 : TestResult { :>> id = "61b2e5a6-3788-4e3a-a354-6d9bae7d9f9d"; :>> outcome = VerdictKind::pass; :>> judgedAgainst = "b171cd7"; :>> judgedAt = "2026-09-06"; :>> judgedBy = "claudeOpus5"; }
    verification releaseGateHasTheTokenCloseOutGate : Test { :>> id = "c242571e-fa45-4e91-8d27-117cd85e1406"; :>> title = "Sprint 588 closeOut gate (autonomous, D0049)"; :>> createdAt = "2026-09-06"; :>> createdBy = "claudeOpus5"; :>> method = VerificationMethod::inspect; :>> procedureText = "CLOSED. v0.4.1 is published with all three platform binaries attached; the failure that hid for a whole release cycle now fails at the commit that introduces it."; }
    // RAN: ci-run id=34048681892 workflow=release
    part releaseGateHasTheTokenCloseOutGateR1 : TestResult { :>> id = "93e652bd-3469-406b-90be-90e769845a3b"; :>> outcome = VerdictKind::pass; :>> judgedAgainst = "b171cd7"; :>> judgedAt = "2026-09-06"; :>> judgedBy = "claudeOpus5"; }
    verification releaseGateHasTheTokenRetroGate : Test { :>> id = "0ad92c80-d267-4629-a88a-17bc4e981c38"; :>> title = "Sprint 588 retro gate (autonomous, D0049)"; :>> createdAt = "2026-09-06"; :>> createdBy = "claudeOpus5"; :>> method = VerificationMethod::analyze; :>> procedureText = "AVOIDABLE-ISSUE SCAN HELD. The avoidable one: I reported v0.4.0 as cut and pushed while its only evidence was that a workflow had STARTED - the run concluded failure seven minutes later and published nothing, and a single gh run view would have said so before I said anything. The process improvement is not a reminder: an outward-facing write is verified by reading the PUBLISHED artifact back, which is what the deploy step now does here and what the sprint DoD cites. The unavoidable one: the token divergence itself could not be seen from this machine, since the everyday gate supplies it and only the release gate did not - that is why it became guard 64 rather than a note. NEW ITEM dcReleaseRecordNamesItsTag (issue387): release-recorded matches a tag to its Release record by substring-in-title, so a title that merely mentions another version misidentifies the record and a v0.4.1 tag would also match a v0.4.11 title - it warned about the wrong record here and only looked like a real disagreement. LESSON, and it is the same one as yesterday: I reported a tag as shipped while its only evidence was that a workflow had started. A verdict about an outward-facing write is not the write's own report - it is the published artifact, read back."; }
    // RAN: ci-run id=34048681892 workflow=release
    part releaseGateHasTheTokenRetroGateR1 : TestResult { :>> id = "cecc8fda-dbba-4a82-9d2b-5822869e6741"; :>> outcome = VerdictKind::pass; :>> judgedAgainst = "b171cd7"; :>> judgedAt = "2026-09-06"; :>> judgedBy = "claudeOpus5"; }
}
