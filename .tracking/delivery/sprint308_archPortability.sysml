// ProjectDeliveryS308 — Sprint 308: the arch portability test, run for real against a second
// project. Three defects found, including a lockout shipped the same day. EXECUTE. 8 pts.
package ProjectDeliveryS308 {
    private import EngineElement::*;
    private import EngineWork::*;
    private import EngineVerification::*;
    private import EngineRelationships::*;

    #CharteredBy dependency from archPortabilityStory to issue129;

    part archPortabilityStory : Story {
        :>> id = "0d8002f0-0814-62f0-9b3e-0000003002f0";
        :>> title = "Sprint 308: verify arch against SelfSync's registry; fix what it found (8 pts)";
        :>> createdAt = "2026-08-15"; :>> createdBy = "claudeOpus5"; :>> kind = WorkKind::code; :>> priority = WorkPriority::p0; :>> owner = "claudeOpus5"; :>> estimatedPoints = 8;
    }

    action def DeliveryRunS308 {
        action storyArchPortability;
        verification storyArchPortabilityDoD : Test { :>> id = "0d8002f1-0814-62f1-9b3e-0000003002f1"; :>> method = VerificationMethod::demo; :>> procedureText = "Delivers dcArchRegistryPortability and resolves issue117, issue128, issue129, issue130. THE ITEM WAS RECORDED AS BLOCKED ON DATA THIS REPO DOES NOT HOLD, AND THAT WAS WRONG — the data was on this machine the whole time. `obsidian-livesync` is SelfSync: a keel-initialised project with 169 authored CodeElements and its own `.engine/schema/codeaudit/` copy. issue117 said the portability claim was unverifiable here; it took one directory listing to disprove. THE PORTABILITY CLAIM ITSELF HOLDS: all six views ran against a different project's registry with NO change to keel. But running them found three real defects, all invisible against keel's own registry because that registry shares an author with the views — exactly the blind spot issue117 predicted. (1) issue128, High: `arch criticality` ranked 23 of their 169 elements LAST as `unclassified`. D0150 derives the ranking from the EMBEDDED RiskClass, and SelfSync declares its own with `durability` and `concurrency`; their `Vault::commit`, `Vault::verify_and_gc` and `write_mirror` sorted below `cosmetic` in the one view whose purpose is what-to-audit-first. Fixed: read the PROJECT's RiskClass, fall back to the engine's. (2) issue129, High: the `attribute-vocabulary` guard — shipped this morning in sprint 303 — produced 1287 VIOLATIONS against that project, which would block every commit there on a binary upgrade. Fixed: union the engine's attribute declaration with the project's, as the marker guard already does. 1287 -> 0, with this repo still clean at 41141 scanned and typo detection unaffected. (3) issue130, Medium: `arch drift` reported all 169 elements as MISSING when in truth none had a filePath authored at all. Fixed: UNLOCATED is now its own state. clippy clean; 217 tests; validate 333 clean; 33 guards green."; }
        part storyArchPortabilityDoDR1 : TestResult { :>> id = "0d8002f2-0814-62f2-9b3e-0000003002f2"; :>> outcome = VerdictKind::pass; :>> judgedAgainst = "0deee4e"; :>> judgedAt = "2026-08-15"; :>> judgedBy = "claudeOpus5"; }
    }

    verification apRefineGate : Test { :>> id = "0d8002f3-0814-62f3-9b3e-0000003002f3"; :>> title = "Sprint 308 refine gate (DoR)"; :>> createdAt = "2026-08-15"; :>> createdBy = "claudeOpus5"; :>> method = VerificationMethod::inspect; :>> procedureText = "DoR. The item was the last on the frontier and was twice recorded as blocked on external data — in sprint 301's re-scope and again in issue117. Before reporting it blocked a THIRD time, I checked whether a second keel project existed on this machine. Four do, and one holds the registry. The lesson is cheap and worth stating: 'blocked on data we do not have' is a claim about the world, and it deserves the same verification as any other claim. estimatedPoints=8, raised from the original estimate once the data was found and the run became real work rather than a status report."; }
    part apRefineGateR1 : TestResult { :>> id = "0d8002f4-0814-62f4-9b3e-0000003002f4"; :>> outcome = VerdictKind::pass; :>> judgedAgainst = "0deee4e"; :>> judgedAt = "2026-08-15"; :>> judgedBy = "claudeOpus5"; }

    verification apStandupGate : Test { :>> id = "0d8002f5-0814-62f5-9b3e-0000003002f5"; :>> title = "Sprint 308 standup gate"; :>> createdAt = "2026-08-15"; :>> createdBy = "claudeOpus5"; :>> method = VerificationMethod::inspect; :>> procedureText = "Approach: treat the other project as READ-ONLY throughout — it is another actor's repository and nothing here writes to it; run all six views; compare their schema module against the shipped one, because a divergent local copy is where the interesting failures live. No blockers."; }
    part apStandupGateR1 : TestResult { :>> id = "0d8002f6-0814-62f6-9b3e-0000003002f6"; :>> outcome = VerdictKind::pass; :>> judgedAgainst = "0deee4e"; :>> judgedAt = "2026-08-15"; :>> judgedBy = "claudeOpus5"; }

    verification apImplementGate : Test { :>> id = "0d8002f7-0814-62f7-9b3e-0000003002f7"; :>> title = "Sprint 308 implement gate"; :>> createdAt = "2026-08-15"; :>> createdBy = "claudeOpus5"; :>> method = VerificationMethod::test; :>> procedureText = "ISSUE129 IS THE ONE THAT MATTERS AND IT IS MINE. I shipped `attribute-vocabulary` this morning as a HARD guard. Run against a real downstream project it produced 1287 violations and would have blocked every commit there on upgrade. The failure is not subtle and I had the lesson in hand: issue090/D0133 is the identical shape for MARKERS, I read it while building the guard, and I quoted it in the module doc as the reason to read the EMBEDDED schema. What I missed is that reading the embedded schema protects the engine's vocabulary FROM REMOVAL and says nothing about a project ADDING to it — the marker guard solved that with ENGINE UNION PROJECT and I implemented only the first half. A FOURTH DEFECT, INTRODUCED BY THE FIX ITSELF AND CAUGHT BY THE GATE: reading the project vocabulary inside `declared_attrs_in` re-parsed the whole project schema directory FOR EVERY ATTRIBUTE ASSIGNMENT — 41k of them — and the pre-commit hook stopped completing inside ten minutes. The commit hung and did not land, which is the gate doing its job: a guard slow enough to time out is a guard someone disables, the issue076/issue081 dynamic this project has already paid for once. Memoised per root; the full suite now runs in 4.3s. THE GENERAL LESSON, and it is why a downstream test is not optional: this guard was verified against 40355 assignments in THIS repo, found zero violations, and looked completely healthy. A control validated only against its author's own corpus is validated against the corpus least likely to break it. Detection is provably unaffected by the fix — the union adds names the project declared, and a misspelling appears in neither set, which the tests assert. issue128 has the same root: a rule derived from the engine's own schema, correct here, wrong the moment a project declares its own taxonomy."; }
    part apImplementGateR1 : TestResult { :>> id = "0d8002f8-0814-62f8-9b3e-0000003002f8"; :>> outcome = VerdictKind::pass; :>> judgedAgainst = "0deee4e"; :>> judgedAt = "2026-08-15"; :>> judgedBy = "claudeOpus5"; }

    verification apReviewGate : Test { :>> id = "0d8002f9-0814-62f9-9b3e-0000003002f9"; :>> title = "Sprint 308 review gate"; :>> createdAt = "2026-08-15"; :>> createdBy = "claudeOpus5"; :>> method = VerificationMethod::inspect; :>> procedureText = "Reviewed. THE ENGINE-VERSUS-PROJECT RULE IS NOW EXPLICIT rather than incidental, because getting it wrong in either direction is a lockout or a wrong answer: engine vocabulary (markers, edge kinds) is read from the EMBEDDED schema so a project cannot lose it; a project-declared enum ORDER and a project's ADDED attributes are read from the PROJECT so the engine cannot overrule its judgment or reject its additions. Both halves are written at the functions that implement them and in the module doc, which previously said 'never the project's' without qualification and was corrected in the same commit. NOT DONE, deliberately: SelfSync's registry uses `file` where the shipped module declares `filePath`, so `arch drift` cannot locate its code even now. That is a MIGRATION for that project to run — `keel migrate` exists for exactly this — and not something to paper over by teaching keel two names for one attribute, which would make the shipped module's vocabulary advisory."; }
    part apReviewGateR1 : TestResult { :>> id = "0d8002fa-0814-62fa-9b3e-0000003002fa"; :>> outcome = VerdictKind::pass; :>> judgedAgainst = "0deee4e"; :>> judgedAt = "2026-08-15"; :>> judgedBy = "claudeOpus5"; }

    verification apCloseOutGate : Test { :>> id = "0d8002fb-0814-62fb-9b3e-0000003002fb"; :>> title = "Sprint 308 closeOut gate (autonomous, D0049)"; :>> createdAt = "2026-08-15"; :>> createdBy = "claudeOpus5"; :>> method = VerificationMethod::inspect; :>> procedureText = "Autonomous closeOut (D0049). issue117, issue128, issue129 and issue130 all resolve through dcArchRegistryPortability. The other project was read and never written. clippy clean; 217 tests; validate 333 clean; check-engine clean; 33 guards green here AND on the downstream project, which is the check that actually mattered."; }
    part apCloseOutGateR1 : TestResult { :>> id = "0d8002fc-0814-62fc-9b3e-0000003002fc"; :>> outcome = VerdictKind::pass; :>> judgedAgainst = "0deee4e"; :>> judgedAt = "2026-08-15"; :>> judgedBy = "claudeOpus5"; }

    verification apRetroGate : Test { :>> id = "0d8002fd-0814-62fd-9b3e-0000003002fd"; :>> title = "Sprint 308 retro gate (autonomous, D0049)"; :>> createdAt = "2026-08-15"; :>> createdBy = "claudeOpus5"; :>> method = VerificationMethod::analyze; :>> procedureText = "Autonomous retro (D0049) under D0131's retroTrack. THE FINDING OF THE WHOLE SESSION: a control validated only against its author's own corpus is validated against the corpus least likely to break it. `attribute-vocabulary` scanned 40355 assignments here, found zero violations, and was shipped as a hard guard the same morning; the first contact with a real downstream project produced 1287 violations and a total lockout. Everything else I built today — the derived vocabulary, the arch views, the criticality ranking — was verified the same way, against this repo alone, and two of those also broke on first contact. WELL: (1) checking whether the 'blocked on external data' claim was true before restating it a third time, which is what unblocked the item at all; (2) treating the other repo as strictly read-only; (3) fixing the lockout by copying the marker guard's ENGINE-UNION-PROJECT shape rather than inventing a new rule, and asserting that detection survived. AVOIDABLE-ISSUE, tracked as issue129 rather than absorbed: I had the exact precedent in hand and implemented half of it. NO NEW CONTROL PROPOSED HERE, and the reason is stated: the control that would have caught this is running the gate against a downstream project, which is now a real capability rather than a hypothetical one, and belongs in a Decision about release practice rather than a guard invented at the end of a sprint. Estimate 8 pts, delivered."; }
    part apRetroGateR1 : TestResult { :>> id = "0d8002fe-0814-62fe-9b3e-0000003002fe"; :>> outcome = VerdictKind::pass; :>> judgedAgainst = "0deee4e"; :>> judgedAt = "2026-08-15"; :>> judgedBy = "claudeOpus5"; }
}
