// ProjectDeliveryS601 — Sprint 601: Rank 4 of D0367: a green gate writes a receipt keyed on every input a guard can read, and the next run whose key is equal answers from it (dcGateAnswersFromItsReceipt, D0371). EXECUTE. 3 pts.
package ProjectDeliveryS601 {
    private import EngineElement::*;
    private import EngineWork::*;
    private import EngineVerification::*;
    private import EngineRelationships::*;

    #CharteredBy dependency from gateAnswersFromItsReceiptStory to d0371;

    part gateAnswersFromItsReceiptStory : Story {
        :>> id = "62a9dbae-eabe-4cd3-b5a2-1f1f4cbe569c";
        :>> title = "Sprint 601: Rank 4 of D0367: a green gate writes a receipt keyed on every input a guard can read, and the next run whose key is equal answers from it (dcGateAnswersFromItsReceipt, D0371) (3 pts)";
        :>> createdAt = "2026-09-07"; :>> createdBy = "claudeOpus5"; :>> kind = WorkKind::code; :>> priority = WorkPriority::p0; :>> owner = "claudeOpus5"; :>> estimatedPoints = 3;
    }

    action def DeliveryRunS601 {
        action storyGateAnswersFromItsReceipt;
        verification storyGateAnswersFromItsReceiptDoD : Test { :>> id = "d34be0b2-4a53-4f14-950a-d30003e71a0e"; :>> method = VerificationMethod::test; :>> procedureText = "DELIVERED: new module keel-cli/src/receipt.rs - receipt::key(root) digests HEAD's full id, every (XY, path) entry of `git status --porcelain -z -uall` with that path's (len, mtime), every file under .keel/ outside metrics/ and bin/ as (relpath, len, mtime), and the binary's build commit with its own (len, mtime); a path younger than two seconds marks the key unsettled; git failing yields no key. receipt::read returns the stored receipt only for an equal, settled key and reconstructs each GuardReport from a name this binary knows. receipt::record_green recomputes the key after the run and writes .keel/metrics/guard-receipt.toml (write_atomic) only when it equals the before key, merging the layers an equal earlier receipt covered. receipt::delete on any red run. receipt::forced honours --no-receipt and KEEL_NO_RECEIPT=1. Wired: cmd_guard all-guards path prints the stored reports and one line naming the receipt's age, records on green, deletes on red, strips --no-receipt before classifying its args; hook_stop returns 0 before validate when a receipt covers validate+guards+rules, records all three on green and deletes on red, the `if problems.is_empty() {` / `return 0;` shape the static test reads intact; cmd_gate --fast answers from a receipt covering validate+guards and never writes one; workspace::gate_outcome (gate_problems delegates) answers or records the same three layers and gate_one prints the receipt line instead of re-running validate for its count. CLAUDE.md section 5 carries the receipt in one paragraph. VERIFIED: receipt tests a_green_run_writes_the_receipt_and_the_next_run_answers_from_it, a_touched_tracked_file_a_new_untracked_file_and_a_changed_keel_file_each_force_a_run (also: a .keel/metrics/ write leaves the key alone), a_red_run_deletes_the_receipt_and_an_unsettled_key_is_never_trusted, status_entries_drop_the_rename_source_and_the_receipt_dirs_and_keep_every_other_field pass in cargo test --release; the full lib suite 411 pass after the test helper's raw git spawn was routed through gitx::git() (no_git_spawn_bypasses_the_counted_constructor caught it); clippy pedantic clean. MEASURED on this tree, shell timer: idle `keel hook stop` 5202 / 5428 ms before, 218 / 260 / 318 ms after against an equal key (the first run after a rebuild, 8683 ms, wrote the receipt); `keel guard --no-receipt` 5081 ms, `keel guard` from the receipt 215 / 239 ms, stdout identical except the one added receipt line (diff); `keel gate --fast .` 677 ms with --no-receipt, 189 / 229 ms from the receipt; a touched tracked file forced a 5549 ms run and `git checkout` of it restored the hit (318 ms). keel validate . 683 clean. Resolves the every-turn-boundary term of issue409."; }
        // RAN: cargo test --release -p keel-cli: 411 pass incl. 4 receipt tests; shell-timed hook stop 5202/5428 ms -> 218/260/318 ms, guard 5081 -> 215/239 ms (diff: one added line), gate --fast 677 -> 189/229 ms
        part storyGateAnswersFromItsReceiptDoDR1 : TestResult { :>> id = "9a7e5a7e-d277-4f89-b36e-dafc8170ab10"; :>> outcome = VerdictKind::pass; :>> judgedAgainst = "dd4d91fd8efd7d7d49e6b521aee9d4467e7b3d44"; :>> judgedAt = "2026-09-08T00:22:00-06:00"; :>> judgedBy = "claudeOpus5"; }
    }

    verification gateAnswersFromItsReceiptRefineGate : Test { :>> id = "017bb5d6-26f8-4170-8f53-2d6aa628ca80"; :>> title = "Sprint 601 refine gate (DoR)"; :>> createdAt = "2026-09-07"; :>> createdBy = "claudeOpus5"; :>> method = VerificationMethod::inspect; :>> procedureText = "READY, 3 pts: one new module, four call sites wired, four tests, a measurement - the DoD names the check for each. Chartered by D0371, a #SafetyChange because the hook path in main.rs and the gate in workspace.rs are the enforcement surface (D0209 clause 2); it stays proposed for the human's word under D0337 and the work proceeds with the Decision co-committed, which is what the lock asks. The DoD was re-read for the issue372/sprint599 defect before any check ran: every command it names exists (`keel guard`, `keel hook stop`, `keel gate --fast`, `--no-receipt`)."; }
    // RAN: cargo test --release -p keel-cli (411 pass); timed hook stop / guard / gate --fast with and without the receipt; keel validate .
    part gateAnswersFromItsReceiptRefineGateR1 : TestResult { :>> id = "bc15f6bd-f364-4248-9302-e4ceeb24f137"; :>> outcome = VerdictKind::pass; :>> judgedAgainst = "dd4d91fd8efd7d7d49e6b521aee9d4467e7b3d44"; :>> judgedAt = "2026-09-08T00:20:00-06:00"; :>> judgedBy = "claudeOpus5"; }
    verification gateAnswersFromItsReceiptStandupGate : Test { :>> id = "d3299267-014b-4d1c-8924-b0d813436bfe"; :>> title = "Sprint 601 standup gate"; :>> createdAt = "2026-09-07"; :>> createdBy = "claudeOpus5"; :>> method = VerificationMethod::inspect; :>> procedureText = "THREE CHOICES. First, the key hashes the parsed status ENTRIES, not the raw bytes: the first cut hashed the bytes and the fixture's own receipt appeared in them - in a repo that has not ignored .keel/ the receipt would have invalidated itself on every write, and the DoD's first test failed on 'removing it restores the key'. Second, the racy window is the same two-second bar corpus uses and it gates BOTH directions - an unsettled key is neither written nor honoured - so a boundary right after an edit pays one full run and writes nothing, and the next one writes. Third, the fast tier reads and never writes: three guards are not the guard set, and a receipt written by them would let hook stop skip sixty-two."; }
    // RAN: cargo test --release -p keel-cli (411 pass); timed hook stop / guard / gate --fast with and without the receipt; keel validate .
    part gateAnswersFromItsReceiptStandupGateR1 : TestResult { :>> id = "b258cf05-0294-4f01-ae0a-b9114fecb08d"; :>> outcome = VerdictKind::pass; :>> judgedAgainst = "dd4d91fd8efd7d7d49e6b521aee9d4467e7b3d44"; :>> judgedAt = "2026-09-08T00:20:00-06:00"; :>> judgedBy = "claudeOpus5"; }
    verification gateAnswersFromItsReceiptImplementGate : Test { :>> id = "6ace73d2-c9b1-40d0-ac52-a9975df7139a"; :>> title = "Sprint 601 implement gate"; :>> createdAt = "2026-09-07"; :>> createdBy = "claudeOpus5"; :>> method = VerificationMethod::test; :>> procedureText = "RAN: Write tool for receipt.rs; python patch_receipt.py (hook_stop, cmd_guard, cmd_gate, workspace gate_outcome/gate_one, each anchor required unique), fix_clippy_receipt.py, fix_status_entries.py, doc601.py; sed for the lib.rs module line, the partial-move fix, ALL_LAYERS hoisted into receipt.rs, the XY trim, the test helper's gitx route; cargo clippy --release -p keel-cli --all-targets (clean after single_match_else, too_long_first_doc_paragraph, must_use_candidate, items_after_statements, one E0382); cargo build --release; cargo test --release -p keel-cli (411 pass); timed hook stop, guard, gate --fast from a copy of the binary (keel-serve.exe) with and without the receipt, diff of guard stdout; the tracked-file touch and revert; keel validate .; keel record decision --safety-change --from d0371.md."; }
    // RAN: cargo test --release -p keel-cli (411 pass); timed hook stop / guard / gate --fast with and without the receipt; keel validate .
    part gateAnswersFromItsReceiptImplementGateR1 : TestResult { :>> id = "3e931ff6-8ee2-4dd7-b455-57ee17cd2bc8"; :>> outcome = VerdictKind::pass; :>> judgedAgainst = "dd4d91fd8efd7d7d49e6b521aee9d4467e7b3d44"; :>> judgedAt = "2026-09-08T00:20:00-06:00"; :>> judgedBy = "claudeOpus5"; }
    verification gateAnswersFromItsReceiptReviewGate : Test { :>> id = "8b7abb49-001e-490e-afac-a585747103f2"; :>> title = "Sprint 601 review gate — three passes per D0172"; :>> createdAt = "2026-09-07"; :>> createdBy = "claudeOpus5"; :>> method = VerificationMethod::inspect; :>> procedureText = "THREE QUESTIONS (D0172). Can a receipt answer over a changed input? Every input a guard reads is in the key by argument, not by list: HEAD for unmodified tracked files, git's own status for the rest with each path's facts, the two .keel/ directories left out are the hooks' own ledger (read by no guard) and binaries (covered by the build id), and the wall clock is read by no guard (grep). A change the digest cannot see is caught by the before/after key; a change it cannot resolve is caught by the two-second bar. Is the output the same? Identical guard stdout plus one line; hook stop silent either way; gate --fast prints its clean line with the receipt's age. What is NOT claimed: that the receipt speeds anything on CI (no .keel/ there, by design); that the first boundary after an edit is faster (it is not, and does not write); that `keel status`, `keel suite` or `reverify` read it (they do not)."; }
    // RAN: cargo test --release -p keel-cli (411 pass); timed hook stop / guard / gate --fast with and without the receipt; keel validate .
    part gateAnswersFromItsReceiptReviewGateR1 : TestResult { :>> id = "c645b570-1892-4d81-b63b-625288e4131e"; :>> outcome = VerdictKind::pass; :>> judgedAgainst = "dd4d91fd8efd7d7d49e6b521aee9d4467e7b3d44"; :>> judgedAt = "2026-09-08T00:20:00-06:00"; :>> judgedBy = "claudeOpus5"; }
    verification gateAnswersFromItsReceiptCloseOutGate : Test { :>> id = "4ae32708-527d-434e-a951-2bc107afaa2d"; :>> title = "Sprint 601 closeOut gate (autonomous, D0049)"; :>> createdAt = "2026-09-07"; :>> createdBy = "claudeOpus5"; :>> method = VerificationMethod::inspect; :>> procedureText = "CLOSED. Idle turn boundary 5.2-5.4 s to 0.2-0.3 s; `keel guard` 5.1 s to 0.2 s and the fast gate 0.68 s to 0.2 s when nothing has moved. D0371 recorded as a #SafetyChange and awaits the human's word; the sprint's work is co-committed with it as the keystone lock requires. The after number is under dcHookDaemonOnlyIfTheReceiptIsNotEnough's 1 s bar, which that item's judgment reads next."; }
    // RAN: cargo test --release -p keel-cli (411 pass); timed hook stop / guard / gate --fast with and without the receipt; keel validate .
    part gateAnswersFromItsReceiptCloseOutGateR1 : TestResult { :>> id = "892ed696-ffd1-482a-8359-4783a14e426b"; :>> outcome = VerdictKind::pass; :>> judgedAgainst = "dd4d91fd8efd7d7d49e6b521aee9d4467e7b3d44"; :>> judgedAt = "2026-09-08T00:20:00-06:00"; :>> judgedBy = "claudeOpus5"; }
    verification gateAnswersFromItsReceiptRetroGate : Test { :>> id = "98907740-a8f8-45a8-9afb-e3a964d9050a"; :>> title = "Sprint 601 retro gate (autonomous, D0049)"; :>> createdAt = "2026-09-07"; :>> createdBy = "claudeOpus5"; :>> method = VerificationMethod::analyze; :>> procedureText = "AVOIDABLE-ISSUE SCAN HELD. Two findings, both caught by existing controls before commit; no new item - already tracked: issue410 holds the git-spawn class and dcGateAnswersFromItsReceipt the receipt class. the fixture's receipt invalidated its own key because raw status bytes were hashed - found by the DoD's own test, corrected by hashing filtered entries (the correction is in the code, the class is dcGateAnswersFromItsReceipt's own); and the test helper spawned git raw - found by no_git_spawn_bypasses_the_counted_constructor (issue410's control), which is the control doing what D0047 asks. One measurement finding kept for rank 6: idle hook stop is now 0.2-0.3 s, below dcHookDaemonOnlyIfTheReceiptIsNotEnough's bar, so that item is judged moot on this number rather than built."; }
    // RAN: cargo test --release -p keel-cli (411 pass); timed hook stop / guard / gate --fast with and without the receipt; keel validate .
    part gateAnswersFromItsReceiptRetroGateR1 : TestResult { :>> id = "c05e4a03-1e72-4a6f-abf5-41424020264a"; :>> outcome = VerdictKind::pass; :>> judgedAgainst = "dd4d91fd8efd7d7d49e6b521aee9d4467e7b3d44"; :>> judgedAt = "2026-09-08T00:20:00-06:00"; :>> judgedBy = "claudeOpus5"; }
}
