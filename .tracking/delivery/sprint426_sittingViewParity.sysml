// ProjectDeliveryS426 — Sprint 426: authority-queue and sitting-coverage now compute the human's review debt from ONE grandfather basis (issue227, the panel's High finding). EXECUTE. 1 pts.
package ProjectDeliveryS426 {
    private import EngineElement::*;
    private import EngineWork::*;
    private import EngineVerification::*;
    private import EngineRelationships::*;

    #CharteredBy dependency from sittingViewParityStory to d0187;

    part sittingViewParityStory : Story {
        :>> id = "14bf9011-5ce4-4bda-839b-26da9ca35547";
        :>> title = "Sprint 426: one obligation, one answer (1 pts)";
        :>> createdAt = "2026-08-23"; :>> createdBy = "claudeFable5"; :>> kind = WorkKind::code; :>> priority = WorkPriority::p0; :>> owner = "claudeFable5"; :>> estimatedPoints = 1;
    }

    action def DeliveryRunS426 {
        action storySittingViewParity;
        verification storySittingViewParityDoD : Test { :>> id = "40fff09a-bcff-4e41-ad06-a36ac17849fa"; :>> method = VerificationMethod::test; :>> procedureText = "DELIVERED: dcSittingViewParity (resolves issue227, the process-value panel's High finding, verified live before charter). THE DEFECT: authority-queue grandfathered sitting reviews on the D0073 in-force DATE while sitting-coverage grandfathers on the D0155 human attestation (present-at-introduction-commit) - two computed views told the human two different sizes of their own duty (279-escalated-65-days vs due-6), the exact dual-computation class D0018 forbids, in the pair of views that size the single mandatory human gate. THE FIX: authority-queue consumes the same crate::govern::grandfathered_under(root, SITTING_DECISION) basis, structurally shared rather than duplicated; the grandfathered count is excluded from due but REPORTED in the row's note (never hidden); the escalation clock starts from the oldest DUE item, so a 65-day-old grandfathered sprint can no longer keep the queue permanently escalated. ALSO: the two decision-gated frontier items (dcConfirmationRecordDelegation on D0198, dcOversightRedesign on D0200) gained their #DependsOn edges, so the blocked-on-acceptance mechanism computes their state instead of the convener remembering it. VERIFIED: both views read back due=7 (the same population, sprints 419-425 accrued); authority-queue reads escalated=false with waitingDays=0 from the oldest due item; the note names the shared basis and cites issue227; full suite 229 green, clippy clean."; }
        part storySittingViewParityDoDR1 : TestResult { :>> id = "f449fad7-dafa-4211-a5cf-d5381118c7d7"; :>> outcome = VerdictKind::pass; :>> judgedAgainst = "55d1381fd9a618573ad73c204260e19ca706e139"; :>> judgedAt = "2026-08-22"; :>> judgedBy = "claudeFable5"; }
    }

    verification sittingViewParityRefineGate : Test { :>> id = "6afe2af4-6a1e-420f-9fe6-8b8dafda1f26"; :>> title = "Sprint 426 refine gate (DoR)"; :>> createdAt = "2026-08-23"; :>> createdBy = "claudeFable5"; :>> method = VerificationMethod::inspect; :>> procedureText = "DoR. Resolves the panel's only High finding, chartered same-day. In scope: the shared grandfather basis, the honest note, the escalation-clock fix, the two missing #DependsOn edges. 1 point."; }
    part sittingViewParityRefineGateR1 : TestResult { :>> id = "b244cbe6-ce9e-455b-a840-a18ba81bccaa"; :>> outcome = VerdictKind::pass; :>> judgedAgainst = "55d1381fd9a618573ad73c204260e19ca706e139"; :>> judgedAt = "2026-08-22"; :>> judgedBy = "claudeFable5"; }
    verification sittingViewParityStandupGate : Test { :>> id = "1adc4b1b-c257-40f6-873e-2df1647c2c58"; :>> title = "Sprint 426 standup gate"; :>> createdAt = "2026-08-23"; :>> createdBy = "claudeFable5"; :>> method = VerificationMethod::inspect; :>> procedureText = "Approach: share the COMPUTATION (both views call the same govern::grandfathered_under with the same decision constant), never re-state the policy in a second place - the same structural cure applied to the enforcement contract in sprint 423. No blockers."; }
    part sittingViewParityStandupGateR1 : TestResult { :>> id = "3a9f26c8-580d-49e5-861c-10c1bc3f4d7d"; :>> outcome = VerdictKind::pass; :>> judgedAgainst = "55d1381fd9a618573ad73c204260e19ca706e139"; :>> judgedAt = "2026-08-22"; :>> judgedBy = "claudeFable5"; }
    verification sittingViewParityImplementGate : Test { :>> id = "dee93e14-7e99-4a9b-b0a1-76d1e11e2f9b"; :>> title = "Sprint 426 implement gate"; :>> createdAt = "2026-08-23"; :>> createdBy = "claudeFable5"; :>> method = VerificationMethod::test; :>> procedureText = "Verified by running: keel authority-queue . and keel sitting-coverage . read back the SAME due count (7) where they previously read 279 vs 6; the authority row reports 273 grandfathered-within-population beside the due count and defers the full 313 census to sitting-coverage (different populations - authority-queue first excludes pre-D0073 sprints - both stated, neither hidden); escalated flipped false because the clock now starts at the oldest DUE item; cargo test 229 pass, clippy pedantic+nursery clean."; }
    part sittingViewParityImplementGateR1 : TestResult { :>> id = "1707963e-f473-402b-ae6d-6ba1f472fcfd"; :>> outcome = VerdictKind::pass; :>> judgedAgainst = "55d1381fd9a618573ad73c204260e19ca706e139"; :>> judgedAt = "2026-08-22"; :>> judgedBy = "claudeFable5"; }
    verification sittingViewParityReviewGate : Test { :>> id = "809afcd3-0b18-4af6-9505-f90038f95c26"; :>> title = "Sprint 426 review gate — three passes per D0172"; :>> createdAt = "2026-08-23"; :>> createdBy = "claudeFable5"; :>> method = VerificationMethod::inspect; :>> procedureText = "PASS 1, CLAIMS: the before numbers (279 vs 6) are the panel's, verified live by the convener before this sprint existed; the after numbers are this session's read-backs. PASS 2, BOUNDARY: the two views still report different GRANDFATHERED totals (273 vs 313) because their base populations differ (D0073-onward vs all sprints) - that is stated in the row note rather than unified, because unifying the populations would change what authority-queue is FOR; a reviewer who wants one census should say so. PASS 3, OWN DIFF: no test pins the parity structurally - the shared helper call is the control, and a divergence would need someone to re-duplicate the basis; noted as the residual rather than papered over with a weak string-match test. WHAT A REVIEWER SHOULD ATTACK: whether escalated=false after the fix understates a real debt - the 7 due sittings are all from TODAY, so the flip is correct on this tree, but the first sitting the human skips will start the clock honestly."; }
    part sittingViewParityReviewGateR1 : TestResult { :>> id = "99b58148-8cd3-4f28-98a3-208f892d5f4b"; :>> outcome = VerdictKind::pass; :>> judgedAgainst = "55d1381fd9a618573ad73c204260e19ca706e139"; :>> judgedAt = "2026-08-22"; :>> judgedBy = "claudeFable5"; }
    verification sittingViewParityCloseOutGate : Test { :>> id = "e2060e65-5ea8-4c9a-95a4-0c5987d93f16"; :>> title = "Sprint 426 closeOut gate (autonomous, D0049)"; :>> createdAt = "2026-08-23"; :>> createdBy = "claudeFable5"; :>> method = VerificationMethod::inspect; :>> procedureText = "Autonomous closeOut (D0049). issue227 resolves; the frontier's decision-gated items now compute their blocked state; validate + all 46 guards green."; }
    part sittingViewParityCloseOutGateR1 : TestResult { :>> id = "48544bfa-2e4d-4205-8cf7-dd553e7c558d"; :>> outcome = VerdictKind::pass; :>> judgedAgainst = "55d1381fd9a618573ad73c204260e19ca706e139"; :>> judgedAt = "2026-08-22"; :>> judgedBy = "claudeFable5"; }
    verification sittingViewParityRetroGate : Test { :>> id = "b22c7b14-60cc-4997-865f-b909856b73dd"; :>> title = "Sprint 426 retro gate (autonomous, D0049)"; :>> createdAt = "2026-08-23"; :>> createdBy = "claudeFable5"; :>> method = VerificationMethod::analyze; :>> procedureText = "Autonomous retro (D0049). AVOIDABLE-ISSUE SCAN under rcRecurrence: second instance this week of the duplicated-policy class (sprint 423's enforcement prose, now a duplicated grandfather basis) - the practice that kills the class is SHARE THE COMPUTATION, and both fixes applied it; a future guard could grep for second callers re-deriving what govern:: exposes, noted for the control-evaluation sprint. WELL: the panel-to-fix latency for its High finding was under three hours, with the fix READ BACK against the exact numbers the panel cited. Estimate 1 pt, delivered 1."; }
    part sittingViewParityRetroGateR1 : TestResult { :>> id = "61db8c8e-5eab-47b8-a9b5-48d7db7cf079"; :>> outcome = VerdictKind::pass; :>> judgedAgainst = "55d1381fd9a618573ad73c204260e19ca706e139"; :>> judgedAt = "2026-08-22"; :>> judgedBy = "claudeFable5"; }
}
