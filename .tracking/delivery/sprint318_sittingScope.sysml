// ProjectDeliveryS318 — Sprint 318: the sitting-review obligation becomes a queue somebody can work.
// CHANGE (§3a) under D0155. 3 pts.
package ProjectDeliveryS318 {
    private import EngineElement::*;
    private import EngineWork::*;
    private import EngineVerification::*;
    private import EngineRelationships::*;

    #CharteredBy dependency from sittingScopeStory to d0155;

    part sittingScopeStory : Story {
        :>> id = "0d800390-0814-6390-9b3e-000000300390";
        :>> title = "Sprint 318: one grandfather line for sitting review (3 pts)";
        :>> createdAt = "2026-08-17"; :>> createdBy = "claudeOpus5"; :>> kind = WorkKind::decision; :>> priority = WorkPriority::p0; :>> owner = "claudeOpus5"; :>> estimatedPoints = 3;
    }

    action def DeliveryRunS318 {
        action storySittingScope;
        verification storySittingScopeDoD : Test { :>> id = "0d800391-0814-6391-9b3e-000000300391"; :>> method = VerificationMethod::test; :>> procedureText = "Resolves issue135 by applying D0155. `sitting-coverage` now reports `due` (uncovered AND not present at D0155's introduction commit), `grandfathered_unreviewed`, `due_sprints` and `grandfatherBasis`, while `uncovered` keeps its existing meaning so nothing that read the old field is silently redefined. The obligation counter reads `due` and its issue135 caveat is removed, because the number is defensible now and a caveat on a defensible number is noise. READ BACK FROM THE COMPUTED VIEW, not from the change: 317 sprints, 4 covered, 313 uncovered, due 0, grandfathered_unreviewed 313, with the basis naming the mechanism. THIS SPRINT'S OWN STORY POSTDATES THE LINE BY CONSTRUCTION — the Decision and the code were committed WITHOUT this record so that the sprint doing the work could not grandfather itself, and `due` therefore reads 1 at HEAD: the queue's first live item is this sitting. clippy clean; 226 tests; validate 345 clean; check-engine clean; 33 guards green."; }
        part storySittingScopeDoDR1 : TestResult { :>> id = "0d800392-0814-6392-9b3e-000000300392"; :>> outcome = VerdictKind::pass; :>> judgedAgainst = "ac14d78"; :>> judgedAt = "2026-08-17"; :>> judgedBy = "claudeOpus5"; }
    }

    verification ssRefineGate : Test { :>> id = "0d800393-0814-6393-9b3e-000000300393"; :>> title = "Sprint 318 refine gate (DoR)"; :>> createdAt = "2026-08-17"; :>> createdBy = "claudeOpus5"; :>> method = VerificationMethod::inspect; :>> procedureText = "DoR. The last item on the ready frontier, and it needed a human because it waives a HUMAN obligation — an AI actor cannot decide that 313 sittings will never receive the review D0049 requires. Before asking, I did the part that did not depend on the answer: measured the split (317 sprints, 4 covered, 313 uncovered, 145 before the convention's first review and 168 after) and TESTED THE DoD'S OWN PROPOSED BOUNDARY, which failed — grandfathering at the earliest actually-attested sprint leaves 168 live. That finding is what made the question worth the human's time instead of a request to choose between options I had not checked. estimatedPoints=3."; }
    part ssRefineGateR1 : TestResult { :>> id = "0d800394-0814-6394-9b3e-000000300394"; :>> outcome = VerdictKind::pass; :>> judgedAgainst = "ac14d78"; :>> judgedAt = "2026-08-17"; :>> judgedBy = "claudeOpus5"; }

    verification ssStandupGate : Test { :>> id = "0d800395-0814-6395-9b3e-000000300395"; :>> title = "Sprint 318 standup gate"; :>> createdAt = "2026-08-17"; :>> createdBy = "claudeOpus5"; :>> method = VerificationMethod::inspect; :>> procedureText = "Approach: reuse `govern::grandfathered_under` rather than introduce a boundary of my own — D0079 and D0080 already draw forward-only lines this way, so the change is a caller and not a mechanism, and the set is derived from git rather than from a date I picked. Add the new fields alongside `uncovered` rather than redefining it. Commit the Decision before the sprint record so the sprint cannot grandfather itself. No blockers."; }
    part ssStandupGateR1 : TestResult { :>> id = "0d800396-0814-6396-9b3e-000000300396"; :>> outcome = VerdictKind::pass; :>> judgedAgainst = "ac14d78"; :>> judgedAt = "2026-08-17"; :>> judgedBy = "claudeOpus5"; }

    verification ssImplementGate : Test { :>> id = "0d800397-0814-6397-9b3e-000000300397"; :>> title = "Sprint 318 implement gate"; :>> createdAt = "2026-08-17"; :>> createdBy = "claudeOpus5"; :>> method = VerificationMethod::test; :>> procedureText = "THE UNRESOLVED-BOUNDARY BRANCH INVERTS THE ESTABLISHED STANCE, deliberately, and that is the design decision inside this change. Where a git failure makes a GATE grandfather everything (D0050) so it never spuriously blocks, an obligation surface whose line cannot be resolved reports EVERY uncovered sitting as due and says why. A gate failing open is cautious; an obligation surface reporting nothing owed when it does not know is exactly the misleading-quiet N-C2 exists to forbid — and it is the more dangerous default here because the reader's whole reason for looking is to learn whether anything is owed. Covered by `an_unresolved_grandfather_line_reports_every_sitting_as_due`, which builds a root with no D0155 introduction commit and asserts due==uncovered, grandfathered==0, and that the basis SAYS it could not scope."; }
    part ssImplementGateR1 : TestResult { :>> id = "0d800398-0814-6398-9b3e-000000300398"; :>> outcome = VerdictKind::pass; :>> judgedAgainst = "ac14d78"; :>> judgedAt = "2026-08-17"; :>> judgedBy = "claudeOpus5"; }

    verification ssReviewGate : Test { :>> id = "0d800399-0814-6399-9b3e-000000300399"; :>> title = "Sprint 318 review gate"; :>> createdAt = "2026-08-17"; :>> createdBy = "claudeOpus5"; :>> method = VerificationMethod::inspect; :>> procedureText = "Reviewed. THE COST IS WRITTEN DOWN WHERE IT CANNOT BE MISTAKEN FOR A FIX: 313 sittings of this repository's history will never receive the per-sitting review D0049 requires, no later computation can recover it, and the figure stays on the view under its own name so a future reader cannot conclude the history was reviewed. What was bought is a queue that measures the live obligation — from here an unreviewed sprint appears immediately as one owed item instead of vanishing into a crowd of 313. The self-grandfathering trap was the one real hazard in applying it, since the mechanism grandfathers whatever exists at the Decision's commit, and a sprint record committed alongside its own Decision would silently exempt itself; splitting the commits closes it and `due` reads 1 at HEAD, which is the honest answer."; }
    part ssReviewGateR1 : TestResult { :>> id = "0d80039a-0814-639a-9b3e-00000030039a"; :>> outcome = VerdictKind::pass; :>> judgedAgainst = "ac14d78"; :>> judgedAt = "2026-08-17"; :>> judgedBy = "claudeOpus5"; }

    verification ssCloseOutGate : Test { :>> id = "0d80039b-0814-639b-9b3e-00000030039b"; :>> title = "Sprint 318 closeOut gate (autonomous, D0049)"; :>> createdAt = "2026-08-17"; :>> createdBy = "claudeOpus5"; :>> method = VerificationMethod::inspect; :>> procedureText = "Autonomous closeOut (D0049). issue135 resolved via #Resolves from d0155; dcSittingObligationScope's DoD result recorded. Doc-sync rode the change: usage.md's sitting-coverage row now states the due/grandfathered split and the fail-loud stance. Two issues remain open and both are the human's to answer rather than mine — issue132 (a Need statement asserting multi-user scope, whose owner is the human) and issue133 (the catch-all-as-root argument arm elsewhere in the subcommand parsers). clippy clean; 226 tests; validate 345 clean; check-engine clean; 33 guards green."; }
    part ssCloseOutGateR1 : TestResult { :>> id = "0d80039c-0814-639c-9b3e-00000030039c"; :>> outcome = VerdictKind::pass; :>> judgedAgainst = "ac14d78"; :>> judgedAt = "2026-08-17"; :>> judgedBy = "claudeOpus5"; }

    verification ssRetroGate : Test { :>> id = "0d80039d-0814-639d-9b3e-00000030039d"; :>> title = "Sprint 318 retro gate (autonomous, D0049)"; :>> createdAt = "2026-08-17"; :>> createdBy = "claudeOpus5"; :>> method = VerificationMethod::analyze; :>> procedureText = "Autonomous retro (D0049) under D0131's retroTrack. WELL: (1) testing the DoD's own proposed remedy BEFORE proposing it is what made this change correct — the item said to grandfather at the convention's start, and that leaves 168 sittings live, so implementing what the item asked for would have produced a queue nobody could work and a Decision that read as if the problem were solved; (2) the question went to the human with the measurement attached rather than as a menu, which is the difference between asking them to decide and asking them to guess; (3) the self-grandfathering trap was anticipated and closed by commit ORDER rather than by a note asking a future reader to be careful. AVOIDABLE-ISSUE: none this sprint — no source file was corrupted, no stale binary was consulted, and the gate ran before the commit rather than after. NOTE FOR THE HUMAN, not an item: `due` reads 1 at HEAD and that item is this sitting, so the very first thing the new queue asks for is a review of the change that created it. Estimate 3 pts, delivered."; }
    part ssRetroGateR1 : TestResult { :>> id = "0d80039e-0814-639e-9b3e-00000030039e"; :>> outcome = VerdictKind::pass; :>> judgedAgainst = "ac14d78"; :>> judgedAt = "2026-08-17"; :>> judgedBy = "claudeOpus5"; }
}
