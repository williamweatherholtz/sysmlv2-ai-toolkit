// ProjectDeliveryS408 — Sprint 408: D0190 delivered: one declared version identity, parity warned at every gate entry point - both sprint-394 FAILs flipped on probes. EXECUTE. 2 pts.
package ProjectDeliveryS408 {
    private import EngineElement::*;
    private import EngineWork::*;
    private import EngineVerification::*;
    private import EngineRelationships::*;

    #CharteredBy dependency from versionIdentityStory to d0190;

    part versionIdentityStory : Story {
        :>> id = "ff6c1100-e838-4fda-8798-f54c46d35a19";
        :>> title = "Sprint 408: version identity and parity (2 pts)";
        :>> createdAt = "2026-08-22"; :>> createdBy = "claudeFable5"; :>> kind = WorkKind::code; :>> priority = WorkPriority::p0; :>> owner = "claudeFable5"; :>> estimatedPoints = 2;
    }

    action def DeliveryRunS408 {
        action storyVersionIdentity;
        verification storyVersionIdentityDoD : Test { :>> id = "3a23e81d-98c4-493b-8a9a-3e149844067f"; :>> method = VerificationMethod::test; :>> procedureText = "DELIVERED (D0190, accepted on their 'approved. keep the momentum going'): (1) engine-version.toml - the declared version this on-disk engine's checks are defined against; keel init stamps it, keel migrate re-stamps it on a completed apply, and the SELF-BUILD's own declaration is authored at 0.2.3. DESIGN RECONCILIATION, stated in both files: migrate's recorded no-stamp rule still holds - migrate derives its vintage from the TREE and never reads this file; the declaration exists ONLY for the parity warning, so the two designs answer different questions (which transforms apply vs which binary's checks govern). (2) The parity warning at all three gate entry points (keel validate, keel guard, hook stop): advisory, names keel migrate, never blocks (skew is not dishonest state, D0098); VERIFIED BOTH WAYS live - a deliberately stale 0.1.0 declaration fired the warning at validate, the restored 0.2.3 silenced it. (3) The binary version is the ONE declared semver: keel --version and /api/version report the API contract (2.0.0) and claude-surface versions as DERIVED facts beside it (probed live: api 2.0.0 / binary 0.2.3 / surface 0.2.3), with breaking API changes recorded in release Decisions rather than versioned apart. (4) Both sprint-394 verification FAILs flipped exactly per the decision's clause 4: srDcEngineVersionParityV1R2 and srRelSemverReconciledV1R2 record pass with the probe evidence. engine-version.toml joined the process-def guard's instance-data exemptions (machine-stamped, like unit-ids)."; }
        part storyVersionIdentityDoDR1 : TestResult { :>> id = "4475538a-98d7-4a6b-b54c-985200105405"; :>> outcome = VerdictKind::pass; :>> judgedAgainst = "8d603de"; :>> judgedAt = "2026-08-22"; :>> judgedBy = "claudeFable5"; }
    }

    verification versionIdentityRefineGate : Test { :>> id = "3124966b-bed7-446f-8c4d-e0bb36270914"; :>> title = "Sprint 408 refine gate (DoR)"; :>> createdAt = "2026-08-22"; :>> createdBy = "claudeFable5"; :>> method = VerificationMethod::inspect; :>> procedureText = "DoR. Chartered by d0190, accepted this session. The one open design question (D0190's stamp vs migrate's recorded no-stamp rule) was resolved by scoping, not by overruling either: the stamp is read by the warning alone. 2 points."; }
    part versionIdentityRefineGateR1 : TestResult { :>> id = "11c55a6e-3ebc-40ca-bdab-e8be402ab8f3"; :>> outcome = VerdictKind::pass; :>> judgedAgainst = "8d603de"; :>> judgedAt = "2026-08-22"; :>> judgedBy = "claudeFable5"; }
    verification versionIdentityStandupGate : Test { :>> id = "0d126dd3-0be3-4c6d-b6a5-84710d45dd16"; :>> title = "Sprint 408 standup gate"; :>> createdAt = "2026-08-22"; :>> createdBy = "claudeFable5"; :>> method = VerificationMethod::inspect; :>> procedureText = "Approach: helper + three call sites, init/migrate stamping, reporting surfaces, then verify the warning in BOTH directions before recording anything. No blockers."; }
    part versionIdentityStandupGateR1 : TestResult { :>> id = "87116ae8-6f74-41f2-a0bd-9d8ba0b68e74"; :>> outcome = VerdictKind::pass; :>> judgedAgainst = "8d603de"; :>> judgedAt = "2026-08-22"; :>> judgedBy = "claudeFable5"; }
    verification versionIdentityImplementGate : Test { :>> id = "2470fa06-2de1-4ec2-adcc-7bd389e13e53"; :>> title = "Sprint 408 implement gate"; :>> createdAt = "2026-08-22"; :>> createdBy = "claudeFable5"; :>> method = VerificationMethod::test; :>> procedureText = "Verified by running: the skew warning fired against a deliberately stale declaration and silenced against the matching one (both transcripts in-session); keel --version prints all three identities plus the declaration state; /api/version serves binaryVersion + surfaceVersion beside apiVersion (probed on the restarted console); cargo test 10 suites 0 failures; clippy pedantic+nursery clean; validate 446 clean."; }
    part versionIdentityImplementGateR1 : TestResult { :>> id = "b6aed019-f8ed-4cd7-b579-32e7310f2061"; :>> outcome = VerdictKind::pass; :>> judgedAgainst = "8d603de"; :>> judgedAt = "2026-08-22"; :>> judgedBy = "claudeFable5"; }
    verification versionIdentityReviewGate : Test { :>> id = "b978bbcc-4ce4-4a8e-9dee-a443d87aab91"; :>> title = "Sprint 408 review gate — three passes per D0172"; :>> createdAt = "2026-08-22"; :>> createdBy = "claudeFable5"; :>> method = VerificationMethod::inspect; :>> procedureText = "PASS 1, CLAIMS: every behavior claim has a both-directions probe from this session. PASS 2, BOUNDARY: the migrate-vs-stamp tension was the real design risk - the record resolves it by stating each mechanism's single reader (migrate reads the tree; the warning reads the stamp) IN both source files, so the next reader meets the reconciliation where the tension lives. PASS 3, OWN DIFF: the D0070 marker was added to d0190 BEFORE the landing attempt this time - the sprint-395/407 refusal class finally pre-empted rather than hit (its root fix is chartered as dcRecordDecisionMarkerFlag). WHAT A REVIEWER SHOULD ATTACK: the stamp is trusted at face value by the warning - a project that hand-edits engine-version.toml to match its binary silences the warning without migrating; the honest counter is that the same hand can delete the file entirely (pre-D0190 silent state), so the control is against ACCIDENT, not adversary, like the whole K3 class."; }
    part versionIdentityReviewGateR1 : TestResult { :>> id = "c3bb8086-0ce5-48fa-b307-194dcda73b36"; :>> outcome = VerdictKind::pass; :>> judgedAgainst = "8d603de"; :>> judgedAt = "2026-08-22"; :>> judgedBy = "claudeFable5"; }
    verification versionIdentityCloseOutGate : Test { :>> id = "2d76501e-b6df-4cb8-9d43-fdd9eaa278c1"; :>> title = "Sprint 408 closeOut gate (autonomous, D0049)"; :>> createdAt = "2026-08-22"; :>> createdBy = "claudeFable5"; :>> method = VerificationMethod::inspect; :>> procedureText = "Autonomous closeOut (D0049). Both R2 flips recorded with probe citations; the console restarted on the new binary; validate + all 45 guards green."; }
    part versionIdentityCloseOutGateR1 : TestResult { :>> id = "d85bf1e3-7afc-48e2-99c0-8114b83e3d9e"; :>> outcome = VerdictKind::pass; :>> judgedAgainst = "8d603de"; :>> judgedAt = "2026-08-22"; :>> judgedBy = "claudeFable5"; }
    verification versionIdentityRetroGate : Test { :>> id = "15487a3d-97a8-4ca2-905c-00e15f68c7dd"; :>> title = "Sprint 408 retro gate (autonomous, D0049)"; :>> createdAt = "2026-08-22"; :>> createdBy = "claudeFable5"; :>> method = VerificationMethod::analyze; :>> procedureText = "Autonomous retro (D0049). AVOIDABLE-ISSUE SCAN under rcRecurrence: the D0070-marker refusal class did NOT recur - pre-empted by adding the marker up front, and its root fix is chartered (issue213/dcRecordDecisionMarkerFlag), so the class closes at the tool. WELL: verifying the warning in both directions caught nothing this time but is the cheap discipline that caught issue202's class before - kept. Estimate 2 pts, delivered 2."; }
    part versionIdentityRetroGateR1 : TestResult { :>> id = "f5f107ce-0df7-4a2a-ba68-47abb25a580b"; :>> outcome = VerdictKind::pass; :>> judgedAgainst = "8d603de"; :>> judgedAt = "2026-08-22"; :>> judgedBy = "claudeFable5"; }
}
