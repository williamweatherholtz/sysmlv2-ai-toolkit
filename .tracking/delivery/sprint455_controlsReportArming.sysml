// ProjectDeliveryS455 — Sprint 455: the control inventory says whether each control can actually FIRE, not only whether it is declared (D0217, the third surface from issue240). EXECUTE. 2 pts.
package ProjectDeliveryS455 {
    private import EngineElement::*;
    private import EngineWork::*;
    private import EngineVerification::*;
    private import EngineRelationships::*;

    #CharteredBy dependency from controlsReportArmingStory to d0217;

    part controlsReportArmingStory : Story {
        :>> id = "89c354ef-d43d-405f-a5bc-47e18296caa1";
        :>> title = "Sprint 455: declared is not armed (2 pts)";
        :>> createdAt = "2026-08-24"; :>> createdBy = "claudeFable5"; :>> kind = WorkKind::code; :>> priority = WorkPriority::p0; :>> owner = "claudeFable5"; :>> estimatedPoints = 2;
    }

    action def DeliveryRunS455 {
        action storyControlsReportArming;
        verification storyControlsReportArmingDoD : Test { :>> id = "3666ec3c-6b90-42a5-b856-388d0d15666e"; :>> method = VerificationMethod::test; :>> procedureText = "DELIVERED: dcControlsReportArming (closes the residual STATED at issue240 rather than silently claimed). THE DEFECT: keel controls (D0195) computes the two-way hazard/control diff from typed EDGES, so it answers whether a control is DECLARED against a hazard and structurally CANNOT answer whether that control can fire. During issue240 core.hooksPath pointed at a null device, the pre-commit gate could not run at all, and controls reported uncoveredHazards as empty - truthful on the question it asked, misleading on the question a reader has. It was the third of three surfaces reporting an unreachable control as healthy; orient and hardening were fixed by dcArmedNotDeclared and this one was DEFERRED and tracked, because it needed a modeling decision rather than a predicate swap. THE FIX: arming is declared per control in a new contract, .engine/contracts/control-arming.toml - checkable = true with a named probe the binary implements, or checkable = false with a stated reason, and NO entry reads UNDECLARED so silence is a gap rather than consent. The view emits a controlArming row per control (ARMED, NOT-ARMED carrying the probe reason, not-machine-checkable carrying the declared reason, UNDECLARED, or PROBE-MISSING when a declared probe is not implemented - reported rather than treated as armed) plus ONE new gap class, deliberately the only decidable one: hazardsWithADisarmedControl. Eight of nine controls are honestly not machine-checkable - a CI job's arming and a remote's branch protection are not observable from a working tree - and saying so with a reason is the N-C2 discipline rather than a probe that fails open. A frozen-schema armed field was rejected because it would put a runtime fact in an authored one; declaring the BINDING as data and computing the STATE keeps the authored layer irreducible, and follows the D0184 rule-owners precedent so a downstream project declares its own controls without a fork. VERIFIED by probe reproducing the exact issue240 state (hooksPath = nul with the contract present): ctlCommitGate reads NOT-ARMED with the reason, uncoveredHazards remains empty - correctly, since declaration did not change - and hazardsWithADisarmedControl names ehz2 and ehz4, the two hazards whose covering control could not fire; with the contract absent every control reads UNDECLARED. On this tree ctlCommitGate is ARMED and the gap class is empty."; }
        part storyControlsReportArmingDoDR1 : TestResult { :>> id = "54dc0f8a-f4ed-41dc-b4d5-f4a91df11804"; :>> outcome = VerdictKind::pass; :>> judgedAgainst = "9ca8eeb2afb111f7da277d7cd72bdb531df8c917"; :>> judgedAt = "2026-08-24"; :>> judgedBy = "claudeFable5"; }
    }

    verification controlsReportArmingRefineGate : Test { :>> id = "47242a47-2ebe-40de-93da-8e0d44e173b8"; :>> title = "Sprint 455 refine gate (DoR)"; :>> createdAt = "2026-08-24"; :>> createdBy = "claudeFable5"; :>> method = VerificationMethod::inspect; :>> procedureText = "DoR. Closes the dcControlsReportArming residual from issue240 - the one surface deferred at the time because it needed a modeling decision. Scope: declare arming as data, report it beside declaration, add the single decidable gap class. 2 points."; }
    part controlsReportArmingRefineGateR1 : TestResult { :>> id = "033d1c7d-da3e-452a-85ac-a10368bc11a8"; :>> outcome = VerdictKind::pass; :>> judgedAgainst = "9ca8eeb2afb111f7da277d7cd72bdb531df8c917"; :>> judgedAt = "2026-08-24"; :>> judgedBy = "claudeFable5"; }
    verification controlsReportArmingStandupGate : Test { :>> id = "46b0a38b-e31f-4f73-8c0b-52e86cdc4d61"; :>> title = "Sprint 455 standup gate"; :>> createdAt = "2026-08-24"; :>> createdBy = "claudeFable5"; :>> method = VerificationMethod::inspect; :>> procedureText = "Approach: declare the BINDING as data and compute the STATE - a boolean on the control would need frozen schema/core AND would put a runtime fact in an authored one, which is the dual truth the engine forbids. Report not-machine-checkable WITH its reason rather than omitting those controls, because the absence of a check must be distinguishable from a passing check. Add exactly one gap class and make it the decidable one. The contract lives under .engine/contracts/ which the keystone locks, so D0217 co-commits. No blockers."; }
    part controlsReportArmingStandupGateR1 : TestResult { :>> id = "839145e6-b91d-4c95-8ce5-5b0e4c9824a5"; :>> outcome = VerdictKind::pass; :>> judgedAgainst = "9ca8eeb2afb111f7da277d7cd72bdb531df8c917"; :>> judgedAt = "2026-08-24"; :>> judgedBy = "claudeFable5"; }
    verification controlsReportArmingImplementGate : Test { :>> id = "72cc9109-d4fa-40b6-ae46-af3f3eca4681"; :>> title = "Sprint 455 implement gate"; :>> createdAt = "2026-08-24"; :>> createdBy = "claudeFable5"; :>> method = VerificationMethod::test; :>> procedureText = "Verified by running the freshness-checked binary and by a probe built to be capable of failing: in a throwaway worktree at the issue240 state with the contract copied in, ctlCommitGate reads NOT-ARMED carrying the reason that core.hooksPath resolves to a non-directory so the gate CANNOT run, and hazardsWithADisarmedControl names ehz2 and ehz4 while uncoveredHazards stays empty; with the contract absent all nine controls read UNDECLARED. On the real tree ARMED and the gap empty. cargo clippy --workspace --all-targets -D warnings clean after restoring a doc comment my insertion had orphaned; full lib suite 253 pass; validate 506 + all 49 guards + check-engine + rules green."; }
    part controlsReportArmingImplementGateR1 : TestResult { :>> id = "7ed4a58d-eefd-4958-9428-c66b48aae063"; :>> outcome = VerdictKind::pass; :>> judgedAgainst = "9ca8eeb2afb111f7da277d7cd72bdb531df8c917"; :>> judgedAt = "2026-08-24"; :>> judgedBy = "claudeFable5"; }
    verification controlsReportArmingReviewGate : Test { :>> id = "8f7ffbfd-5a96-4300-923d-a9d007ed8668"; :>> title = "Sprint 455 review gate — three passes per D0172"; :>> createdAt = "2026-08-24"; :>> createdBy = "claudeFable5"; :>> method = VerificationMethod::inspect; :>> procedureText = "PASS 1, CLAIMS: both probe outputs, the arming states and the named hazards are quoted read-backs. PASS 2, BOUNDARY: (i) only ONE probe exists (commit-gate reachability), so this closes the surface's honesty and not its coverage - eight controls report a reason for being uncheckable and a reader can contest any of those reasons, which is the point of writing them down; (ii) not-machine-checkable is never counted as armed and never as a gap, because counting it either way would be a claim the model cannot support; (iii) PROBE-MISSING exists so a declared probe name the binary does not implement reads as a defect rather than silently as armed. PASS 3, OWN DIFF: two findings against myself. First, I orphaned a doc comment by inserting helpers between it and its function - the identical mistake made in guards.rs an hour earlier, so the recurrence is mine and mechanical. Second and much worse, the probe itself DISARMED THE REAL REPOSITORY: a linked worktree shares the common .git/config, so setting core.hooksPath with -C inside the worktree rewrote the parent's config; that is recorded as issue249 and it settles issue240's origin, which I had previously described only as probably probe residue. WHAT A REVIEWER SHOULD ATTACK: the eight not-machine-checkable reasons individually - each is a judgment that something cannot be observed from a working tree, and at least ctlBranchProtection could be probed by an authenticated API call if a project accepted a view performing network I/O."; }
    part controlsReportArmingReviewGateR1 : TestResult { :>> id = "c9ebcc65-7fbe-471c-910c-86d04da3b2e4"; :>> outcome = VerdictKind::pass; :>> judgedAgainst = "9ca8eeb2afb111f7da277d7cd72bdb531df8c917"; :>> judgedAt = "2026-08-24"; :>> judgedBy = "claudeFable5"; }
    verification controlsReportArmingCloseOutGate : Test { :>> id = "19d449fb-b942-40ab-b597-a2013167b936"; :>> title = "Sprint 455 closeOut gate (autonomous, D0049)"; :>> createdAt = "2026-08-24"; :>> createdBy = "claudeFable5"; :>> method = VerificationMethod::inspect; :>> procedureText = "Autonomous closeOut (D0049). All three surfaces from issue240 now report reachability rather than declaration; issue249 records the worktree-config mechanism that caused it. validate + all 49 guards + check-engine + rules green. One chartered follow-on remains: dcNoFalseCleanRange."; }
    part controlsReportArmingCloseOutGateR1 : TestResult { :>> id = "1178c36c-72ca-46a0-8a4e-56e92c73c7ad"; :>> outcome = VerdictKind::pass; :>> judgedAgainst = "9ca8eeb2afb111f7da277d7cd72bdb531df8c917"; :>> judgedAt = "2026-08-24"; :>> judgedBy = "claudeFable5"; }
    verification controlsReportArmingRetroGate : Test { :>> id = "9f012133-eafb-4048-9768-9847902c25c3"; :>> title = "Sprint 455 retro gate (autonomous, D0049)"; :>> createdAt = "2026-08-24"; :>> createdBy = "claudeFable5"; :>> method = VerificationMethod::analyze; :>> procedureText = "Autonomous retro (D0049). AVOIDABLE-ISSUE SCAN under rcRecurrence: (1) THE finding of this sprint is that the detection control worked twice, both times on my own mistake: the conditional hooks test added for issue248 failed within a minute of my probe disarming the repo, so the state was caught by a check rather than by luck. That is the D0047 shape vindicated - do not try to prevent a methodology error by vigilance, detect the resulting STATE regardless of cause. (2) The probe-methodology error is now written down as issue249 rather than rediscovered a third time: a worktree shares .git/config, so a probe must use the per-command git -c override, which the audit-adherence probes did and this one did not. (3) The orphaned-doc-comment insertion error recurred within the hour from guards.rs to view/mod.rs; clippy catches it every time, so it costs a cycle rather than correctness. WELL: the deferral at issue240 was honest and was honoured - the residual was tracked, not forgotten, and it closed with a probe that demonstrates the difference between the old answer and the new one on the same tree. Estimate 2 pts, delivered 2."; }
    part controlsReportArmingRetroGateR1 : TestResult { :>> id = "888c9396-b122-4c75-bd4d-5246a29b8187"; :>> outcome = VerdictKind::pass; :>> judgedAgainst = "9ca8eeb2afb111f7da277d7cd72bdb531df8c917"; :>> judgedAt = "2026-08-24"; :>> judgedBy = "claudeFable5"; }
}
