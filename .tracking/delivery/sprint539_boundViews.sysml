// ProjectDeliveryS539 — Sprint 539: every advertised view is bound - receipted live, probed both ways, and a duplicate key found on the way. EXECUTE. 1 pt.
package ProjectDeliveryS539 {
    private import EngineElement::*;
    private import EngineWork::*;
    private import EngineVerification::*;
    private import EngineRelationships::*;

    #CharteredBy dependency from boundViewsStory to d0093;

    part boundViewsStory : Story {
        :>> id = "9451f74f-f87b-4b8f-a178-b34ed7f43850";
        :>> title = "Sprint 539: six advertised views served live with HTTP 200, the binding control failing by name when a binding is removed, and viewStatus stamped once (1 pt)";
        :>> createdAt = "2026-09-04"; :>> createdBy = "claudeOpus5"; :>> kind = WorkKind::code; :>> priority = WorkPriority::p0; :>> owner = "claudeOpus5"; :>> estimatedPoints = 1;
    }

    action def DeliveryRunS539 {
        action storyBoundViews;
        verification storyBoundViewsDoD : Test { :>> id = "9d382c6d-1124-4b5e-b277-bae0231d8421"; :>> method = VerificationMethod::test; :>> procedureText = "DELIVERED BACKLOG ITEMS: dcEveryAdvertisedViewIsBound (resolves issue285, and issue368 found on the way). The bindings and the two-sided control landed at e4e8ee8 on 2026-08-26 and were never recorded - unrecorded is not done. RECEIPTED NOW: a live server served all six advertised views with HTTP 200 and computed JSON; the control was mutated (one binding removed) and FAILED naming exactly that command, then restored and passed; it refuses an empty registry and an empty scrape. FOUND: two views stamped viewStatus twice; with_status now drops an inner stamp and its own verdict wins (stale over computed), with a four-shape test. VERIFY: 472 tests, clippy clean."; }
        // RAN: keel-serve.exe serve --port 7791; curl /api/computed/<six> -> 200 x6, bodies begin viewStatus computed with content; taskkill; removed the attestation-coverage arm from computed_binding -> cargo test every_advertised_computed_view_is_bound FAILED: ["attestation-coverage"]; restored -> ok; cargo test --release 472/0; clippy 0
        part storyBoundViewsDoDR1 : TestResult { :>> id = "00eb972c-8719-4e17-a534-9f66b8bccc5e"; :>> outcome = VerdictKind::pass; :>> judgedAgainst = "7bae4a0"; :>> judgedAt = "2026-09-04"; :>> judgedBy = "claudeOpus5"; }
    }

    verification boundViewsRefineGate : Test { :>> id = "8ec9a22d-0365-476e-bff6-340cea1eb1fe"; :>> title = "Sprint 539 refine gate (DoR)"; :>> createdAt = "2026-09-04"; :>> createdBy = "claudeOpus5"; :>> method = VerificationMethod::inspect; :>> procedureText = "READY as a receipting sprint: the code existed, the DoD's VERIFY clause named two live checks nobody had run - a server and a mutation - and a sprint that only records what a commit nine days ago built is still the sprint where it becomes done."; }
    verification boundViewsStandupGate : Test { :>> id = "e6ddb952-5bd7-45ad-92fc-63add8f04696"; :>> title = "Sprint 539 standup gate"; :>> createdAt = "2026-09-04"; :>> createdBy = "claudeOpus5"; :>> method = VerificationMethod::inspect; :>> procedureText = "ONE CHOICE: the duplicate key was fixed at the choke point, not in the two views that stamp themselves - the choke point exists so no render path can emit an unstamped body, and it is also the only place that knows the OUTER verdict; a body that says computed about itself while the cache says stale must read stale. Second: the server ran from a COPY of the binary (CLAUDE.md, issue150) so the build was never blocked."; }
    verification boundViewsImplementGate : Test { :>> id = "7f96b7ea-b0f9-4511-93d5-fd0a755c3608"; :>> title = "Sprint 539 implement gate"; :>> createdAt = "2026-09-04"; :>> createdBy = "claudeOpus5"; :>> method = VerificationMethod::test; :>> procedureText = "RAN: six curls, the raw bodies read by eye after a path mix-up broke the JSON check - which is how the duplicate key was seen at all; the first fix kept the inner stamp and the stale path proved it wrong within the minute, so the second fix drops it. The mutation probe used a backup copy of serve.rs and the diff after restore was exactly the with_status change."; }
    verification boundViewsReviewGate : Test { :>> id = "816fb1f7-7cc7-4c15-b951-ef4c4f9b12a5"; :>> title = "Sprint 539 review gate — three passes per D0172"; :>> createdAt = "2026-09-04"; :>> createdBy = "claudeOpus5"; :>> method = VerificationMethod::inspect; :>> procedureText = "THREE PASSES. (1) IS THE LIVE RECEIPT REPEATABLE: yes - the commands are in the RAN line, the server is a copy of the built binary, the port is free after taskkill. (2) DOES THE CONTROL COVER NEW VIEWPOINTS: it scrapes renderer prose, so a viewpoint added tomorrow without a binding fails the suite tomorrow. (3) IS THE STAMP FIX COMPLETE: four body shapes tested - self-stamped, plain object, empty object, array - and stale-over-computed; the two self-stamping views are left as they are, because the choke point is now correct for any future view that does the same."; }
    verification boundViewsCloseOutGate : Test { :>> id = "cf2e3db0-3730-434e-8b67-16df7d435039"; :>> title = "Sprint 539 closeOut gate (autonomous, D0049)"; :>> createdAt = "2026-09-04"; :>> createdBy = "claudeOpus5"; :>> method = VerificationMethod::inspect; :>> procedureText = "CLOSED. issue285 and issue368 resolve."; }
    verification boundViewsRetroGate : Test { :>> id = "67079e64-e446-486c-8b9b-67a699810c56"; :>> title = "Sprint 539 retro gate (autonomous, D0049)"; :>> createdAt = "2026-09-04"; :>> createdBy = "claudeOpus5"; :>> method = VerificationMethod::analyze; :>> procedureText = "no new item - already tracked: this is the third item this week found built-but-unrecorded (the recall ranker at b02e953, the bindings at e4e8ee8) - the build-now-record-later shape the memory already names, and the frontier surfaces it by leaving the item ready until its DoD result exists; issue368 was found only because a broken check made me read the raw body, which is d0295's lesson again (read the thing, not the summary of it)."; }
}
