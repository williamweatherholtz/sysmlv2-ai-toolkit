// ProjectDeliveryS396 — Sprint 396: twelve examined-never-exercised SRs run against the live system; the spec pin made real with a negative control. EXECUTE. 2 pts.
package ProjectDeliveryS396 {
    private import EngineElement::*;
    private import EngineWork::*;
    private import EngineVerification::*;
    private import EngineRelationships::*;

    #CharteredBy dependency from exerciseCampaignStory to d0101;

    part exerciseCampaignStory : Story {
        :>> id = "eac2f053-c3dc-4569-b179-1e1ec1fda6f2";
        :>> title = "Sprint 396: the system ran against its requirements (2 pts)";
        :>> createdAt = "2026-08-21"; :>> createdBy = "claudeFable5"; :>> kind = WorkKind::code; :>> priority = WorkPriority::p0; :>> owner = "claudeFable5"; :>> estimatedPoints = 2;
    }

    action def DeliveryRunS396 {
        action storyExerciseCampaign;
        verification storyExerciseCampaignDoD : Test { :>> id = "c2dd95c4-9545-40d5-8278-3fb9ab44df43"; :>> method = VerificationMethod::test; :>> procedureText = "DELIVERED: exercise-verification.sysml - 12 Tests with #Verify edges, each citing a RUN: live console probes (arrival bound 32 viewpoints -> 6 choices; 4 obligation classes all viewpoint-derived; the no-free-form-AI refusal observed), guards executing at the gate (attestation-authority consuming roles, guard 43 running the release reconciliation it caught two defects with), this session's own recorded round-trips (three decisions authored + one accepted; the SHA causal clock re-verifying drift twice; the pre-commit gate refusing sprint 395's first commit and the loop recovering), and ONE REAL FIX: sr13SpecPin's embedded digest was the all-zeros not-yet-pinned sentinel, so the divergence check had never verified anything - the live manifest was fetched, its SHA-256 pinned, the positive build verified against the live URL, and a NEGATIVE CONTROL (one flipped hex character) failed the build with the mismatch message before being restored green. Lens read back: EXERCISED 73% -> 91%, examined-never-exercised 21 -> 9, and all 9 remaining are build-gated (D0185 typed contracts x2, D0190 version identity x2, D0189-scoped console surface x2, view-state unchartered) or human-gated (srConsoleObligationActionable needs their browser) with the reason recorded on each."; }
        part storyExerciseCampaignDoDR1 : TestResult { :>> id = "4f2a84a5-63b9-40e2-b50f-4614e5382f85"; :>> outcome = VerdictKind::pass; :>> judgedAgainst = "bae0cf6"; :>> judgedAt = "2026-08-21"; :>> judgedBy = "claudeFable5"; }
    }

    verification exerciseCampaignRefineGate : Test { :>> id = "d31ef98b-8e7f-4682-aee0-94b32d3fbbe4"; :>> title = "Sprint 396 refine gate (DoR)"; :>> createdAt = "2026-08-21"; :>> createdBy = "claudeFable5"; :>> method = VerificationMethod::inspect; :>> procedureText = "DoR. Increment 3 of the verification campaign, chartered by d0101 (evidence is re-runnable and honest, never fabricated - the campaign's own rule). Scope: exercise only where machinery exists; a requirement whose machinery is unbuilt keeps its honest examined-FAIL rather than a staged demo. 2 points."; }
    part exerciseCampaignRefineGateR1 : TestResult { :>> id = "1fc8e6d9-cbe1-487b-8882-aab171f21672"; :>> outcome = VerdictKind::pass; :>> judgedAgainst = "bae0cf6"; :>> judgedAt = "2026-08-21"; :>> judgedBy = "claudeFable5"; }
    verification exerciseCampaignStandupGate : Test { :>> id = "9c75d158-6123-45fd-aeff-f926d5e31fa7"; :>> title = "Sprint 396 standup gate"; :>> createdAt = "2026-08-21"; :>> createdBy = "claudeFable5"; :>> method = VerificationMethod::inspect; :>> procedureText = "Approach: classify the 21 first (12 exercisable / 8 build-gated / 1 human-gated), probe before authoring, and where the exercise reveals the mechanism was never really live (the spec pin) FIX it and record the pre-fix state in the record itself. No blockers."; }
    part exerciseCampaignStandupGateR1 : TestResult { :>> id = "f9067fa9-f8f1-4e27-9037-cda119964e27"; :>> outcome = VerdictKind::pass; :>> judgedAgainst = "bae0cf6"; :>> judgedAt = "2026-08-21"; :>> judgedBy = "claudeFable5"; }
    verification exerciseCampaignImplementGate : Test { :>> id = "4daccb12-d654-489f-9bfa-3c956be4adc9"; :>> title = "Sprint 396 implement gate"; :>> createdAt = "2026-08-21"; :>> createdBy = "claudeFable5"; :>> method = VerificationMethod::test; :>> procedureText = "Probes captured before authoring: /api/surfaces (6 surfaces / 32 viewpoints), /api/obligations (4 classes, named), the sprint-393 refusal transcript, reverify runs at 0433ca6 and 2af2ac9, enforcement-report per-event counts (post-edit 104 / pre-bash 334 / pre-write 5 / stop 5). sr13SpecPin: digest e86a23b3... pinned; SYSML_V2_SPEC_OFFLINE=0 build green; flipped-hex negative control FAILED the build with the mismatch message; restored green. validate 433 clean; lens read back exercised 91%."; }
    part exerciseCampaignImplementGateR1 : TestResult { :>> id = "82b605ab-b3dc-4053-9d02-9add964f34c6"; :>> outcome = VerdictKind::pass; :>> judgedAgainst = "bae0cf6"; :>> judgedAt = "2026-08-21"; :>> judgedBy = "claudeFable5"; }
    verification exerciseCampaignReviewGate : Test { :>> id = "0932283b-bc6d-492e-bd03-f71e917b6fc3"; :>> title = "Sprint 396 review gate — three passes per D0172"; :>> createdAt = "2026-08-21"; :>> createdBy = "claudeFable5"; :>> method = VerificationMethod::inspect; :>> procedureText = "PASS 1, CLAIMS: every record cites a run this session performed or a guard execution counted in today's output - none cites the SR's rationale or the implementing code alone. PASS 2, BOUNDARY: the weakest records are the self-referential ones (sr07AgentLoop, sr09SelfBuild exercised BY the session doing the exercising) - defensible because the statement's own success criterion is the tracked history, and the records cite the gate REFUSING as the negative path, not just the happy loop. PASS 3, OWN DIFF: the sr13 pin targets master/README.md, so upstream edits WILL fail networked builds by design - the record says so and the build message names the remedy; CI carries no offline flag, which is deliberate and stated. WHAT A REVIEWER SHOULD ATTACK: several exercise records lean on probes made for OTHER sprints' records (393/394) - each names which, so the reuse is traceable rather than laundered."; }
    part exerciseCampaignReviewGateR1 : TestResult { :>> id = "30ad7b4f-29be-4778-bd8b-576d3de175c2"; :>> outcome = VerdictKind::pass; :>> judgedAgainst = "bae0cf6"; :>> judgedAt = "2026-08-21"; :>> judgedBy = "claudeFable5"; }
    verification exerciseCampaignCloseOutGate : Test { :>> id = "4242fb68-50b6-410b-8360-f5afb56ed287"; :>> title = "Sprint 396 closeOut gate (autonomous, D0049)"; :>> createdAt = "2026-08-21"; :>> createdBy = "claudeFable5"; :>> method = VerificationMethod::inspect; :>> procedureText = "Autonomous closeOut (D0049). Twelve #Verify edges landed; lens read back (exercised 91%, neither still 0); the 9 remaining never-exercised each carry a recorded reason and a flip condition. validate + all 44 guards green."; }
    part exerciseCampaignCloseOutGateR1 : TestResult { :>> id = "b02803b3-a564-4e5e-99a7-7158cf804fb1"; :>> outcome = VerdictKind::pass; :>> judgedAgainst = "bae0cf6"; :>> judgedAt = "2026-08-21"; :>> judgedBy = "claudeFable5"; }
    verification exerciseCampaignRetroGate : Test { :>> id = "24277b7e-1353-4520-acce-5d2efce9d7c9"; :>> title = "Sprint 396 retro gate (autonomous, D0049)"; :>> createdAt = "2026-08-21"; :>> createdBy = "claudeFable5"; :>> method = VerificationMethod::analyze; :>> procedureText = "Autonomous retro (D0049). AVOIDABLE-ISSUE SCAN under rcRecurrence: the sentinel-that-never-checked (sr13's all-zeros pin) is the same family as issue202 (a gate whose only client could not reach it) - a control shipped in the OFF state and nothing measured that it had never fired. The fire-ledger (D0180) is the existing counter-control for hooks; for build-time checks there is none, and this retro NAMES that as the residual rather than inventing a control mid-sprint. WELL: classify-first kept 9 unexercisable SRs from getting staged demos - the campaign's honesty rule held under completion pressure. Estimate 2 pts, delivered 2."; }
    part exerciseCampaignRetroGateR1 : TestResult { :>> id = "09662967-5f57-46a2-be06-de402fba7e7c"; :>> outcome = VerdictKind::pass; :>> judgedAgainst = "bae0cf6"; :>> judgedAt = "2026-08-21"; :>> judgedBy = "claudeFable5"; }
}
