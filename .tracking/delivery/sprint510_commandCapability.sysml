// ProjectDeliveryS510 — Sprint 510: the capability half D0252 promised and never built. EXECUTE. 3 pts.
package ProjectDeliveryS510 {
    private import EngineElement::*;
    private import EngineWork::*;
    private import EngineVerification::*;
    private import EngineRelationships::*;

    #CharteredBy dependency from commandCapabilityStory to d0252;

    part commandCapabilityStory : Story {
        :>> id = "8b40f1a7-2d69-4c53-9e18-46a2075bc3f9";
        :>> title = "Sprint 510: a unit declares the commands it invokes, and an engine lacking one refuses by name (3 pts)";
        :>> createdAt = "2026-09-01"; :>> createdBy = "claudeOpus5"; :>> kind = WorkKind::code; :>> priority = WorkPriority::p0; :>> owner = "claudeOpus5"; :>> estimatedPoints = 3;
    }

    action def DeliveryRunS510 {
        action storyCommandCapability;
        verification storyCommandCapabilityDoD : Test { :>> id = "a51c8e39-70b4-4f26-8d07-1e93b60fa4d2"; :>> method = VerificationMethod::test; :>> procedureText = "DELIVERED BACKLOG ITEMS: dcUnitDeclaresTheCommandsItInvokes. Step 2 of 5 in the D0275 migration plan and D0273's stated prerequisite. THE GAP: D0252 clause A promised a unit declares the capabilities it invokes - guards, schema types AND commands - and that an install whose engine lacks one REFUSES naming the missing capability rather than a version number. Only the guard half shipped (D0183/K8). So a renamed command failed SILENTLY downstream: the skill landed and its instructions did not run. Clause A even records that renaming a command is a breaking change for units that declare it, recorded so a future rename is not made casually - and the human has now authorised exactly such a rename. DONE: cli_surface::COMMAND_NAMES as the inventory; unit_commands derives what a unit invokes by scanning for a keel-prefixed token that is ALREADY dispatched, so the scan is self-limiting; export writes commands into unit.toml; the handshake refuses before any file is written, with NO --degrade escape. VERIFY: the inventory matches the dispatch BOTH ways, plus derivation and refusal cases."; }
        // RAN: capability_refusal_bites 3/3; the inventory test caught a real mismatch on its first run; workspace suite 457 passed / 0 failed; clippy clean
        part storyCommandCapabilityDoDR1 : TestResult { :>> id = "b62d9f4a-81c5-4037-9e18-2fa4c71db5e3"; :>> outcome = VerdictKind::pass; :>> judgedAgainst = "21cdce7"; :>> judgedAt = "2026-09-01"; :>> judgedBy = "claudeOpus5"; }
    }

    verification commandCapabilityRefineGate : Test { :>> id = "c73ea052-92d6-4148-af29-30b5d82ec6f4"; :>> title = "Sprint 510 refine gate (DoR)"; :>> createdAt = "2026-09-01"; :>> createdBy = "claudeOpus5"; :>> method = VerificationMethod::inspect; :>> procedureText = "READY without a new Decision, and that is the point: D0252 clause A is already ACCEPTED and specifies this behaviour in its own words. The work is building an accepted promise, not deciding anything - so the acceptance criterion is the Decision text itself, which is the strongest form of a DoR existing before implementation."; }
    verification commandCapabilityStandupGate : Test { :>> id = "d84fb163-a3e7-4259-b03a-41c6e930fd05"; :>> title = "Sprint 510 standup gate"; :>> createdAt = "2026-09-01"; :>> createdBy = "claudeOpus5"; :>> method = VerificationMethod::inspect; :>> procedureText = "TWO DESIGN CHOICES worth stating because both could reasonably have gone the other way. (1) DERIVED, NOT AUTHORED. A hand-maintained commands list in a contract goes stale the first time a skill's prose changes, and a stale capability declaration is WORSE than none - it refuses installs that would work and permits ones that will not. Deriving costs nothing to author (D0054) and cannot drift from the text it describes. The risk is false positives from prose, answered by making the scan self-limiting: a token counts only if it follows `keel ` AND is already dispatched, so a prose word cannot invent a dependency unless someone wrote a real command after the word keel - at which point the unit genuinely does instruct its reader to run it. (2) NO --degrade, unlike guards and rules. A missing guard means enforcement did not travel and the prose still reads correctly; a missing COMMAND means the prose instructs a reader to run something that does not exist. Degrading would install a skill that is actively wrong rather than merely toothless."; }
    verification commandCapabilityImplementGate : Test { :>> id = "e95a0274-b4f8-436a-c14b-52d70a41fe16"; :>> title = "Sprint 510 implement gate"; :>> createdAt = "2026-09-01"; :>> createdBy = "claudeOpus5"; :>> method = VerificationMethod::test; :>> procedureText = "RAN: cargo test --release --test capability_refusal_bites -> 3 passed. Workspace suite -> 457 passed, 0 failed. clippy -> clean. THE LOAD-BEARING CASE IS THE INVENTORY, not the refusal. Rust cannot introspect a match at runtime, so COMMAND_NAMES must be a const, and a const that drifts from the dispatch makes the handshake CONFIDENTLY WRONG - refusing commands the binary has, or accepting ones it lacks. the_command_inventory_matches_the_dispatch parses main.rs's one top-level match and asserts set equality in BOTH directions. It earned its place on the first run by catching `--version`: dispatched, but a flag spelling rather than a command, so the parser was tightened to require a leading lowercase letter and the reasoning written into the test. 99 commands in the inventory."; }
    verification commandCapabilityReviewGate : Test { :>> id = "f06b1385-c509-4471-d225-63e81b52af27"; :>> title = "Sprint 510 review gate — three passes per D0172"; :>> createdAt = "2026-09-01"; :>> createdBy = "claudeOpus5"; :>> method = VerificationMethod::inspect; :>> procedureText = "THREE PASSES. (1) DOES THE REFUSAL FIRE TOO EARLY: it runs in the handshake, before any file is written, and the test asserts the refused unit left NO trace - a half-installed unit is precisely the state the handshake exists to prevent, so early is correct. (2) CAN IT REFUSE A UNIT THAT WOULD ACTUALLY WORK: only if a unit's prose names a command it does not really need. That is possible - a skill mentioning `keel orphans` as an aside would declare it - and it is the accepted cost of deriving: the false positive is a refusal a human can read and act on, whereas the false NEGATIVE this replaces was a silent no-op. Erring toward the readable failure is the right direction. (3) IS THE INVENTORY A NEW MAINTENANCE BURDEN: yes, one const to update per command added - and the test fails loudly when it is not, naming the command. That is the trade D0252 clause A already accepted when it recorded that capability names become a public interface."; }
    verification commandCapabilityCloseOutGate : Test { :>> id = "0a17c496-d61a-4582-e336-74f92c63b038"; :>> title = "Sprint 510 closeOut gate (autonomous, D0049)"; :>> createdAt = "2026-09-01"; :>> createdBy = "claudeOpus5"; :>> method = VerificationMethod::inspect; :>> procedureText = "CLOSED. D0252 clause A's command half exists. D0273's prerequisite is met, so the clean break can now be made LOUD downstream instead of silent. Next: dcMigrationFixtureIsRealistic, which makes steps 1 and 2 provable against a project that looks like a real one rather than a fresh scaffold."; }
    verification commandCapabilityRetroGate : Test { :>> id = "1b28d5a7-e703-4693-f447-85a03d740149"; :>> title = "Sprint 510 retro gate (autonomous, D0049)"; :>> createdAt = "2026-09-01"; :>> createdBy = "claudeOpus5"; :>> method = VerificationMethod::analyze; :>> procedureText = "ONE FINDING, and it is about how the gap survived. D0252 clause A was ACCEPTED on 2026-08-30 and its command half was never built, while its guard half had shipped earlier under a different Decision. Nothing detected the shortfall: the Decision read as delivered because the mechanism it named already existed for one capability class, and no control asks whether an accepted Decision's clauses are all built. The decision-scaffolding guard is the nearest thing and it only checks that an accepted #ProspectiveChange has SOME inbound tracked-item edge - d0252 had one, for clause B's rollback work, so it passed while half of clause A sat unbuilt. The generalisable shape: a multi-clause Decision satisfies a per-Decision coverage check as soon as ONE clause is chartered, so partial delivery of a compound Decision is structurally invisible. Not fixed here; the honest form would be per-clause charter edges, which is a schema question and belongs in a proposal."; }
}
