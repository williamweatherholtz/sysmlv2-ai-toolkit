// =====================================================================
// ProjectDeliveryS86 — Sprint 86: reportScorecards (D0087 Stage 1). The computed REPORT/SCORECARD
// layer: `sysmlv2 report <assurance|traceability|quality-debt|flow> [--html]` — human-digestible
// aggregate metrics (coverage %, critique %, attestation %, findings, traceability completeness,
// debt, volatility, flow/velocity) rolled up from the per-element views; HEALTH vs OPPORTUNITY.
// (Stage 2 = git-derived trends, Sprint 87.)
// Total: 5 pts  Ceremony: AUTONOMOUS (D0049); the report-layer CHANGE was human-accepted (D0087).
// =====================================================================
package ProjectDeliveryS86 {
    private import EngineElement::*;
    private import EngineWork::*;
    private import EngineVerification::*;
    private import EngineRelationships::*;

    #CharteredBy dependency from reportScorecardsStory to d0087;

    part reportScorecardsStory : Story {
        :>> id = "63940516-2c7d-4e8f-b086-51627384b701";
        :>> title = "Sprint 86: reportScorecards (5 pts) — `sysmlv2 report <name> [--html]` computed aggregate scorecards (assurance/traceability/quality-debt/flow); report process/skill/viewpoint (D0087 Stage 1)";
        :>> createdAt = "2026-06-21";
        :>> createdBy = "wweatherholtz";
        :>> kind = WorkKind::code;
        :>> priority = WorkPriority::p1;
        :>> owner = "claudeOpus";
        :>> estimatedPoints = 5;
    }

    action def DeliveryRunS86 {
        action storyReportScorecards;
        verification storyReportScorecardsDoD : Test { :>> id = "63940516-2c7d-4e8f-b086-51627384b702"; :>> method = VerificationMethod::test; :>> procedureText = "`sysmlv2 report <assurance|traceability|quality-debt|flow> [--html]` emits computed aggregate scorecards rolling up the per-element views (compute_coverage/critique/attestation/readiness/orient/decisions): assurance [health] (coverage %, critique %, attestation %, findings by severity, suspect load, READY/NOT), traceability [health] (% needs/reqs verified, satisfy/verify edge completeness), quality-debt [opportunity] (charter debt, volatility, suspect+stale), flow [opportunity] (ready/WIP/throughput/velocity/open-issues). Card-based JSON + one unifying HTML scorecard template (good/warn/bad tone). report process-def (.engine/processes/report.sysml) + report skill + skills-registry + 'report' viewpoint; D0087 #ProspectiveChange keystone (D0070); doc-sync CLAUDE.md/usage.md; serde-free (Json emitter); /*.html git-ignored. VERIFY: all 4 reports emit sensible live numbers (assurance coverage 100% / critique 12% / attestation 100%; traceability needs+reqs verified 100% + verify-edge 100% after a direction-bug fix; quality-debt; flow throughput 87 / velocity ~2); --html cards render; clippy --workspace --all-targets -D warnings + cargo test (38 lib, +pct +report-cards regressions) + rust validate + guard all (9) green; d0087 Core-3 critiqued. Stage 2 (git trends) deferred to Sprint 87 per D0087."; }
        part storyReportScorecardsDoDR1 : TestResult { :>> id = "63940516-2c7d-4e8f-b086-51627384b703"; :>> outcome = VerdictKind::pass; :>> judgedAgainst = "9e1aa68"; :>> judgedAt = "2026-06-21"; :>> judgedBy = "claudeOpus"; }
    }

    verification reportScorecardsRefineGate : Test { :>> id = "63940516-2c7d-4e8f-b086-51627384b704"; :>> title = "Sprint 86 refine gate (DoR)"; :>> createdAt = "2026-06-21"; :>> createdBy = "claudeOpus"; :>> method = VerificationMethod::inspect; :>> procedureText = "DoR: the human asked for human-digestible report artifacts with aggregated values/metrics (coverage totals, %, others) indicating HEALTH + OPPORTUNITY. Research (INCOSE DE Measurement Framework + SE Leading Indicators + model-quality canon + DO-178C traceability) -> a computed report/scorecard layer aggregating the per-element views. Human accepted all four reports + trends-now; recorded as D0087, sequenced Stage 1 (scorecards, this sprint) + Stage 2 (git trends, next). estimatedPoints=5. #CharteredBy d0087. DoD accepted."; }
    part reportScorecardsRefineGateR1 : TestResult { :>> id = "63940516-2c7d-4e8f-b086-51627384b705"; :>> outcome = VerdictKind::pass; :>> judgedAgainst = "9e1aa68"; :>> judgedAt = "2026-06-21"; :>> judgedBy = "claudeOpus"; }

    verification reportScorecardsStandupGate : Test { :>> id = "63940516-2c7d-4e8f-b086-51627384b706"; :>> title = "Sprint 86 standup gate"; :>> createdAt = "2026-06-21"; :>> createdBy = "claudeOpus"; :>> method = VerificationMethod::inspect; :>> procedureText = "Approach: view.rs report layer — pct/cov_tone/card helpers; report_cards(root,name) builds shared inputs (model/orient/done/stale/cov) once + dispatches to assurance/traceability/quality-debt/flow card builders reusing the per-element computations; report() JSON + report_html() via one REPORT_TEMPLATE of tone-coloured cards. main.rs cmd_report (--html flag) + dispatch + ViewError::UnknownReport. report process/skill/viewpoint + registries + doc-sync + d0087 critiques. Watch: verify edge DIRECTION (incoming to requirement); governed-vs-total in %. No blockers."; }
    part reportScorecardsStandupGateR1 : TestResult { :>> id = "63940516-2c7d-4e8f-b086-51627384b707"; :>> outcome = VerdictKind::pass; :>> judgedAgainst = "9e1aa68"; :>> judgedAt = "2026-06-21"; :>> judgedBy = "claudeOpus"; }

    verification reportScorecardsImplementGate : Test { :>> id = "63940516-2c7d-4e8f-b086-51627384b708"; :>> title = "Sprint 86 implement gate"; :>> createdAt = "2026-06-21"; :>> createdBy = "claudeOpus"; :>> method = VerificationMethod::test; :>> procedureText = "Implemented the 4 report card-builders + report()/report_html() + REPORT_TEMPLATE + cmd_report + report process/skill/viewpoint/registries + doc-sync + d0087 Core-3 critiques. VERIFY (live): report assurance -> coverage 100% / critique 12% / attestation 100% / findings 0 / READY; traceability -> needs+reqs verified 100% + needs-satisfy 100% + reqs-verify 100% (after fixing the incoming-edge direction bug); quality-debt -> charter-critique-debt 97 / volatility 0% / suspect+stale 9; flow -> ready 0 / WIP 0 / throughput 87 / velocity ~2 / open-issues 0; --html emits tone-coloured cards. clippy --workspace --all-targets -D warnings green; cargo test 38 lib pass (incl pct_handles_empty_denominator + report_produces_cards_and_rejects_unknown); rust validate clean; guard all (9) PASS (critique 0 gaps after d0087 critiques; process-change keystone via D0087 #ProspectiveChange + report.sysml)."; }
    part reportScorecardsImplementGateR1 : TestResult { :>> id = "63940516-2c7d-4e8f-b086-51627384b709"; :>> outcome = VerdictKind::pass; :>> judgedAgainst = "9e1aa68"; :>> judgedAt = "2026-06-21"; :>> judgedBy = "claudeOpus"; }

    verification reportScorecardsReviewGate : Test { :>> id = "63940516-2c7d-4e8f-b086-51627384b70a"; :>> title = "Sprint 86 review gate"; :>> createdAt = "2026-06-21"; :>> createdBy = "claudeOpus"; :>> method = VerificationMethod::inspect; :>> procedureText = "Diff reviewed. Reports are pure computed #Views aggregating existing per-element computations (reuse over invention) — no stored metric, no committed snapshot, /*.html git-ignored, consistent with §2.1/D0018 and coverage/assured/render. The card/tone JSON shape lets ONE template render all four (and future) reports. HEALTH (assurance/traceability) vs OPPORTUNITY (quality-debt/flow) split matches how SE leading indicators are read. The verify-edge direction bug (requirement is the #Verify TARGET) was caught in smoke-test and fixed before commit. Honest scope: Stage 1 is point-in-time; git-derived TRENDS are Stage 2 (Sprint 87), recorded in D0087. doc-sync done."; }
    part reportScorecardsReviewGateR1 : TestResult { :>> id = "63940516-2c7d-4e8f-b086-51627384b70b"; :>> outcome = VerdictKind::pass; :>> judgedAgainst = "9e1aa68"; :>> judgedAt = "2026-06-21"; :>> judgedBy = "claudeOpus"; }

    verification reportScorecardsCloseOutGate : Test { :>> id = "63940516-2c7d-4e8f-b086-51627384b70c"; :>> title = "Sprint 86 closeOut gate (autonomous, D0049)"; :>> createdAt = "2026-06-21"; :>> createdBy = "claudeOpus"; :>> method = VerificationMethod::inspect; :>> procedureText = "Autonomous closeOut (D0049): storyReportScorecards DoD recorded pass; all 4 scorecards live (JSON + --html); report process/skill/viewpoint registered; D0087 accepted + Core-3 critiqued; doc-sync done; clippy + cargo test (38) + rust validate + guard all (9) green. Self-evidencing (D0051). Stage 1 of the report layer is operational; Stage 2 (git trends) is next."; }
    part reportScorecardsCloseOutGateR1 : TestResult { :>> id = "63940516-2c7d-4e8f-b086-51627384b70d"; :>> outcome = VerdictKind::pass; :>> judgedAgainst = "9e1aa68"; :>> judgedAt = "2026-06-21"; :>> judgedBy = "claudeOpus"; }

    verification reportScorecardsRetroGate : Test { :>> id = "63940516-2c7d-4e8f-b086-51627384b70e"; :>> title = "Sprint 86 retro gate (autonomous, D0049)"; :>> createdAt = "2026-06-21"; :>> createdBy = "claudeOpus"; :>> method = VerificationMethod::analyze; :>> procedureText = "Autonomous retro (D0049). WELL: research-first grounded the metric set in the recognized MBSE measurement canon (INCOSE DE Measurement Framework + SE Leading Indicators) before coding, so the reports surface the RIGHT numbers (verification coverage % as the headline, volatility as the early-warning); the card/tone JSON shape gave one reusable renderer for all four reports; everything is reuse-over-invention (aggregates of existing per-element computations) so almost no new measurement logic. CAUGHT (avoidable-issue candidate): the requirements-with-verify metric first read 0% because I used has_outgoing while #Verify points INTO the requirement (the requirement is the edge TARGET) — an avoidable direction error I should have checked against the known edge semantics; caught it in smoke-test against the known-good model (100% expected) and fixed before commit. Lesson: when a coverage metric reads 0%/100% unexpectedly, validate edge DIRECTION against the schema before trusting the number — a metric that silently reads the wrong direction is worse than no metric. Estimate 5 pts held. Stage 1 scorecards operational; git-derived trends (Stage 2) follow in Sprint 87."; }
    part reportScorecardsRetroGateR1 : TestResult { :>> id = "63940516-2c7d-4e8f-b086-51627384b70f"; :>> outcome = VerdictKind::pass; :>> judgedAgainst = "9e1aa68"; :>> judgedAt = "2026-06-21"; :>> judgedBy = "claudeOpus"; }
}
