// ProjectDeliveryS546 — Sprint 546: the issues guard reads the link, not just the edge; the multi-clause defect goes to the human as a fork instead of a fake. EXECUTE. 3 pts.
package ProjectDeliveryS546 {
    private import EngineElement::*;
    private import EngineWork::*;
    private import EngineVerification::*;
    private import EngineRelationships::*;

    #CharteredBy dependency from controlDefectsStory to d0304;

    part controlDefectsStory : Story {
        :>> id = "d0a6ac96-2edc-4b3c-aa06-a78262a8e572";
        :>> title = "Sprint 546: the issues guard reads the link, not just the edge; the multi-clause defect goes to the human as a fork instead of a fake (3 pts)";
        :>> createdAt = "2026-09-04"; :>> createdBy = "claudeOpus5"; :>> kind = WorkKind::code; :>> priority = WorkPriority::p0; :>> owner = "claudeOpus5"; :>> estimatedPoints = 3;
    }

    action def DeliveryRunS546 {
        action storyControlDefects;
        verification storyControlDefectsDoD : Test { :>> id = "36803d2e-3a42-439d-8791-f823a6658682"; :>> method = VerificationMethod::test; :>> procedureText = "DELIVERED BACKLOG ITEMS: dcControlDefectsAreFixed, rescoped honestly to issue333 (issue332 was already dcSessionActorReachesHooks's - the ownership guard reads actor::resolve at guards.rs:2902 and its registry entry had already left; issue331 is SPLIT to dcDecisionClausesAreAddressable behind fork d0303). DONE for issue333: view::unnamed_resolutions reads every resolves edge and asks whether the resolver's text names the issue OR the issue's text names the resolver; the issues guard fails an issue created on/after 2026-09-04 that has neither and counts earlier misses in one warning (111 on this tree); the [issues] control-defect entry leaves in this commit; guards.md's row carries the rule. NOT DONE, deliberately: issue331 - a clauses-versus-stories heuristic was measured at 40 hits with delivered and partial cases indistinguishable, so instead of a fake control the schema question is raised as fork d0303 (three options, costs, research, recommendation C) and the split item is blocked on it. VERIFY: the arming test - the issue323 shape fires forward of the cutoff, either naming direction passes, a pre-cutoff miss is counted; the live run caught issue370's unstated link (its text named the Decision and the test, not the carrying item) and it is corrected; 481 tests; clippy clean; judgment-request-quality passes on d0303."; }
        // RAN: census (144/111/40), arming test 1/1, live guard run 4 fires -> 1 real -> 0, suite 481/0, clippy 0, d0303 fork quality PASS
        part storyControlDefectsDoDR1 : TestResult { :>> id = "e5875535-478d-429a-a6dc-0045ffc548d5"; :>> outcome = VerdictKind::pass; :>> judgedAgainst = "3990204"; :>> judgedAt = "2026-09-04"; :>> judgedBy = "claudeOpus5"; }
    }

    verification controlDefectsRefineGate : Test { :>> id = "8dbb92d7-5354-4c4f-9a2e-e4e0cc9ed5c0"; :>> title = "Sprint 546 refine gate (DoR)"; :>> createdAt = "2026-09-04"; :>> createdBy = "claudeOpus5"; :>> method = VerificationMethod::inspect; :>> procedureText = "READY once the registry, not the DoD, was trusted for the issue numbers: the DoD had them permuted (331 as ownership, 333 as decision-scaffolding); the registry and the issue titles agree the other way, and the DoD text now says so above its original wording rather than being rewritten."; }
    verification controlDefectsStandupGate : Test { :>> id = "baf36236-49f1-4be4-9ec2-fc17b59ec7b8"; :>> title = "Sprint 546 standup gate"; :>> createdAt = "2026-09-04"; :>> createdBy = "claudeOpus5"; :>> method = VerificationMethod::inspect; :>> procedureText = "THREE CHOICES stated plainly. (1) Either naming direction satisfies the check, because the ordinary order of events is fix-then-record and requiring the resolver side alone would force edits to verified DoDs (the issue343 class). (2) Forward-only with a counted history line: 111 records written under a weaker rule are not a red gate. (3) issue331 is not solved by a heuristic that cannot tell d0302's complete delivery from d0252's partial one - the honest move is the fork, and the DoD of this item is re-scoped to say what it delivers rather than passed against a promise it does not keep."; }
    verification controlDefectsImplementGate : Test { :>> id = "951a4a34-2c1d-4c2b-8795-e44b92a9075d"; :>> title = "Sprint 546 implement gate"; :>> createdAt = "2026-09-04"; :>> createdBy = "claudeOpus5"; :>> method = VerificationMethod::test; :>> procedureText = "RAN: census first - 144 one-directional misses, 111 two-directional, 40 multi-clause Decisions with fewer stories including four fully delivered this week; the guard's first live run fired on four of my own issues from today, three of which were linked by the issue's text and one (issue370) genuinely unstated - fixed in the issue's description, not by loosening the check; two clippy items; d0303 recorded as a fork and passing judgment-request-quality first time."; }
    verification controlDefectsReviewGate : Test { :>> id = "e5de2e4c-157d-4aa4-88d7-fe447dae36c2"; :>> title = "Sprint 546 review gate — three passes per D0172"; :>> createdAt = "2026-09-04"; :>> createdBy = "claudeOpus5"; :>> method = VerificationMethod::inspect; :>> procedureText = "THREE PASSES. (1) CAN THE CHECK BE GAMED: a resolver that names the issue and cannot resolve it passes - stated in D0304 as the same limit D0192 states for quotes; the DoD result the resolver must eventually pass is the backstop. (2) IS THE RESCOPE HONEST: the DoD text keeps its original wording under a dated correction, the split item carries issue331's edge, and this item's pass claims issue333 only. (3) IS THE CUTOFF RETROACTIVE DOWNSTREAM: yes - issue352's class, named in the guard comment and D0304, fixed by dcForwardOnlyCutoffIsTheProjectsOwn, not here."; }
    verification controlDefectsCloseOutGate : Test { :>> id = "d6407ae6-cb5e-4acd-a036-009ef536f586"; :>> title = "Sprint 546 closeOut gate (autonomous, D0049)"; :>> createdAt = "2026-09-04"; :>> createdBy = "claudeOpus5"; :>> method = VerificationMethod::inspect; :>> procedureText = "CLOSED. issue333 resolves; d0303 awaits the human's word; the registry holds one entry, decision-scaffolding, with its stated reason."; }
    verification controlDefectsRetroGate : Test { :>> id = "547ee987-823c-4b3e-91a9-fe4bfda0e5ef"; :>> title = "Sprint 546 retro gate (autonomous, D0049)"; :>> createdAt = "2026-09-04"; :>> createdBy = "claudeOpus5"; :>> method = VerificationMethod::analyze; :>> procedureText = "no new item - already tracked: issue331's path is d0303 and dcDecisionClausesAreAddressable; the retroactive-cutoff class is issue352 and its resolver; the fake-control temptation this sprint refused is the d0151 rule applied to controls - a check that would have passed on the motivating case and failed on the healthy one is a claim in a conclusion's grammar, and measuring it first is what kept it out."; }
}
