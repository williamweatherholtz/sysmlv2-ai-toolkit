// ProjectDeliveryS643 — Sprint 643: Sprint 643: the two defects the first live pushes of D0421/D0422 exposed - CI red on cab7cac because the touched set never ran the lib unit tests and one of them hardcoded the suite synopsis's citations (issue438), and the hook's land copy never made because command -v keel resolves into target/release and the case block matched literal paths (issue437). Both Decisions' texts amended to say what the code now does. 2 pts.. EXECUTE. 2 pts.
package ProjectDeliveryS643 {
    private import EngineElement::*;
    private import EngineWork::*;
    private import EngineVerification::*;
    private import EngineRelationships::*;

    #CharteredBy dependency from libTestsAndTheResolvedHookStory to d0421;

    part libTestsAndTheResolvedHookStory : Story {
        :>> id = "02566087-b534-4352-b4d6-2cc452cd9ac0";
        :>> title = "Sprint 643: Sprint 643: the two defects the first live pushes of D0421/D0422 exposed - CI red on cab7cac because the touched set never ran the lib unit tests and one of them hardcoded the suite synopsis's citations (issue438), and the hook's land copy never made because command -v keel resolves into target/release and the case block matched literal paths (issue437). Both Decisions' texts amended to say what the code now does. 2 pts. (2 pts)";
        :>> createdAt = "2026-09-10"; :>> createdBy = "claudeOpus5"; :>> kind = WorkKind::code; :>> priority = WorkPriority::p0; :>> owner = "claudeOpus5"; :>> estimatedPoints = 2;
    }

    action def DeliveryRunS643 {
        action storyLibTestsAndTheResolvedHook;
        verification storyLibTestsAndTheResolvedHookDoD : Test { :>> id = "77dcc33c-f894-4424-8975-4212dc761118"; :>> method = VerificationMethod::test; :>> procedureText = "DELIVERED: dcTouchedRunIncludesTheLibTests resolves issue438 - Touched.lib, --lib on the one cargo run, lib in the receipt and in failing_binaries, nothing_to_run as the one emptiness rule, the guards.rs test deriving its present set from the live synopsis; dcHookCopyFollowsPathResolution resolves issue437 - the hook tests the resolved file's directory against target/release by pwd -P and copies for a basename of keel or keel.exe, keeping the real extension. VERIFY: lib 451 passed 0 failed; touched_tests_run_before_land 4 passed; push_gate_is_withdrawn 2 passed; clippy clean; hookprobe.sh four cases as the DoD names; the commit carrying this leaves target/release/keel-land.exe on disk with land run from it; CI on this push read from gh run list."; }
        // RAN: both resolvers stamped pass at b522674 on the receipts above; whats-next reads dcHookCopyFollowsPathResolution, dcTouchedRunIncludesTheLibTests at the head
        part storyLibTestsAndTheResolvedHookDoDR1 : TestResult { :>> id = "d03cb226-8dfa-483c-a657-7dc3403afa12"; :>> outcome = VerdictKind::pass; :>> judgedAgainst = "b522674"; :>> judgedAt = "2026-09-09T18:40:00-06:00"; :>> judgedBy = "claudeOpus5"; }
    }

    verification libTestsAndTheResolvedHookRefineGate : Test { :>> id = "3b33ab19-1f24-4482-8ad2-4b0d8b664bb2"; :>> title = "Sprint 643 refine gate (DoR)"; :>> createdAt = "2026-09-10"; :>> createdBy = "claudeOpus5"; :>> method = VerificationMethod::inspect; :>> procedureText = "Definition of Ready: issue438 Critical and issue437 High, recorded 2026-09-09 with resolvers naming them, ranked at the frontier head and read back from whats-next; both changes are bounded to touched.rs, one test in guards.rs, the fixture, and the hook block; 2 points."; }
    // RAN: sprint643 Refine: the fill's Refine section; validate 728 clean, check-engine clean, guard ALL PASS exit 0 at b522674+working tree
    part libTestsAndTheResolvedHookRefineGateR1 : TestResult { :>> id = "c53b3ae7-de2c-4dc8-8d28-1d4e2f217821"; :>> outcome = VerdictKind::pass; :>> judgedAgainst = "b522674"; :>> judgedAt = "2026-09-09T18:40:00-06:00"; :>> judgedBy = "claudeOpus5"; }
    verification libTestsAndTheResolvedHookStandupGate : Test { :>> id = "c9057a7d-0100-4591-9d3a-513818c78424"; :>> title = "Sprint 643 standup gate"; :>> createdAt = "2026-09-10"; :>> createdBy = "claudeOpus5"; :>> method = VerificationMethod::inspect; :>> procedureText = "No blocker. The first cut of each control was probed against cases chosen from an assumption about the host (PATH keel lives elsewhere; unit tests do not read live facts) rather than from the host - the same shape as issue435 the sprint before."; }
    // RAN: sprint643 Standup: the fill's Standup section; validate 728 clean, check-engine clean, guard ALL PASS exit 0 at b522674+working tree
    part libTestsAndTheResolvedHookStandupGateR1 : TestResult { :>> id = "bd3bd802-1b1c-424d-b0d9-db6f6f4437d6"; :>> outcome = VerdictKind::pass; :>> judgedAgainst = "b522674"; :>> judgedAt = "2026-09-09T18:40:00-06:00"; :>> judgedBy = "claudeOpus5"; }
    verification libTestsAndTheResolvedHookImplementGate : Test { :>> id = "e26aa033-497d-4921-95d0-27163709fdf0"; :>> title = "Sprint 643 implement gate"; :>> createdAt = "2026-09-10"; :>> createdBy = "claudeOpus5"; :>> method = VerificationMethod::test; :>> procedureText = "lib643.py (touched.rs, guards.rs test, fixture), hook643.py (.githooks/post-commit), dec643.py (D0421/D0422 text, CLAUDE.md two anchors), INERT line reworded so push_gate_is_withdrawn holds, nothing_to_run const fn for clippy."; }
    // RAN: sprint643 Implement: the fill's Implement section; validate 728 clean, check-engine clean, guard ALL PASS exit 0 at b522674+working tree
    part libTestsAndTheResolvedHookImplementGateR1 : TestResult { :>> id = "d1a7ec58-8fbf-46de-a7fc-e5454fd4a163"; :>> outcome = VerdictKind::pass; :>> judgedAgainst = "b522674"; :>> judgedAt = "2026-09-09T18:40:00-06:00"; :>> judgedBy = "claudeOpus5"; }
    verification libTestsAndTheResolvedHookReviewGate : Test { :>> id = "9821dcf2-f087-4012-a705-6ef3b9031ad5"; :>> title = "Sprint 643 review gate — three passes per D0172"; :>> createdAt = "2026-09-10"; :>> createdBy = "claudeOpus5"; :>> method = VerificationMethod::inspect; :>> procedureText = "Three passes per D0172: (1) a downstream project with no keel-cli/src sees lib = false and no behaviour change; the hook copies only for a binary resolving INTO the self-build's target dir; (2) the guards.rs test now states the property (cites only what is in force) instead of a snapshot, so a future synopsis citation cannot go red for being new; (3) the lib run adds ~15 s to an ARMED land only - INERT lands print the set and run nothing, as before."; }
    // RAN: sprint643 Review: the fill's Review section; validate 728 clean, check-engine clean, guard ALL PASS exit 0 at b522674+working tree
    part libTestsAndTheResolvedHookReviewGateR1 : TestResult { :>> id = "e138e155-da4a-4118-bdca-1307cf125567"; :>> outcome = VerdictKind::pass; :>> judgedAgainst = "b522674"; :>> judgedAt = "2026-09-09T18:40:00-06:00"; :>> judgedBy = "claudeOpus5"; }
    verification libTestsAndTheResolvedHookCloseOutGate : Test { :>> id = "d049a04c-2958-4d6b-bd17-7f9b101cbf0c"; :>> title = "Sprint 643 closeOut gate (autonomous, D0049)"; :>> createdAt = "2026-09-10"; :>> createdBy = "claudeOpus5"; :>> method = VerificationMethod::inspect; :>> procedureText = "validate clean, check-engine clean, guard ALL PASS exit 0; both resolvers stamped at the pre-commit tree b522674; issue437/438 triaged through them; D0421/D0422 remain proposed for the human, texts amended."; }
    // RAN: sprint643 CloseOut: the fill's CloseOut section; validate 728 clean, check-engine clean, guard ALL PASS exit 0 at b522674+working tree
    part libTestsAndTheResolvedHookCloseOutGateR1 : TestResult { :>> id = "456f55a6-2716-4182-add3-a2c75a373eb6"; :>> outcome = VerdictKind::pass; :>> judgedAgainst = "b522674"; :>> judgedAt = "2026-09-09T18:40:00-06:00"; :>> judgedBy = "claudeOpus5"; }
    verification libTestsAndTheResolvedHookRetroGate : Test { :>> id = "6391dc7e-cefe-4f35-b244-bc1d21b27a67"; :>> title = "Sprint 643 retro gate (autonomous, D0049)"; :>> createdAt = "2026-09-10"; :>> createdBy = "claudeOpus5"; :>> method = VerificationMethod::analyze; :>> procedureText = "Avoidable-issue scan: two controls in two days were probed against the wrong negative case because the case came from an assumption, not from reading the host (issue435: the token in prose; issue437: PATH resolution). D0388 says choose the cases BEFORE reading the tree - it does not say to read the HOST for the live case. issue439 is the third finding of this session in the same family: a measured fact nobody owned. No new item beyond issue439, already recorded and ranked."; }
    // RAN: sprint643 Retro: the fill's Retro section; validate 728 clean, check-engine clean, guard ALL PASS exit 0 at b522674+working tree
    part libTestsAndTheResolvedHookRetroGateR1 : TestResult { :>> id = "2767c9b6-2fe7-4d9b-8a11-1b974419e66d"; :>> outcome = VerdictKind::pass; :>> judgedAgainst = "b522674"; :>> judgedAt = "2026-09-09T18:40:00-06:00"; :>> judgedBy = "claudeOpus5"; }
}
