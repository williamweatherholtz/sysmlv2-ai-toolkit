// =====================================================================
// ProjectDeliveryS92 — Sprint 92: indicatorType (D0089). The general Indicator + Measurement item
// types (monitored measures; ISO-15939/PSM/SMM): computed/pulled/manual methods, `sysmlv2 indicators`
// (direction-aware status) + `record-measurement`, demonstrated across all 3 methods. Generalizes the
// git-only first cut (the human's correction). Frozen-schema unfreeze (human sign-off).
// Total: 8 pts  Ceremony: AUTONOMOUS (D0049); the schema unfreeze + Indicator model human-accepted (D0089).
// =====================================================================
package ProjectDeliveryS92 {
    private import EngineElement::*;
    private import EngineWork::*;
    private import EngineVerification::*;
    private import EngineRelationships::*;

    #CharteredBy dependency from indicatorTypeStory to d0089;

    part indicatorTypeStory : Story {
        :>> id = "63940516-2c7d-4e8f-b092-51627384bd01";
        :>> title = "Sprint 92: indicatorType (8 pts) — general Indicator + Measurement item types (computed/pulled/manual), `sysmlv2 indicators` + record-measurement, all 3 methods demonstrated (D0089)";
        :>> createdAt = "2026-06-22";
        :>> createdBy = "wweatherholtz";
        :>> kind = WorkKind::modeling;
        :>> priority = WorkPriority::p1;
        :>> owner = "claudeOpus";
        :>> estimatedPoints = 8;
    }

    action def DeliveryRunS92 {
        action storyIndicatorType;
        verification storyIndicatorTypeDoD : Test { :>> id = "63940516-2c7d-4e8f-b092-51627384bd02"; :>> method = VerificationMethod::test; :>> procedureText = "Add the general Indicator model (D0089; ISO-15939/PSM/SMM), generalizing my git-only first cut per the human's correction. SCHEMA (frozen unfreeze, human sign-off; SCHEMA_ORDER + _ID_TYPES updated): schema/core/indicator.sysml = part def Indicator (measures/goal/unit/method/collectionRef) + part def Measurement (value/measuredAt/source) + enums IndicatorGoal{minimize,maximize,observe} + MeasurementMethod{computed,pulled,manual}. An Indicator informs by DIRECTION (D0088), excluded from assurance/orphan required-edge sets (no verify/satisfy). TOOLING: view.rs indicators(root,trend) + indicator_status + measurement_series (source-agnostic: computed series via headline_at/trend_series; pulled/manual from #Measures-linked Measurements); main.rs cmd_indicators; write.rs append_measurement + main.rs cmd_record_measurement (#Measures edge). PROCESS/SKILL/VIEWPOINT: .engine/processes/indicator.sysml + indicator skill + skills-registry + indicators viewpoint. INSTANCES: 3 computed (coverage/velocity/volatility -> report headlines) + 1 pulled (avRegulationCount + 2 seed Measurements) + 1 manual (authoringFriction + 2 seed Measurements — the friction case, now first-class showing 'improving'). d0089 #ProspectiveChange keystone + Core-3 critiqued; doc-sync CLAUDE.md/usage.md. VERIFY: validate_schema 15/15; validate_instances 104/104; rust validate 105 (the .tracking authority, D0048 — Indicator/Measurement types resolve, only the pre-existing marker-edge kernel limit remains); `sysmlv2 indicators` shows all 3 methods (authoringFriction 4->2 improving, avRegulationCount 42->47 observed, computed current values); record-measurement appends + validates; clippy --workspace --all-targets -D warnings + cargo test (43 lib, +indicator_status_is_direction_aware) + guard all (12) green."; }
        part storyIndicatorTypeDoDR1 : TestResult { :>> id = "63940516-2c7d-4e8f-b092-51627384bd03"; :>> outcome = VerdictKind::pass; :>> judgedAgainst = "e35674d"; :>> judgedAt = "2026-06-22"; :>> judgedBy = "claudeOpus"; }
    }

    verification indicatorTypeRefineGate : Test { :>> id = "63940516-2c7d-4e8f-b092-51627384bd04"; :>> title = "Sprint 92 refine gate (DoR)"; :>> createdAt = "2026-06-22"; :>> createdBy = "claudeOpus"; :>> method = VerificationMethod::inspect; :>> procedureText = "DoR: the human asked to first-class the Indicator (from the D0088 measure spectrum — the friction case kept being forced into the requirement/verification frame), then corrected toward GENERALITY (git is a specialized indicator; need stock/regulation/twitter/survey too; some programmatic, some bespoke). Research grounded it in ISO-15939/PSM/SMM. Signed off: 'build the general model' + 'all 3 methods demonstrated'. Frozen-schema unfreeze accepted (D0089). estimatedPoints=8. #CharteredBy d0089. DoD accepted."; }
    part indicatorTypeRefineGateR1 : TestResult { :>> id = "63940516-2c7d-4e8f-b092-51627384bd05"; :>> outcome = VerdictKind::pass; :>> judgedAgainst = "e35674d"; :>> judgedAt = "2026-06-22"; :>> judgedBy = "claudeOpus"; }

    verification indicatorTypeStandupGate : Test { :>> id = "63940516-2c7d-4e8f-b092-51627384bd06"; :>> title = "Sprint 92 standup gate"; :>> createdAt = "2026-06-22"; :>> createdBy = "claudeOpus"; :>> method = VerificationMethod::inspect; :>> procedureText = "Approach: schema/core/indicator.sysml (Indicator/Measurement + 2 enums) + _schema_files SCHEMA_ORDER + _ID_TYPES; view.rs indicators/indicator_status/measurement_series (reuse headline_at/trend_series for computed); write.rs append_measurement (#Measures); main.rs cmd_indicators + cmd_record_measurement; process + skill + registry + viewpoint; instances for all 3 methods; D0089 + critiques + doc-sync. Watch: 'at' is a reserved keyword (use measuredAt); bare `dependency` isn't ingested (use #Measures/#Informs markers); add 'indicators' to VIEW_SUBCOMMANDS. No blockers."; }
    part indicatorTypeStandupGateR1 : TestResult { :>> id = "63940516-2c7d-4e8f-b092-51627384bd07"; :>> outcome = VerdictKind::pass; :>> judgedAgainst = "e35674d"; :>> judgedAt = "2026-06-22"; :>> judgedBy = "claudeOpus"; }

    verification indicatorTypeImplementGate : Test { :>> id = "63940516-2c7d-4e8f-b092-51627384bd08"; :>> title = "Sprint 92 implement gate"; :>> createdAt = "2026-06-22"; :>> createdBy = "claudeOpus"; :>> method = VerificationMethod::test; :>> procedureText = "Implemented schema + tooling + process/skill/viewpoint + instances + D0089 + critiques + doc-sync. VERIFY (live): validate_schema 15/15 (incl indicator.sysml); validate_instances 104/104 (incl d0089 + indicator process); rust validate 105 clean; `sysmlv2 indicators` = authoringFriction 4->2 [manual/improving], avRegulationCount 42->47 [pulled/observed], coverage 100% / velocity 281 / volatility 0 [computed]; record-measurement appended a datapoint the view picked up; clippy --workspace --all-targets -D warnings green; cargo test 43 lib pass; guard all (12) PASS (after adding 'indicators' to VIEW_SUBCOMMANDS — caught by viewpoint-renderer->assured cascade). The Indicator/Measurement types resolve in the kernel; only the pre-existing marker-edge limit (Verify/Resolves/Measures/Informs) remains in validate_tracking, which is non-authoritative (D0048)."; }
    part indicatorTypeImplementGateR1 : TestResult { :>> id = "63940516-2c7d-4e8f-b092-51627384bd09"; :>> outcome = VerdictKind::pass; :>> judgedAgainst = "e35674d"; :>> judgedAt = "2026-06-22"; :>> judgedBy = "claudeOpus"; }

    verification indicatorTypeReviewGate : Test { :>> id = "63940516-2c7d-4e8f-b092-51627384bd0a"; :>> title = "Sprint 92 review gate"; :>> createdAt = "2026-06-22"; :>> createdBy = "claudeOpus"; :>> method = VerificationMethod::inspect; :>> procedureText = "Diff reviewed. The model is the established ISO-15939/SMM one (measure vs measurement; objective/subjective method), mapped to compute-don't-store: computed series recompute from the repo; pulled/manual are irreducible recorded observations with provenance (a market-share/survey value can't be faked or recomputed — like a TestResult but carrying a value not a verdict). Indicator informs by DIRECTION, not a threshold (D0088) — so the friction case is now a first-class indicator showing 'improving', no longer mis-modeled as an un-verifiable Requirement. The direction-aware status is fully automatable (it needs only a (value,at) series) — nothing quantitative is authored on the Indicator. Honest scope: derived (indicator-of-indicators) measures + automated pulled-collection scrapers are documented future layers; the demonstrators seed pulled/manual data. Frozen-schema discipline held (sign-off, re-freeze). No bare-dependency edges (markers required)."; }
    part indicatorTypeReviewGateR1 : TestResult { :>> id = "63940516-2c7d-4e8f-b092-51627384bd0b"; :>> outcome = VerdictKind::pass; :>> judgedAgainst = "e35674d"; :>> judgedAt = "2026-06-22"; :>> judgedBy = "claudeOpus"; }

    verification indicatorTypeCloseOutGate : Test { :>> id = "63940516-2c7d-4e8f-b092-51627384bd0c"; :>> title = "Sprint 92 closeOut gate (autonomous, D0049)"; :>> createdAt = "2026-06-22"; :>> createdBy = "claudeOpus"; :>> method = VerificationMethod::inspect; :>> procedureText = "Autonomous closeOut (D0049): storyIndicatorType DoD recorded pass; Indicator + Measurement types live (schema 15/15, instances 104/104, rust 105); indicators view + record-measurement operational across computed/pulled/manual; process/skill/viewpoint registered; D0089 accepted + Core-3 critiqued; doc-sync done; clippy + cargo test (43) + guard all (12) green. Self-evidencing (D0051). The Indicator item type closes the D0088 measure-spectrum gap — a monitored measure now has a first-class home."; }
    part indicatorTypeCloseOutGateR1 : TestResult { :>> id = "63940516-2c7d-4e8f-b092-51627384bd0d"; :>> outcome = VerdictKind::pass; :>> judgedAgainst = "e35674d"; :>> judgedAt = "2026-06-22"; :>> judgedBy = "claudeOpus"; }

    verification indicatorTypeRetroGate : Test { :>> id = "63940516-2c7d-4e8f-b092-51627384bd0e"; :>> title = "Sprint 92 retro gate (autonomous, D0049)"; :>> createdAt = "2026-06-22"; :>> createdBy = "claudeOpus"; :>> method = VerificationMethod::analyze; :>> procedureText = "Autonomous retro (D0049). WELL: the human's correction (git is a SPECIALIZED indicator, not the general one) redirected to the right, standards-backed model (ISO-15939/PSM/SMM) — and grounding in that 25-year measurement-information-model made the design fall out cleanly: measure-vs-measurement, objective/subjective method, compute-where-reproducible/author-the-irreducible. The friction case landing as a first-class indicator showing 'improving' is a satisfying close on the original 'forced-into-verification' awkwardness (D0088->D0089). CAUGHT (avoidable-issue candidates, all caught pre-commit): (1) 'at' is a reserved SysML keyword (renamed measuredAt); (2) a bare `dependency from X to Y` parses but is NOT ingested as an edge — needs a #Marker (used #Measures/#Informs); (3) adding the `indicators` subcommand without adding it to the guard's VIEW_SUBCOMMANDS made viewpoint-renderer fail and CASCADE into assured. Lesson: when adding a subcommand that a viewpoint renderer names, update VIEW_SUBCOMMANDS in the same change — the guard set is coupled to the command set. Estimate 8 pts held. The general Indicator capability is operational across all three measurement methods."; }
    part indicatorTypeRetroGateR1 : TestResult { :>> id = "63940516-2c7d-4e8f-b092-51627384bd0f"; :>> outcome = VerdictKind::pass; :>> judgedAgainst = "e35674d"; :>> judgedAt = "2026-06-22"; :>> judgedBy = "claudeOpus"; }
}
