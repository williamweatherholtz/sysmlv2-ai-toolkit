// ProjectDeliveryS661 — Sprint 661: Close dcAdvanceRefusesAnyBoundStep (D0321 option A's second half): keel advance refuses --to any step whose earlier bound check is red, for ANY process, and the ceremony order it and three other readers enforce is read from the tree instead of a compiled table. Before this sprint the six-gate sequence lived in four places - orient.rs GATE_ORDER, guards.rs GATE_ORDER, algo.rs CEREMONY_GATES, and an include_str test holding one of them to delivery.sysml - and only the agile-workflow's steps had an in-loop refusal, hand-coded. After it: a ProcessStep may bind `gate:<phase>` (D0435, proposed), the six ceremony steps carry theirs through the D0434 transform's second run, orient::gate_order reads the workflow chain the bound phases belong to, and `keel advance <process> [--to <step>]` evaluates each step's guard or rule on the tree and refuses a forward move past a red one (D0436, proposed). The sprint also carries the finding made while recording its Decisions: check-engine passes a file keel check rejects (issue467).. EXECUTE. 5 pts.
package ProjectDeliveryS661 {
    private import EngineElement::*;
    private import EngineWork::*;
    private import EngineVerification::*;
    private import EngineRelationships::*;

    #CharteredBy dependency from advanceRefusesAnyBoundStepStory to d0321;

    part advanceRefusesAnyBoundStepStory : Story {
        :>> id = "57088002-2765-4207-b006-b4e276f8ba63";
        :>> title = "Sprint 661: Close dcAdvanceRefusesAnyBoundStep (D0321 option A's second half): keel advance refuses --to any step whose earlier bound check is red, for ANY process, and the ceremony order it and three other readers enforce is read from the tree instead of a compiled table. Before this sprint the six-gate sequence lived in four places - orient.rs GATE_ORDER, guards.rs GATE_ORDER, algo.rs CEREMONY_GATES, and an include_str test holding one of them to delivery.sysml - and only the agile-workflow's steps had an in-loop refusal, hand-coded. After it: a ProcessStep may bind `gate:<phase>` (D0435, proposed), the six ceremony steps carry theirs through the D0434 transform's second run, orient::gate_order reads the workflow chain the bound phases belong to, and `keel advance <process> [--to <step>]` evaluates each step's guard or rule on the tree and refuses a forward move past a red one (D0436, proposed). The sprint also carries the finding made while recording its Decisions: check-engine passes a file keel check rejects (issue467). (5 pts)";
        :>> createdAt = "2026-09-10"; :>> createdBy = "claudeOpus5"; :>> kind = WorkKind::code; :>> priority = WorkPriority::p0; :>> owner = "claudeOpus5"; :>> estimatedPoints = 5;
    }

    action def DeliveryRunS661 {
        action storyAdvanceRefusesAnyBoundStep;
        verification storyAdvanceRefusesAnyBoundStepDoD : Test { :>> id = "783c2c08-4122-44ca-828a-9e4a9f4da139"; :>> method = VerificationMethod::test; :>> procedureText = "The DoD of dcAdvanceRefusesAnyBoundStep: sprint advance unchanged - `keel advance 660` reads the six gates in the same order and reports ceremony complete; the four existing cursor tests hold against the order read from the tree. Process form: `keel advance implementation` lists implDo/implReview/implClose as gate: bindings needing a run and implModel as judgment; `keel advance stpa-self --to stpa5Trigger` is PERMITTED naming the five judgment steps it did not judge; `keel advance decision-authoring` reports unenforceable-by-step exit 0. Fixture test a_bound_earlier_step_refuses_the_advance_while_red_and_permits_it_when_green: two steps both bound to doc-guard-count, guards.md carrying '999 forward guards' (red) refuses --to s2 exit 1, the corrected file permits it exit 0, --to s1 permitted, --to s9 refused as unknown. Fixture test a_process_with_no_bound_step_is_unenforceable_not_refused: exit 0 in both forms, unknown process exit 1. orient::gate_order: this tree's order is the six (this_trees_ceremony_order_is_the_delivery_chain); a tree binding no gate has no order (no_gate_binding_means_no_order); a chain linearises as written, a fork in branch order, a cycle orders nothing. Guard step-check-resolves resolves gate:refine and fails gate:closeout in a fixture with a declared chain; live 13 scanned 0 violations. Transform second run: 6 bound, 7 already, 38/185 conserved, untouched-line hash equal. cli-surface-declared PASS after the mirror row was regenerated; hardening stepEnforcement checkedCount 13 of 185."; }
        // RAN: keel-suite.exe suite --touched . -> 546 passed 0 failed; cargo clippy --release --all-targets -- -D warnings -> Finished; keel advance 660 . / implementation . / decision-authoring . / stpa-self --to stpa5Trigger . -> each exit 0 as the DoD lists; keel guard --no-receipt . -> 71 PASS incl. step-check-resolves 13 scanned
        part storyAdvanceRefusesAnyBoundStepDoDR1 : TestResult { :>> id = "0d80c788-5214-4c6f-9e33-9d13a2c2494b"; :>> outcome = VerdictKind::pass; :>> judgedAgainst = "05c34777a99d73a6696832de4fe5b758a0796954"; :>> judgedAt = "2026-09-10T22:37:43Z"; :>> judgedBy = "claudeOpus5"; }
    }

    verification advanceRefusesAnyBoundStepRefineGate : Test { :>> id = "452d4786-07b3-44bb-bc3d-e1a6d86e6477"; :>> title = "Sprint 661 refine gate (DoR)"; :>> createdAt = "2026-09-10"; :>> createdBy = "claudeOpus5"; :>> method = VerificationMethod::inspect; :>> procedureText = "Five points, as sized: two process-change Decisions, a new module-level reader replacing four compiled copies, the process form of a command with its verdict evaluation through guards::run_one and view::check, a second transform run with its reconciliation, the CLI fact and mirror, and the doc-sync. Ready: dcAdvanceRefusesAnyBoundStep is head of whats-next after dcProcessStepDeclaresItsCheck closed at 05c3477 (CI success read from gh run list --json conclusion). Both Decisions are process-change and stay proposed under D0337; the sprint builds under them, the D0430 precedent. Known before the tree was read: the advance fixture's positive case is a red doc-guard-count (a guards.md line claiming a count), its negative the same file corrected; gate_order's positive is a bound phase in a declared chain, its negative a tree with no binding."; }
    // RAN: test
    part advanceRefusesAnyBoundStepRefineGateR1 : TestResult { :>> id = "29680913-7368-4d86-bd73-99815132b23b"; :>> outcome = VerdictKind::pass; :>> judgedAgainst = "05c34777a99d73a6696832de4fe5b758a0796954"; :>> judgedAt = "2026-09-10T22:37:43Z"; :>> judgedBy = "claudeOpus5"; }
    // RAN: keel whats-next . read dcAdvanceRefusesAnyBoundStep at the head of the frontier; points 5 set on the Story; #CharteredBy d0321 on the record
    part advanceRefusesAnyBoundStepRefineGateR2 : TestResult { :>> id = "ddae6281-6b23-4c43-8226-f55fb803148f"; :>> outcome = VerdictKind::pass; :>> judgedAgainst = "05c34777a99d73a6696832de4fe5b758a0796954"; :>> judgedAt = "2026-09-10T22:37:43Z"; :>> judgedBy = "claudeOpus5"; }
    verification advanceRefusesAnyBoundStepStandupGate : Test { :>> id = "976b98a0-9470-4444-b368-06cd47d87d7f"; :>> title = "Sprint 661 standup gate"; :>> createdAt = "2026-09-10"; :>> createdBy = "claudeOpus5"; :>> method = VerificationMethod::inspect; :>> procedureText = "Blocker at the start: none. 05c3477 is on origin; its land ran the touched set (546 passed, 244 s) and CI concluded success before this sprint touched keel-cli/src. Hazard known going in: the ceremony order is read by four callers and a wrong linearisation would refuse every sprint advance at once - handled by the live probe against sprint 660 before any record was written, and by the test that holds this tree's order to the six. Hazard not known going in: the instance gate accepted a file with unbalanced braces (issue467) - found because the tail of the file was printed after the edit, not because a gate said so."; }
    // RAN: keel validate . -> 752 tracking file(s) validated clean; keel check-engine . -> instance files validated clean; no blocker
    part advanceRefusesAnyBoundStepStandupGateR1 : TestResult { :>> id = "35ebc18b-976f-4871-ac40-fd5f7895a675"; :>> outcome = VerdictKind::pass; :>> judgedAgainst = "05c34777a99d73a6696832de4fe5b758a0796954"; :>> judgedAt = "2026-09-10T22:37:43Z"; :>> judgedBy = "claudeOpus5"; }
    verification advanceRefusesAnyBoundStepImplementGate : Test { :>> id = "ba696553-e2f2-4880-9391-914cf2791608"; :>> title = "Sprint 661 implement gate"; :>> createdAt = "2026-09-10"; :>> createdBy = "claudeOpus5"; :>> method = VerificationMethod::test; :>> procedureText = "Built in order. D0435 and D0436 recorded from draft files (process-change markers, proposed), their #DependsOn edges added by hand - and the insertion doubled a closing brace, which check-engine passed and keel check rejected; reproduced once deliberately with both commands, reverted, and recorded as issue467 in-field with resolver dcCheckEngineParsesEveryInstanceFile (placed after this sprint's item in the backlog - declaration order is priority). orient.rs: GATE_ORDER replaced by workflow_successions / workflow_phases / gate_order / linearise / gate_name with four tests; in_progress_sprints reads the order and its terminal. guards.rs: the constant deleted, the ceremony helpers take the order as &[String], the guard warns unenforceable-by-step on an empty order, the include_str module deleted, declared_check_names gains gate:<phase> from the chains, step-check-resolves hints the missing phase, the fixture gains a workflow file and the gate: positive/negative test. algo.rs: CEREMONY_GATES deleted, scan_delivery_files takes the order from audit. scaffold.rs: GATES becomes GATE_KINDS with a lookup, the loop iterates gate_order(root). cursor.rs replaced: sprint path unchanged over the read order, process path added (resolve_process, process_steps, evaluate, advance_process). The transform gained six agile-workflow gate bindings, dry-run reconciled and applied. commands.sysml cliAdvance invocation and synopsis updated; the guard cli-surface-declared then FAILED on the Rust mirror - the intended control - and cli_facts.rs was regenerated to match. CLAUDE.md's advance lines doc-synced. Build clean first try; live probes as the DoD lists; guard --no-receipt: every guard PASS, step-check-resolves 13."; }
    // RAN: keel-suite.exe suite --touched . -> 15 binaries ok, 546 passed 0 failed, 220 s (touched-receipt.toml outcome=pass); cargo clippy --release --all-targets -- -D warnings -> Finished, no diagnostics; keel advance 660 . -> ceremony complete; keel advance implementation . -> 3 gate: bindings need a run, 1 judgment; keel advance decision-authoring . -> unenforceable-by-step exit 0; keel advance stpa-self --to stpa5Trigger . -> PERMITTED exit 0
    part advanceRefusesAnyBoundStepImplementGateR1 : TestResult { :>> id = "dcf8ccd8-8e5a-449c-a891-6ea6a6e1bd29"; :>> outcome = VerdictKind::pass; :>> judgedAgainst = "05c34777a99d73a6696832de4fe5b758a0796954"; :>> judgedAt = "2026-09-10T22:37:43Z"; :>> judgedBy = "claudeOpus5"; }
    // RAN: re-judged at 4bdb55a on the verifier's OWN run (issue468: the prior pass at 05c3477 was recorded on a receipt 46 minutes stale): keel suite --touched . outcome pass 659 passed 0 failed, stems algo cli_facts cursor guards orient scaffold touched, log touched-1789083931.log, receipt at 1789084365; scaffold tests pass against the declare_ceremony fixture
    part advanceRefusesAnyBoundStepImplementGateR2 : TestResult { :>> id = "2bcaaf04-e15a-4e46-8197-e30ca3ccf768"; :>> outcome = VerdictKind::pass; :>> judgedAgainst = "4bdb55a458f8b25a15f538a7b9f6bc1ee68c7034"; :>> judgedAt = "2026-09-10T23:34:32Z"; :>> judgedBy = "claudeOpus5"; }
    verification advanceRefusesAnyBoundStepReviewGate : Test { :>> id = "50c2ac37-e2b7-4ebf-a60c-c1acd71831b8"; :>> title = "Sprint 661 review gate — three passes per D0172"; :>> createdAt = "2026-09-10"; :>> createdBy = "claudeOpus5"; :>> method = VerificationMethod::inspect; :>> procedureText = "Three passes (D0172). Substance: the order is now a fact one function reads, and a downstream project that declares a different chain - or none - gets that chain, or an honest unenforceable-by-step, where before it got this project's six gates compiled in. The process form's claim is exactly as strong as the checks it names: it refuses only on a red guard or rule, lists judgment steps as not judged, and reports a gate binding as needing a run - it cannot become a checklist that gatekeeps the human, which is the D0426 direction. Record: two Decisions proposed with markers and DependsOn edges, issue467 in-field with a resolver whose DoD names its two probe cases, the DoD of the item untouched from its authoring. Process: the cli-surface-declared guard fired on the mirror before anything was claimed about the CLI - the control worked as its Decision said; check-engine did NOT fire on a file it should have, and that is the sprint's finding."; }
    // RAN: keel guard --no-receipt . -> 71 PASS, no FAIL/ERROR; step-check-resolves 13 scanned 0 violations; ceremony 662 scanned 0 violations; cli-surface-declared 109 scanned 0 violations; keel sync-claude --check . -> keel-owned subset matches (46 registry skills)
    part advanceRefusesAnyBoundStepReviewGateR1 : TestResult { :>> id = "4f4e32dc-802e-4d8a-9dd2-8b5073847fed"; :>> outcome = VerdictKind::pass; :>> judgedAgainst = "05c34777a99d73a6696832de4fe5b758a0796954"; :>> judgedAt = "2026-09-10T22:37:43Z"; :>> judgedBy = "claudeOpus5"; }
    verification advanceRefusesAnyBoundStepCloseOutGate : Test { :>> id = "69e7b0c1-263c-42f9-b415-b06b96c38929"; :>> title = "Sprint 661 closeOut gate (autonomous, D0049)"; :>> createdAt = "2026-09-10"; :>> createdBy = "claudeOpus5"; :>> method = VerificationMethod::inspect; :>> procedureText = "Delivered: D0435 and D0436 (proposed), orient::gate_order replacing four compiled copies of the ceremony order, keel advance's process form with two fixture tests, the ceremony guard and audit reading the order from the tree, the scaffold iterating it, six gate bindings on the agile-workflow steps through the transform's second run, step-check-resolves' gate: class with its fixture tests, the cliAdvance fact and its mirror, CLAUDE.md doc-sync, issue467 recorded and triaged with dcCheckEngineParsesEveryInstanceFile authored, dcAdvanceRefusesAnyBoundStep's DoD passed on the verifier's receipt. Not delivered, by design: per-step results for a process run other than a sprint - the process form evaluates tree-wide checks, so PERMITTED means the earlier steps' checks hold now, not that the steps were performed in order (D0436 STATED)."; }
    // RAN: keel validate . -> 752 clean; keel check-engine . -> clean; keel guard --no-receipt . -> 71 PASS; every DoD probe in the Implement receipt exit 0
    part advanceRefusesAnyBoundStepCloseOutGateR1 : TestResult { :>> id = "5f0fd01e-d05f-489e-a26b-12adca2bdbb3"; :>> outcome = VerdictKind::pass; :>> judgedAgainst = "05c34777a99d73a6696832de4fe5b758a0796954"; :>> judgedAt = "2026-09-10T22:37:43Z"; :>> judgedBy = "claudeOpus5"; }
    verification advanceRefusesAnyBoundStepRetroGate : Test { :>> id = "1a71b655-81e4-4d6b-bbfd-ad318464a7cc"; :>> title = "Sprint 661 retro gate (autonomous, D0049)"; :>> createdAt = "2026-09-10"; :>> createdBy = "claudeOpus5"; :>> method = VerificationMethod::analyze; :>> procedureText = "Autonomous retro (D0049). AVOIDABLE-ISSUE SCAN: one Issue this sprint. issue467, check-engine clean over an unparseable file: avoidable in the sense that `keel check` already had the parser and check-engine did not call it; not caught because the commit tier trusts check-engine's verdict and no test hands check-engine a malformed file. FINDING 1 -> backlog: dcCheckEngineParsesEveryInstanceFile, High, placed at the frontier's second position. FINDING 2, process improvement: the doubled brace came from insert_before with an anchor that spanned two closing lines - the helper did what it was asked, the ask was wrong; the tail was printed after the edit, which is the only reason it was seen. A textpatch operation that inserts before a closing brace should not need the caller to restate the brace; recorded here, not as an item, because one occurrence is not a pattern (D0311 counts recurrence). FINDING 3, process: the cli-surface-declared guard caught the un-regenerated mirror on the first guard run, before the help was read - a control firing on the agent's act, evidence for keeping it (D0426 evidenced). Sprint size: five points, one sitting."; }
    // RAN: AVOIDABLE-ISSUE SCAN recorded in the sprint's retro text: issue467 (check-engine clean over a file keel check rejects) with resolver dcCheckEngineParsesEveryInstanceFile in .tracking/backlog.sysml; keel validate . -> 752 clean
    part advanceRefusesAnyBoundStepRetroGateR1 : TestResult { :>> id = "b36686d8-81e5-49e6-bf1e-31fd684650cd"; :>> outcome = VerdictKind::pass; :>> judgedAgainst = "05c34777a99d73a6696832de4fe5b758a0796954"; :>> judgedAt = "2026-09-10T22:37:43Z"; :>> judgedBy = "claudeOpus5"; }
}
