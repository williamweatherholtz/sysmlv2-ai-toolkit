// ProjectDeliveryS487 — Sprint 487: the control map is reconciled against what actually enforces. EXECUTE. 5 pts.
package ProjectDeliveryS487 {
    private import EngineElement::*;
    private import EngineWork::*;
    private import EngineVerification::*;
    private import EngineRelationships::*;

    #CharteredBy dependency from controlMapReconciledStory to d0254;

    part controlMapReconciledStory : Story {
        :>> id = "80da8ddb-258b-49e2-91bc-d1fde5d6ae96";
        :>> title = "Sprint 487: five firing controls enter the map, and a standing check keeps it reconciled (5 pts)";
        :>> createdAt = "2026-08-29"; :>> createdBy = "claudeOpus5"; :>> kind = WorkKind::code; :>> priority = WorkPriority::p0; :>> owner = "claudeOpus5"; :>> estimatedPoints = 5;
    }

    action def DeliveryRunS487 {
        action storyControlMapReconciled;
        verification storyControlMapReconciledDoD : Test { :>> id = "91fb9349-5b3b-4f31-b7f4-b1d24ce987f2"; :>> method = VerificationMethod::test; :>> procedureText = "RESOLVES issue304 and issue305. Reconciled the control map against control-events.toml, the declaration already cross-checked against the events the binary EMITS - so the chain is binary to events to controls, rather than a second hand-maintained list that would be one more thing to drift. FOUND FIVE firing controls absent from the map, two of them BLOCKING: ctlPostEditGate (the per-edit fast tier, which refused a parse error during sprint 483), ctlTurnBoundaryGate (validate plus every guard at the turn boundary), ctlAuditAdherence (CI guard-set monotonicity, D0209), ctlAdoptionCheck (foreign-tree gate on every push, D0231), ctlOverrideObligation (single-use path-bound unlock with a tracked obligation, D0176). Each is declared with a hazard edge. Every one of the 16 declared events now names its control or says why it is instrumentation. VERIFY: guard 54 control-map-reconciled; probe it fires; clippy, full suite, validate, check-engine, 54 guards.: DELIVERED BACKLOG ITEMS: <items>. <what done means, verified how>."; }
        // RAN: // RAN: cargo clippy --workspace --all-targets -D warnings clean; cargo test --workspace --release -> 16 suites ok, 0 FAILED (incl. adoption_check_can_fail 2 passed, which CAUGHT guard 54 mis-firing on a fresh scaffold before it shipped); keel guard -> 54 guards, 0 FAIL; arming probe: injected event naming ctlDoesNotExist -> FAIL 17/1, removed -> PASS 16/0; keel gate --fast 548 clean
        part storyControlMapReconciledDoDR1 : TestResult { :>> id = "538921a9-57d0-42ec-81d5-051dcfcbf800"; :>> outcome = VerdictKind::pass; :>> judgedAgainst = "e2876d6"; :>> judgedAt = "2026-08-29"; :>> judgedBy = "claudeOpus5"; }
    }

    verification controlMapReconciledRefineGate : Test { :>> id = "55af2a17-350f-45c6-b9b7-8ad926580d5a"; :>> title = "Sprint 487 refine gate (DoR)"; :>> createdAt = "2026-08-29"; :>> createdBy = "claudeOpus5"; :>> method = VerificationMethod::inspect; :>> procedureText = "READY: chartered by D0254, which named implemented-but-undeclared as the third failure class. The anchor was chosen rather than invented - control-events.toml already exists and is already cross-checked against the binary's emitted events by control-event-coverage (D0193), so reconciling the map against IT chains to the code instead of to another list."; }
    verification controlMapReconciledStandupGate : Test { :>> id = "50c28b67-b6d7-495c-b16a-2068de1dbbce"; :>> title = "Sprint 487 standup gate"; :>> createdAt = "2026-08-29"; :>> createdBy = "claudeOpus5"; :>> method = VerificationMethod::inspect; :>> procedureText = "No blocker. One thing worth recording: this sprint exists because reading the model back after sprints 485 and 486 showed issue303 and issue304 computing as CLOSED while both sprints' closeOut gates said they stay OPEN. The work was found by the verify-don't-assert discipline, not by any check."; }
    verification controlMapReconciledImplementGate : Test { :>> id = "02adb66a-2ede-4dba-9e29-25fba4ff463a"; :>> title = "Sprint 487 implement gate"; :>> createdAt = "2026-08-29"; :>> createdBy = "claudeOpus5"; :>> method = VerificationMethod::test; :>> procedureText = "RAN: cargo build; keel guard; arming probe; clippy; full suite. GUARD 54 control-map-reconciled: PASS 16 scanned / 0 violations. PROVEN ARMED, not assumed - injected an event naming ctlDoesNotExist: FAIL 17 scanned / 1 violation; removed it: PASS 16 / 0. It also catches the SILENT case: an event declaring no control at all is a violation, because silence must read as a gap rather than as consent. RE-POINTED two #Resolves edges (issue303 to the open dcProveTheRemainingControls task, issue304 to this story) - both had pointed at completed sprints whose DoDs said 'in part'."; }
    verification controlMapReconciledReviewGate : Test { :>> id = "9d11605e-79d1-434e-9ed3-cdad1b47d35a"; :>> title = "Sprint 487 review gate — three passes per D0172"; :>> createdAt = "2026-08-29"; :>> createdBy = "claudeOpus5"; :>> method = VerificationMethod::inspect; :>> procedureText = "THREE PASSES. (1) A CONTROL I BUILT WAS WRONG AND WAS REMOVED, not tuned: a wording gate for issue305 flagged .tracking/backlog.sysml on its first run against the real corpus - a false positive - and was file-scoped while #Resolves edges and DoD prose live in different files. D0232 records three prior attempts to gate verdict wording at 111, 35 and 1 false positives; this was the fourth and calibrated no better. Recorded as declared-unenforceable WITH the reason in process-enforcement.toml rather than shipped or left silent. (2) THE ANCHOR IS RIGHT: reconciling against control-events.toml chains to the binary through an existing cross-check; a fresh list would drift. (3) SCOPE: five controls found and declared; issue303's seven remaining probes are a separate OPEN task, not folded in."; }
    verification controlMapReconciledCloseOutGate : Test { :>> id = "7a070089-6f6a-47dd-a206-9abc703212db"; :>> title = "Sprint 487 closeOut gate (autonomous, D0049)"; :>> createdAt = "2026-08-29"; :>> createdBy = "claudeOpus5"; :>> method = VerificationMethod::inspect; :>> procedureText = "CLOSED. Control map: 9 entries before this session, 15 now (one from D0254, five here). Evidence: 3 of 15 - one armed by view-probe, two proven by test. That ratio got WORSE by declaring honestly, which is the point: the previous 1-of-9 with uncoveredHazards [] was a cleaner-looking number over a less complete map. issue304 and issue305 resolve here; issue303 stays OPEN against dcProveTheRemainingControls, whose seven probes are real work nobody has done."; }
    verification controlMapReconciledRetroGate : Test { :>> id = "c538e8ac-e8ef-4404-8be8-a2d189e72a35"; :>> title = "Sprint 487 retro gate (autonomous, D0049)"; :>> createdAt = "2026-08-29"; :>> createdBy = "claudeOpus5"; :>> method = VerificationMethod::analyze; :>> procedureText = "FINDING, and it is about my own output rather than the codebase: I wrote 'resolves issueNNN in part' into two DoDs, and both issues computed as CLOSED while the sprints' own closeOut gates said they stay open. Resolution is computed from resolver completion and has no partial state - so prose asserted a nuance the computation cannot see, in the self-serving direction, and the open-issue count fell while the work did not get done. Nothing flagged it; reading the computed view back did. SECOND FINDING: the attempted control for it was itself a defect. Language policing has now failed four times in this codebase on recorded evidence, and the correct response was to record the property as unenforceable with its reason rather than ship a miscalibrated guard - an honest gap beats a check that cries wolf, because a guard with false positives is one an actor learns to ignore, which is D0197's whole thesis. BECOMES TRACKED WORK: nothing new; issue305 is resolved by the honest declaration, and issue303's remaining probes are already tracked."; }
}
