// ProjectDeliveryS145 — Sprint 145: honestStateGateReclassify (D0098) — split commit gates into
// HONEST-STATE (integrity, hard-block) vs SELF-ASSURANCE (completeness, non-blocking burndown). This
// step demotes `assured` + `critique`-coverage from the enforced GUARD_NAMES (13 -> 11) and the
// pre-commit hook; they stay runnable diagnostics surfaced as burndown. Unblocks requirement-first
// authoring. CHANGE (CR): Decision d0098 (accepted by wweatherholtz). 4 pts. AUTONOMOUS ceremony (D0049).
package ProjectDeliveryS145 {
    private import EngineElement::*;
    private import EngineWork::*;
    private import EngineVerification::*;
    private import EngineRelationships::*;

    #CharteredBy dependency from honestStateGateReclassifyStory to d0098;

    part honestStateGateReclassifyStory : Story {
        :>> id = "63940516-2c7d-4e8f-c145-51627384c001";
        :>> title = "Sprint 145: honestStateGateReclassify (4 pts) — demote assured + critique-coverage to non-blocking burndown; gates enforce honesty, not completeness (D0098)";
        :>> createdAt = "2026-06-24"; :>> createdBy = "wweatherholtz"; :>> kind = WorkKind::code; :>> priority = WorkPriority::p1; :>> owner = "claudeOpus"; :>> estimatedPoints = 4;
    }

    action def DeliveryRunS145 {
        action storyHonestStateGateReclassify;
        verification storyHonestStateGateReclassifyDoD : Test { :>> id = "63940516-2c7d-4e8f-c145-51627384c002"; :>> method = VerificationMethod::test; :>> procedureText = "D0098 step 1: a commit gate must enforce HONESTY (the model is truthful/well-formed/traceable), NOT COMPLETENESS (are we done). The enforced `assured` (composite readiness) + `critique` (critique-COVERAGE) were hard-gating completeness — punishing requirement-first authoring (a governed uncovered Need/SR could not be committed; root of issue046/047) and inviting metric-gaming. FIX: removed `critique` + `assured` from guards.rs GUARD_NAMES (13 -> 11) and the .githooks/pre-commit assurance block; they remain RUNNABLE diagnostics (`keel guard assured`/`critique`, `keel assured`/`critique-coverage`) and become NON-BLOCKING burndown. The 11 enforced honest-state guards stay hard (actors, acceptance-events, sprint-coverage, ceremony, charter, process-change, issues, viewpoint-renderer, manifest-coverage, critic-independence [critique INDEPENDENCE = honesty, kept], process-skill). The D0079 honesty core (compute-don't-author, never fake a pass) is kept in full. Downstream `keel init` projects inherit automatically (their scaffold hook runs `keel guard` over GUARD_NAMES). VERIFIED (live): `keel guard` = 11 guards, ALL PASS; `keel guard assured` + `keel guard critique` still run as diagnostics (they currently FAIL flagging d0098 itself as uncovered/uncritiqued — the honest burndown, NOT blocking the commit, demonstrating the doctrine). clippy -D warnings green; keel validate 158 clean; kernel validate_instances re-checks d0098 in pre-commit. The requirement-rootedness HARD guard + the tier-satisfaction burndown + the orient burndown surfacing are the NEXT step (requirementRootednessGuard)."; }
        part storyHonestStateGateReclassifyDoDR1 : TestResult { :>> id = "63940516-2c7d-4e8f-c145-51627384c003"; :>> outcome = VerdictKind::pass; :>> judgedAgainst = "6a1c60c"; :>> judgedAt = "2026-06-24"; :>> judgedBy = "claudeOpus"; }
    }

    verification honestStateGateReclassifyRefineGate : Test { :>> id = "63940516-2c7d-4e8f-c145-51627384c004"; :>> title = "Sprint 145 refine gate (DoR)"; :>> createdAt = "2026-06-24"; :>> createdBy = "claudeOpus"; :>> method = VerificationMethod::inspect; :>> procedureText = "DoR: the assurance gates structurally block requirement-first authoring (issue046/047). Human set the doctrine — honest-state gates (hard) vs self-assurance/completeness (non-blocking burndown); pure (nothing completeness-related blocks); rootedness is hard honesty. Decision d0098 accepted ('accepted'). estimatedPoints=4. #CharteredBy d0098. DoR met."; }
    part honestStateGateReclassifyRefineGateR1 : TestResult { :>> id = "63940516-2c7d-4e8f-c145-51627384c005"; :>> outcome = VerdictKind::pass; :>> judgedAgainst = "6a1c60c"; :>> judgedAt = "2026-06-24"; :>> judgedBy = "claudeOpus"; }
    verification honestStateGateReclassifyStandupGate : Test { :>> id = "63940516-2c7d-4e8f-c145-51627384c006"; :>> title = "Sprint 145 standup gate"; :>> createdAt = "2026-06-24"; :>> createdBy = "claudeOpus"; :>> method = VerificationMethod::inspect; :>> procedureText = "Approach: this step = the demotion only (well-bounded). Remove assured+critique from GUARD_NAMES (keep run_one arms so they stay runnable) + the pre-commit hook block; update guard doc-comments + the unknown-guard help; doc-sync CLAUDE.md (13->11 + the honest-vs-assurance doctrine). The additive rootedness hard-gate + tier-satisfaction + orient burndown are deferred to requirementRootednessGuard. No blockers."; }
    part honestStateGateReclassifyStandupGateR1 : TestResult { :>> id = "63940516-2c7d-4e8f-c145-51627384c007"; :>> outcome = VerdictKind::pass; :>> judgedAgainst = "6a1c60c"; :>> judgedAt = "2026-06-24"; :>> judgedBy = "claudeOpus"; }
    verification honestStateGateReclassifyImplementGate : Test { :>> id = "63940516-2c7d-4e8f-c145-51627384c008"; :>> title = "Sprint 145 implement gate"; :>> createdAt = "2026-06-24"; :>> createdBy = "claudeOpus"; :>> method = VerificationMethod::test; :>> procedureText = "GUARD_NAMES 13->11 (assured/critique removed, run_one arms kept); pre-commit hook assurance block removed; guard doc-comments + unknown-guard help updated; CLAUDE.md §5 doc-synced. VERIFIED: `keel guard` = 11 ALL PASS; `keel guard assured`/`critique` still runnable (FAIL as burndown on d0098, non-blocking); clippy green; keel validate 158 clean."; }
    part honestStateGateReclassifyImplementGateR1 : TestResult { :>> id = "63940516-2c7d-4e8f-c145-51627384c009"; :>> outcome = VerdictKind::pass; :>> judgedAgainst = "6a1c60c"; :>> judgedAt = "2026-06-24"; :>> judgedBy = "claudeOpus"; }
    verification honestStateGateReclassifyReviewGate : Test { :>> id = "63940516-2c7d-4e8f-c145-51627384c00a"; :>> title = "Sprint 145 review gate"; :>> createdAt = "2026-06-24"; :>> createdBy = "claudeOpus"; :>> method = VerificationMethod::inspect; :>> procedureText = "Diff reviewed. The demotion is clean + correct: completeness no longer hard-gates (requirement-first unblocked) while every integrity guard + the D0079 no-fake-pass honesty core stay hard. The split is principled — critique INDEPENDENCE (honesty) stays enforced, critique COVERAGE (completeness) demotes. Committing this change WITHOUT critiquing d0098 (it shows on the burndown) is itself the doctrine demonstrated honestly. Additive rootedness/burndown correctly deferred. Clean."; }
    part honestStateGateReclassifyReviewGateR1 : TestResult { :>> id = "63940516-2c7d-4e8f-c145-51627384c00b"; :>> outcome = VerdictKind::pass; :>> judgedAgainst = "6a1c60c"; :>> judgedAt = "2026-06-24"; :>> judgedBy = "claudeOpus"; }
    verification honestStateGateReclassifyCloseOutGate : Test { :>> id = "63940516-2c7d-4e8f-c145-51627384c00c"; :>> title = "Sprint 145 closeOut gate (autonomous, D0049)"; :>> createdAt = "2026-06-24"; :>> createdBy = "claudeOpus"; :>> method = VerificationMethod::inspect; :>> procedureText = "Autonomous closeOut (D0049): DoD pass; gates now enforce honesty not completeness; assured/critique are non-blocking burndown. `keel guard` 11 ALL PASS; clippy + keel validate 158 + kernel validate_instances (pre-commit) green. Self-evidencing (D0051) except d0098 acceptance (human confirmation, held). CR commit. requirementRootednessGuard (rootedness hard-gate + tier-satisfaction + orient burndown) is next; then serveRequirementsTrace is unblocked."; }
    part honestStateGateReclassifyCloseOutGateR1 : TestResult { :>> id = "63940516-2c7d-4e8f-c145-51627384c00d"; :>> outcome = VerdictKind::pass; :>> judgedAgainst = "6a1c60c"; :>> judgedAt = "2026-06-24"; :>> judgedBy = "claudeOpus"; }
    verification honestStateGateReclassifyRetroGate : Test { :>> id = "63940516-2c7d-4e8f-c145-51627384c00e"; :>> title = "Sprint 145 retro gate (autonomous, D0049)"; :>> createdAt = "2026-06-24"; :>> createdBy = "claudeOpus"; :>> method = VerificationMethod::analyze; :>> procedureText = "Autonomous retro (D0049). WELL: the human caught two anti-patterns in sequence — metric-gaming (WIP flags to make assured green) then the deeper conflation of honesty with completeness — yielding a cleaner doctrine than the original design (assured as a HARD gate was itself the bug). The demotion is small + reversible + immediately unblocks requirement-first. AVOIDABLE-ISSUE SCAN: the root cause was a gate enforcing completeness as if it were correctness; the doctrine (D0098) is now the guard against re-introducing self-assurance gates. LESSON: a gate that forces either a fake pass or a blocked commit is mis-designed — gate honesty, surface completeness. NON-blocking: committing with d0098 itself on the burndown demonstrates the doctrine; rootedness/tier-satisfaction/orient-burndown follow in requirementRootednessGuard. Estimate 4 pts held."; }
    part honestStateGateReclassifyRetroGateR1 : TestResult { :>> id = "63940516-2c7d-4e8f-c145-51627384c00f"; :>> outcome = VerdictKind::pass; :>> judgedAgainst = "6a1c60c"; :>> judgedAt = "2026-06-24"; :>> judgedBy = "claudeOpus"; }
}
