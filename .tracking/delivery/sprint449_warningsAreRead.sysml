// ProjectDeliveryS449 — Sprint 449: the guard verdict states its warning population, and a superseded Release stops warning - detected-but-unread was the drift (issue244, D0214). EXECUTE. 2 pts.
package ProjectDeliveryS449 {
    private import EngineElement::*;
    private import EngineWork::*;
    private import EngineVerification::*;
    private import EngineRelationships::*;

    #CharteredBy dependency from warningsAreReadStory to d0214;

    part warningsAreReadStory : Story {
        :>> id = "5f54f490-5981-4c32-93ca-6df52857a9bb";
        :>> title = "Sprint 449: ALL PASS can no longer hide 80 warnings (2 pts)";
        :>> createdAt = "2026-08-24"; :>> createdBy = "claudeFable5"; :>> kind = WorkKind::code; :>> priority = WorkPriority::p0; :>> owner = "claudeFable5"; :>> estimatedPoints = 2;
    }

    action def DeliveryRunS449 {
        action storyWarningsAreRead;
        verification storyWarningsAreReadDoD : Test { :>> id = "ade2acbc-28f6-40ff-be5b-7cdf597ee9ea"; :>> method = VerificationMethod::test; :>> procedureText = "DELIVERED: dcWarningsAreRead (resolves issue244, MEDIUM, and it is the sharpest answer to the human's question about reports drifting from truth). THE DEFECT, measured by the panel's reducer: `keel guard` printed the bare words [guard] ALL PASS while emitting 80 warnings across 10 guards, and one of those was itself a live report-vs-truth contradiction that had shipped and gone unread - 'tag v0.2.0 points at e2c812f but its Release item records commit 425145d'. I read ALL PASS and skated past those warnings repeatedly in the same session, including in commit messages asserting the gate was clean. The panel explicitly REFUSED to add a new drift detector, on the evidence that this engine already detects more than it triages, so another detector makes the felt problem worse. TWO SUBTRACTIVE CHANGES: (1) the verdict line states its population - 'ALL PASS - N warning(s) across M guard(s), NOT violations and NOT blocking, but UNREAD until someone reads them: <guard names>' - no new surface, no new computation, no new cost, and ALL PASS can no longer be read without also reading how much went unread; (2) release-recorded now excludes a Release carrying an inbound #Supersede edge, matching what the sibling views already do for superseded Needs (issue088), requirements (issue127) and tasks (issue100) - because superseding is the ONLY correction path available to a non-owner (D0108), that warning was unresolvable BY CONSTRUCTION, which is precisely what trains a reader to ignore an entire class. COUNTS MOVED and both sides are reported per the issue127 precedent: release-recorded 5 scanned / 1 warning -> 5 scanned / 0 warnings; the whole suite 82 warnings across 11 guards -> 79 across 9. THE TAG WARNING IS TRIAGED, NOT SUPPRESSED: git establishes that 425145d IS an ancestor of the tag two commits back, so the record was TRUE WHEN WRITTEN and the tag was cut later; the tag is published so it must not move (D0129), and release020 is owned by another actor, so a new release020Shipped records the shipped commit and SUPERSEDES the field - the sanctioned non-owner correction, and the change that made the guard fix necessary. VERIFIED: the verdict line prints the population against this repo (79/9); the release warning is gone; 251 lib tests pass; clippy clean; validate + all 48 guards + check-engine + rules green. NOT DONE, deliberately: no new detector, no new gate, and no warning promoted to blocking - D0098 keeps completeness off the commit path."; }
        part storyWarningsAreReadDoDR1 : TestResult { :>> id = "99f53f7e-e104-472b-b279-9ac2f06e6c17"; :>> outcome = VerdictKind::pass; :>> judgedAgainst = "36694872766baf4eb45c4aec55dc23986743394d"; :>> judgedAt = "2026-08-24"; :>> judgedBy = "claudeFable5"; }
    }

    verification warningsAreReadRefineGate : Test { :>> id = "577f724d-61b4-458f-a607-bd14f1c598e4"; :>> title = "Sprint 449 refine gate (DoR)"; :>> createdAt = "2026-08-24"; :>> createdBy = "claudeFable5"; :>> method = VerificationMethod::inspect; :>> procedureText = "DoR. Resolves issue244 (MEDIUM by severity, highest by evidence): the reducer measured 80 warnings riding under ALL PASS with one live contradiction among them, and named detected-but-unread as the drift mechanism that gets WORSE as assurance work proceeds. Scope: state the population at the verdict, and make the one unresolvable warning resolvable. Explicitly NOT in scope: any new detector. 2 points."; }
    part warningsAreReadRefineGateR1 : TestResult { :>> id = "06b8bf8c-0d7e-4272-bd79-1332de63e2ed"; :>> outcome = VerdictKind::pass; :>> judgedAgainst = "36694872766baf4eb45c4aec55dc23986743394d"; :>> judgedAt = "2026-08-24"; :>> judgedBy = "claudeFable5"; }
    verification warningsAreReadStandupGate : Test { :>> id = "6f7701bf-757a-48d0-8be2-7c4f4b56237b"; :>> title = "Sprint 449 standup gate"; :>> createdAt = "2026-08-24"; :>> createdBy = "claudeFable5"; :>> method = VerificationMethod::inspect; :>> procedureText = "Approach: put the number where the verdict is already read rather than building a surface to hold it - the cheapest possible change that makes the population unmissable. Then fix the reason the population could not go down: release-recorded ignored #Supersede, so a correction made through the engine's own sanctioned mechanism could never clear it. Both guards.rs and the verdict line change a computed view's numbers, so D0214 co-commits as the marked Decision and reports pre/post counts, per the issue127 precedent. No blockers."; }
    part warningsAreReadStandupGateR1 : TestResult { :>> id = "d5d38010-f016-4615-9198-74885b9e3aa9"; :>> outcome = VerdictKind::pass; :>> judgedAgainst = "36694872766baf4eb45c4aec55dc23986743394d"; :>> judgedAt = "2026-08-24"; :>> judgedBy = "claudeFable5"; }
    verification warningsAreReadImplementGate : Test { :>> id = "01f6bc5a-1881-44f3-8602-8901c4cc231a"; :>> title = "Sprint 449 implement gate"; :>> createdAt = "2026-08-24"; :>> createdBy = "claudeFable5"; :>> method = VerificationMethod::test; :>> procedureText = "Verified by running the freshness-checked binary: the verdict line prints 'ALL PASS - 79 warning(s) across 9 guard(s) ... : actors, ceremony, viewpoint-renderer, manifest-coverage, attestation-substance, decision-requirement-link, sequence-multiplicity, parser-coverage, decision-scaffolding'; keel guard release-recorded went from 1 warning to 0; the tag/Release facts were established from git (merge-base --is-ancestor: 425145d IS an ancestor of v0.2.0, rev-list --count: 2 commits between); 251 lib tests pass; cargo clippy --workspace --all-targets -D warnings clean; validate 500 + check-engine + rules green."; }
    part warningsAreReadImplementGateR1 : TestResult { :>> id = "992d8626-c3ae-4ec2-b155-6c21d93a6388"; :>> outcome = VerdictKind::pass; :>> judgedAgainst = "36694872766baf4eb45c4aec55dc23986743394d"; :>> judgedAt = "2026-08-24"; :>> judgedBy = "claudeFable5"; }
    verification warningsAreReadReviewGate : Test { :>> id = "049ec278-4ec3-4d17-b5d6-699d1bd4944d"; :>> title = "Sprint 449 review gate — three passes per D0172"; :>> createdAt = "2026-08-24"; :>> createdBy = "claudeFable5"; :>> method = VerificationMethod::inspect; :>> procedureText = "PASS 1, CLAIMS: the verdict string, both guard counts and the git ancestry facts are quoted read-backs. PASS 2, BOUNDARY: (i) the verdict states the population but does NOT triage it - 79 warnings remain, and this sprint deliberately does not promote any of them, because D0098 forbids gating completeness and the panel's whole argument is that the marginal detector now subtracts value; what changed is that the number is unmissable. (ii) The supersede exclusion is textual (`#Supersede dependency from X to Y` scanned across .tracking) rather than model-derived, consistent with how this guard already reads Release blocks; a qualified name would not match. (iii) release020's own commit field is untouched - superseding leaves the original readable, which is the point. PASS 3, OWN DIFF: two honest findings against myself in this sprint. First, appending two follow-on backlog items had silently placed them ABOVE a High-issue resolver, and since declaration order IS priority (D0052) that re-prioritized the frontier; priority-inversion warned, and I reordered rather than explaining it away - which is the guard doing exactly its job on its author. Second, the warning I set out to fix could not have been fixed by anyone who was not the Release's owner, so my first instinct (edit the commit field) would have violated D0108; the supersede path is both correct and what forced the guard fix. WHAT A REVIEWER SHOULD ATTACK: whether stating a large number at the verdict actually causes reading, or merely normalises '79 warnings' as the expected banner - it is an honesty fix, not a triage fix, and if the number does not fall over the next weeks that is evidence the fix was insufficient rather than that the warnings are fine."; }
    part warningsAreReadReviewGateR1 : TestResult { :>> id = "492504b4-5e19-47d7-a58b-2db2c8678c7a"; :>> outcome = VerdictKind::pass; :>> judgedAgainst = "36694872766baf4eb45c4aec55dc23986743394d"; :>> judgedAt = "2026-08-24"; :>> judgedBy = "claudeFable5"; }
    verification warningsAreReadCloseOutGate : Test { :>> id = "c8d3ba7c-f2bb-4ee2-b57a-f96cf760c08b"; :>> title = "Sprint 449 closeOut gate (autonomous, D0049)"; :>> createdAt = "2026-08-24"; :>> createdBy = "claudeFable5"; :>> method = VerificationMethod::inspect; :>> procedureText = "Autonomous closeOut (D0049). issue244 resolved: the population is stated at the verdict, the one unresolvable warning is now resolvable and resolved, and the live tag contradiction is triaged through the sanctioned non-owner path. Backlog reordered so the frontier ranks the High-issue resolver first. Four panel findings remain: issue239, issue245, issue243, issue246."; }
    part warningsAreReadCloseOutGateR1 : TestResult { :>> id = "5aac6a99-17fb-4db7-a972-2fb6015e71ac"; :>> outcome = VerdictKind::pass; :>> judgedAgainst = "36694872766baf4eb45c4aec55dc23986743394d"; :>> judgedAt = "2026-08-24"; :>> judgedBy = "claudeFable5"; }
    verification warningsAreReadRetroGate : Test { :>> id = "152f09c9-d450-4868-baf9-541991148b07"; :>> title = "Sprint 449 retro gate (autonomous, D0049)"; :>> createdAt = "2026-08-24"; :>> createdBy = "claudeFable5"; :>> method = VerificationMethod::analyze; :>> procedureText = "Autonomous retro (D0049). AVOIDABLE-ISSUE SCAN under rcRecurrence: (1) a NEW recurrence class worth naming - I appended tracked items to the end of a backlog whose ORDER carries meaning, and thereby changed priorities I did not intend to change; the durable rule is that appending to an ordered list is a semantic act, and the guard that caught it (priority-inversion) is the model of what a good warning does. (2) The deeper lesson of this sprint is one I was personally the subject of: a warning that CANNOT be cleared teaches the reader to ignore every warning, so an unresolvable-by-construction check is worse than no check - it spends the reader's attention and returns nothing. Any future warning should be shipped with its clearing path demonstrated. WELL: the fix is genuinely subtractive - no new command, no new guard, no new gate - and it closed a real shipped contradiction along the way; the panel's refusal to add a detector was the right call and the evidence for it was already in the repo's own output. Estimate 2 pts, delivered 2."; }
    part warningsAreReadRetroGateR1 : TestResult { :>> id = "d4a91e0a-6190-4f72-9cb3-111de28f52ae"; :>> outcome = VerdictKind::pass; :>> judgedAgainst = "36694872766baf4eb45c4aec55dc23986743394d"; :>> judgedAt = "2026-08-24"; :>> judgedBy = "claudeFable5"; }
}
