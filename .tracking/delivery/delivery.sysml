// =====================================================================
// ProjectDelivery — Delivery-workflow dogfood (dogfoodDelivery, 2026-06-11).
// One Story (foldWhatsNext) run through the full loop:
//   refine (DoR) → standup → implement → review → closeOut
// Phase gates authored here. DeliveryRun action def is read by query.py —
// `storyFoldWhatsNext` appears done once storyFoldWhatsNextR1 is appended.
// =====================================================================
package ProjectDelivery {
    private import EngineElement::*;
    private import EngineWork::*;
    private import EngineVerification::*;

    // ====================================================================
    // The Story being run through the loop
    // ====================================================================
    part foldWhatsNextStory : Story {
        :>> id = "412d390a-1e6b-4f24-9af6-fc5ab279946f";
        :>> title = "foldWhatsNext: merge whats_next.py into query.py workflows subcommand";
        :>> createdAt = "2026-06-11";
        :>> createdBy = "claudeOpus";
        :>> kind = WorkKind::code;
        :>> priority = WorkPriority::p1;
        :>> owner = "claudeOpus";
        :>> estimatedPoints = 2;
    }

    // ====================================================================
    // Delivery-loop backlog — one action per phase; query.py reads this.
    // DoD: storyFoldWhatsNextDoD must pass; TestResult appended on closeOut.
    // ====================================================================
    action def DeliveryRun {
        action storyFoldWhatsNext;
        verification storyFoldWhatsNextDoD : Test { :>> id = "7069d5ef-41a8-4a5f-96e2-6335681de0d9"; :>> method = VerificationMethod::test; :>> procedureText = "query.py workflows subcommand resolves the six workflow DAGs with parity to whats_next.py; whats_next.py retired; validate_all green; single query tool"; }
        part storyFoldWhatsNextR1 : TestResult { :>> id = "5c6d7e8f-9a0b-4c1d-2e3f-4a5b6c7d8e9f"; :>> outcome = VerdictKind::pass; :>> judgedAgainst = "5282ad3"; :>> judgedAt = "2026-06-11"; :>> judgedBy = "claudeOpus"; }
    }

    // ====================================================================
    // Phase gates (one per Delivery phase)
    // TestResults appended when each phase closes.
    // ====================================================================
    verification refineGate : Test {
        :>> id = "84457426-a219-4a22-9abe-06eb5483ccff";
        :>> title = "refine phase gate (DoR)";
        :>> createdAt = "2026-06-11";
        :>> createdBy = "claudeOpus";
        :>> method = VerificationMethod::inspect;
        :>> procedureText = "Story title clear; DoD criterion exists with method; no unmet dependencies; code I/O defined; DoR passes.";
    }
    part refineGateR1 : TestResult { :>> id = "f615ad49-05a1-43ab-aa82-0c8945448990"; :>> outcome = VerdictKind::pass; :>> judgedAgainst = "65a4f78"; :>> judgedAt = "2026-06-11"; :>> judgedBy = "claudeOpus"; }

    verification standupGate : Test {
        :>> id = "baa94f76-9569-429b-b272-18af645735b6";
        :>> title = "standup phase gate";
        :>> createdAt = "2026-06-11";
        :>> createdBy = "claudeOpus";
        :>> method = VerificationMethod::inspect;
        :>> procedureText = "Story in-progress; implementation approach stated; no new blockers discovered at standup.";
    }
    part standupGateR1 : TestResult { :>> id = "f6a7b8c9-d0e1-4f2a-3b4c-5d6e7f8a9b0c"; :>> outcome = VerdictKind::pass; :>> judgedAgainst = "65a4f78"; :>> judgedAt = "2026-06-11"; :>> judgedBy = "claudeOpus"; }

    verification implementGate : Test {
        :>> id = "07b8c9d0-e1f2-4a3b-4c5d-6e7f8a9b0c1d";
        :>> title = "implement phase gate";
        :>> createdAt = "2026-06-11";
        :>> createdBy = "claudeOpus";
        :>> method = VerificationMethod::test;
        :>> procedureText = "query.py workflows outputs valid JSON for all six workflows; whats_next.py deleted; validate_all green; query.py orient still works.";
    }
    part implementGateR1 : TestResult { :>> id = "3a4b5c6d-7e8f-4a9b-0c1d-2e3f4a5b6c7d"; :>> outcome = VerdictKind::pass; :>> judgedAgainst = "65a4f78"; :>> judgedAt = "2026-06-11"; :>> judgedBy = "claudeOpus"; }

    verification reviewGate : Test {
        :>> id = "18c9d0e1-f2a3-4b4c-5d6e-7f8a9b0c1d2e";
        :>> title = "review phase gate";
        :>> createdAt = "2026-06-11";
        :>> createdBy = "claudeOpus";
        :>> method = VerificationMethod::inspect;
        :>> procedureText = "Implementation diff reviewed; no regressions in orient/whats-next/suspect subcommands; code is clean.";
    }
    part reviewGateR1 : TestResult { :>> id = "4b5c6d7e-8f9a-4b0c-1d2e-3f4a5b6c7d8e"; :>> outcome = VerdictKind::pass; :>> judgedAgainst = "65a4f78"; :>> judgedBy = "claudeOpus"; :>> judgedAt = "2026-06-11"; }

    verification closeOutGate : Test {
        :>> id = "29d0e1f2-a3b4-4c5d-6e7f-8a9b0c1d2e3f";
        :>> title = "closeOut phase gate";
        :>> createdAt = "2026-06-11";
        :>> createdBy = "claudeOpus";
        :>> method = VerificationMethod::confirmation;
        :>> procedureText = "foldWhatsNextR1 recorded in backlog (pass); storyFoldWhatsNextR1 recorded in DeliveryRun (pass); query.py orient shows foldWhatsNext as done; user accepts.";
    }
    part closeOutGateR1 : TestResult { :>> id = "7e8f9a0b-1c2d-4e3f-4a5b-6c7d8e9f0a1b"; :>> outcome = VerdictKind::pass; :>> judgedAgainst = "5282ad3"; :>> judgedAt = "2026-06-11"; :>> judgedBy = "wweatherholtz"; }
}
