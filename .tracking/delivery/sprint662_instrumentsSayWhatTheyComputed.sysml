// ProjectDeliveryS662 — Sprint 662: Two instruments that reported an answer they had not computed, both the D0387 class, both found in one day: `keel check-engine` reported '.engine instance files validated clean' over a Decision file the parser rejects (issue467), because both of its passes read `if let Ok(pkg)` and dropped the Err; and the touched receipt held the previous run's `pass, 546` while a run was in progress (issue468), because touched::run wrote the receipt only when cargo returned - D0387's running stub had been applied to the suite receipt and not to the sibling beside it. The sprint also repairs the two scaffold unit tests whose fixture declared no workflow chain after D0435 made the scaffold read the ceremony order from the tree - the failure the land caught and the verifier's stale receipt hid.. EXECUTE. 3 pts.
package ProjectDeliveryS662 {
    private import EngineElement::*;
    private import EngineWork::*;
    private import EngineVerification::*;
    private import EngineRelationships::*;

    #CharteredBy dependency from instrumentsSayWhatTheyComputedStory to d0387;

    part instrumentsSayWhatTheyComputedStory : Story {
        :>> id = "6e5eda8f-234d-42b0-982e-e601326d58e2";
        :>> title = "Sprint 662: Two instruments that reported an answer they had not computed, both the D0387 class, both found in one day: `keel check-engine` reported '.engine instance files validated clean' over a Decision file the parser rejects (issue467), because both of its passes read `if let Ok(pkg)` and dropped the Err; and the touched receipt held the previous run's `pass, 546` while a run was in progress (issue468), because touched::run wrote the receipt only when cargo returned - D0387's running stub had been applied to the suite receipt and not to the sibling beside it. The sprint also repairs the two scaffold unit tests whose fixture declared no workflow chain after D0435 made the scaffold read the ceremony order from the tree - the failure the land caught and the verifier's stale receipt hid. (3 pts)";
        :>> createdAt = "2026-09-10"; :>> createdBy = "claudeOpus5"; :>> kind = WorkKind::code; :>> priority = WorkPriority::p0; :>> owner = "claudeOpus5"; :>> estimatedPoints = 3;
    }

    action def DeliveryRunS662 {
        action storyInstrumentsSayWhatTheyComputed;
        verification storyInstrumentsSayWhatTheyComputedDoD : Test { :>> id = "1e297973-7eed-4a81-bd46-231302d9d09c"; :>> method = VerificationMethod::test; :>> procedureText = "dcCheckEngineParsesEveryInstanceFile and dcTouchedReceiptSaysRunning pass their DoDs; the two scaffold tests pass against a fixture that declares the chain and one gate: binding, and a third test holds the D0435 negative (a tree binding no gate scaffolds no gate); issue467's description carries its correction; the lib suite and the touched set are green on the verifier's OWN run, whose receipt names this change set's stems and an `at` after its launch; the push lands and CI's conclusion is success."; }
        // RAN: keel suite --touched . 659 passed 0 failed on receipt at 1789084365 with stems of this change set (touched-1789083931.log); clippy Finished exit 0 (clippy662.log); scaffold, touched and engine_instance unit tests 15 passed (unit662.log); validate 753 clean; check-engine clean; guard 71/0
        part storyInstrumentsSayWhatTheyComputedDoDR1 : TestResult { :>> id = "f0bfd224-4136-4859-8cea-6b9b752bf0f8"; :>> outcome = VerdictKind::pass; :>> judgedAgainst = "4bdb55a458f8b25a15f538a7b9f6bc1ee68c7034"; :>> judgedAt = "2026-09-10T23:34:32Z"; :>> judgedBy = "claudeOpus5"; }
    }

    verification instrumentsSayWhatTheyComputedRefineGate : Test { :>> id = "e8304e56-2ae3-4945-b24b-9fbe9d006e97"; :>> title = "Sprint 662 refine gate (DoR)"; :>> createdAt = "2026-09-10"; :>> createdBy = "claudeOpus5"; :>> method = VerificationMethod::inspect; :>> procedureText = "Chartered by D0387 (deadRunsLeaveNoAnswer, accepted): an instrument claims its artefact before it computes, so a run that dies - or never registers a file - leaves nothing that reads as current. Both items are that clause on a surface D0387 did not name. Sized 3 points: two small library changes with fixture tests, one test-fixture repair, and the ceremony. Resolves issue467 and issue468."; }
    // RAN: keel advance sprint662 read current step Refine; story chartered d0387, 3 points; keel validate . 753 clean (verifier receipt verify662_receipt.txt)
    part instrumentsSayWhatTheyComputedRefineGateR1 : TestResult { :>> id = "e704e0b2-824a-4c02-ad19-cddd2914d50f"; :>> outcome = VerdictKind::pass; :>> judgedAgainst = "4bdb55a458f8b25a15f538a7b9f6bc1ee68c7034"; :>> judgedAt = "2026-09-10T23:34:32Z"; :>> judgedBy = "claudeOpus5"; }
    verification instrumentsSayWhatTheyComputedStandupGate : Test { :>> id = "19de5ae8-d78f-4985-8e6b-ed5e16bc6103"; :>> title = "Sprint 662 standup gate"; :>> createdAt = "2026-09-10"; :>> createdBy = "claudeOpus5"; :>> method = VerificationMethod::inspect; :>> procedureText = "Order: scaffold fixture first, because it is what blocks the push; then lib.rs validate_engine_instances with its two fixture tests; then touched.rs Phase and the running stub with its two render tests; then the records - the Issue, its resolver placed by priority, issue467's correction - and the verifier's run over the whole change set, read from its OWN receipt after the process exits."; }
    // RAN: order held: scaffold fixture, lib.rs check-engine parse diagnostic, touched.rs running stub, records; changed set in verifier receipt lists scaffold.rs lib.rs touched.rs backlog issues sprint662
    part instrumentsSayWhatTheyComputedStandupGateR1 : TestResult { :>> id = "080bdef1-eb57-4963-9286-d687181d9965"; :>> outcome = VerdictKind::pass; :>> judgedAgainst = "4bdb55a458f8b25a15f538a7b9f6bc1ee68c7034"; :>> judgedAt = "2026-09-10T23:34:32Z"; :>> judgedBy = "claudeOpus5"; }
    verification instrumentsSayWhatTheyComputedImplementGate : Test { :>> id = "2b066d73-afa3-4cf6-b8d3-d9593109d9cc"; :>> title = "Sprint 662 implement gate"; :>> createdAt = "2026-09-10"; :>> createdBy = "claudeOpus5"; :>> method = VerificationMethod::test; :>> procedureText = "scaffold.rs: declare_ceremony writes .engine/workflows/delivery.sysml with the five-link chain and .engine/processes/agile-workflow.sysml with one ProcessStep bound gate:refine; both fixtures call it; a_tree_binding_no_gate_scaffolds_no_gate removes the process file and asserts story + DoD and no gate. lib.rs: validate_engine_instances matches parse_pkg, registers Ok, pushes a Diagnostic for Err on every .engine file (schema or instance - a schema that fails to parse is silently absent from the registry), then validates the parsed instance files; parse_failure_diagnostic lifts the line from the `file:line:col` prefix and suggests `keel check <file>`; two tests in engine_instance_tests, the fixture decision well-formed and with one extra brace (line 6, got RBrace). touched.rs: Phase { NotRun, Running { started, log }, Done(&Run) } replaces Option<&Run> in render_receipt and write_receipt; run() writes the Running stub before cargo starts; the three NotRun callers updated; two render tests. The seven targeted unit tests pass (unit-fix2.log: 15 passed). issue467's description corrected in place under D0388 - validate refuses the same file, check-engine alone was blind."; }
    // RAN: keel suite --touched . run by the verifier in the foreground: outcome pass 659 passed 0 failed, lib 503 passed, receipt at 1789084365 later than launch, stems algo cli_facts cursor guards orient scaffold touched matching the change set, log touched-1789083931.log; cargo clippy --release --all-targets -D warnings Finished exit 0 after the doc-lint fix (clippy662.log); cargo test --lib touched::tests scaffold::tests engine_instance_tests 15 passed 0 failed (unit662.log)
    part instrumentsSayWhatTheyComputedImplementGateR1 : TestResult { :>> id = "50fb7525-d375-479b-b28d-d46cbe8528b8"; :>> outcome = VerdictKind::pass; :>> judgedAgainst = "4bdb55a458f8b25a15f538a7b9f6bc1ee68c7034"; :>> judgedAt = "2026-09-10T23:34:32Z"; :>> judgedBy = "claudeOpus5"; }
    verification instrumentsSayWhatTheyComputedReviewGate : Test { :>> id = "ef81ca75-c98d-40d8-8172-111a096d2b34"; :>> title = "Sprint 662 review gate — three passes per D0172"; :>> createdAt = "2026-09-10"; :>> createdBy = "claudeOpus5"; :>> method = VerificationMethod::inspect; :>> procedureText = "Delivered: check-engine names a parse failure with its line and skips nothing silently; the touched receipt says running while it runs; the scaffold fixtures declare what the scaffold now reads; issue468 recorded in-field with its resolver at the frontier's second position; sprint 661's Implement gate re-judged at this commit on a receipt of THIS change set. Not delivered, stated: the verifier's discipline - reading a receipt's `at` and `stems` against its own launch - is a prompt line, not a control; the control is the stub, which makes the stale read impossible rather than detectable."; }
    // RAN: keel check-engine . clean; live probe: check-engine on the fixture with one extra brace exits 1 naming line 25 got RBrace, well-formed fixture exits 0; keel guard --no-receipt . 71 PASS 0 FAIL; sync-claude --check matches (verifier receipt probes 7a-7d)
    part instrumentsSayWhatTheyComputedReviewGateR1 : TestResult { :>> id = "934ede98-dcff-4f70-82bd-5e78452e2d67"; :>> outcome = VerdictKind::pass; :>> judgedAgainst = "4bdb55a458f8b25a15f538a7b9f6bc1ee68c7034"; :>> judgedAt = "2026-09-10T23:34:32Z"; :>> judgedBy = "claudeOpus5"; }
    verification instrumentsSayWhatTheyComputedCloseOutGate : Test { :>> id = "4393fc8a-3e30-41b0-976a-e0d6f64b226e"; :>> title = "Sprint 662 closeOut gate (autonomous, D0049)"; :>> createdAt = "2026-09-10"; :>> createdBy = "claudeOpus5"; :>> method = VerificationMethod::inspect; :>> procedureText = "Sprint 662 closes on the verifier's receipt only (D0425): the touched set with the lib, clippy --all-targets, validate, check-engine, guard --no-receipt, sync-claude --check, and the receipt's own `at` and `stems` checked against the run's log. dcCheckEngineParsesEveryInstanceFile and dcTouchedReceiptSaysRunning DoD passes appended by the recorder from that receipt."; }
    // RAN: recorded from the verifier receipt only (D0425): touched 659/0 on this change set, clippy Finished, validate 753 clean, check-engine clean, guard 71/0, sync-claude matches; DoD passes for dcCheckEngineParsesEveryInstanceFile and dcTouchedReceiptSaysRunning appended from the same receipt
    part instrumentsSayWhatTheyComputedCloseOutGateR1 : TestResult { :>> id = "66a94761-f730-451d-bc7e-abaf561c88c1"; :>> outcome = VerdictKind::pass; :>> judgedAgainst = "4bdb55a458f8b25a15f538a7b9f6bc1ee68c7034"; :>> judgedAt = "2026-09-10T23:34:32Z"; :>> judgedBy = "claudeOpus5"; }
    verification instrumentsSayWhatTheyComputedRetroGate : Test { :>> id = "afc47f74-66c4-482d-911d-525e905cf118"; :>> title = "Sprint 662 retro gate (autonomous, D0049)"; :>> createdAt = "2026-09-10"; :>> createdBy = "claudeOpus5"; :>> method = VerificationMethod::analyze; :>> procedureText = "AVOIDABLE-ISSUE SCAN: one new Issue this sprint, issue468. Avoidable: yes - D0387 named the class and fixed one file; the sibling receipt was written by the same crate in the same week and nobody grepped for the second writer. FINDING 1 -> the control is in the binary now (dcTouchedReceiptSaysRunning); no new item. FINDING 2, process: the D0425 split held - the recorder wrote only what the verifier reported - and the verifier reported a file that was not its run's; a subagent's receipt must be read AFTER its process exits and checked for `at` and `stems`, and that instruction now lives in the verifier prompt while the stub makes the wrong read impossible. FINDING 3: the land's touched run is what caught it - D0421 evidenced, the second time in two sprints (issue459 was the first). FINDING 4, recurrence: `if let Ok(x)` dropping an Err that should be a diagnostic is the second instance (issue467 here; the reader in lib.rs had two) - one occurrence per site, counted, not yet an item (D0311: two = High at the next)."; }
    // RAN: AVOIDABLE-ISSUE SCAN: one new Issue this sprint, issue468, avoidable - D0387 named the class and fixed one receipt, the sibling writer in the same crate was not grepped for; control now in the binary (dcTouchedReceiptSaysRunning). Process finding: the D0425 split held and the verifier read a receipt that was not its own; the verifier prompt now requires a foreground run and at/stems checks while the running stub makes the stale read impossible. D0421 evidenced a second time (land caught what the stale receipt hid). Recurrence counted: if let Ok(x) dropping an Err that should be a diagnostic, second site, not yet an item
    part instrumentsSayWhatTheyComputedRetroGateR1 : TestResult { :>> id = "e262af20-2072-4ad2-9e25-23505f219a1c"; :>> outcome = VerdictKind::pass; :>> judgedAgainst = "4bdb55a458f8b25a15f538a7b9f6bc1ee68c7034"; :>> judgedAt = "2026-09-10T23:34:32Z"; :>> judgedBy = "claudeOpus5"; }
}
