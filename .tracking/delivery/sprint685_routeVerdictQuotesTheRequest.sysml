// ProjectDeliveryS685 — Sprint 685: Every route verdict the routing rig records names the text that decided it. Under D0459 (derived from us103, the human's words in st111: 'is the user asking for a view? if so, quote the text indicating so') routing_probe.py gains a second judging step, --rubric: the written six-question rubric .engine/tools/routing_rubric.md is put to a lower-capability model about each request of routing_prompts.toml, every yes carries a verbatim quote, and the pure judge_route REFUSES - never counts - a verdict that misses a question, has no quote, quotes words not in the request, or affirms no route. A re-run's disagreement is a finding naming both quotes (D0381), never a rate; the model and the cost are read from the CLI's own result and recorded beside the verdicts. Delivers dcRoutingVerdictQuotesItsEvidence and records its DoD result as the three paid runs actually read. EXECUTE.. EXECUTE. 3 pts.
package ProjectDeliveryS685 {
    private import EngineElement::*;
    private import EngineWork::*;
    private import EngineVerification::*;
    private import EngineRelationships::*;

    #CharteredBy dependency from routeVerdictQuotesTheRequestStory to d0459;

    part routeVerdictQuotesTheRequestStory : Story {
        :>> id = "8272734b-a848-4ac5-ad77-9aee0e605052";
        :>> title = "Sprint 685: Every route verdict the routing rig records names the text that decided it. Under D0459 (derived from us103, the human's words in st111: 'is the user asking for a view? if so, quote the text indicating so') routing_probe.py gains a second judging step, --rubric: the written six-question rubric .engine/tools/routing_rubric.md is put to a lower-capability model about each request of routing_prompts.toml, every yes carries a verbatim quote, and the pure judge_route REFUSES - never counts - a verdict that misses a question, has no quote, quotes words not in the request, or affirms no route. A re-run's disagreement is a finding naming both quotes (D0381), never a rate; the model and the cost are read from the CLI's own result and recorded beside the verdicts. Delivers dcRoutingVerdictQuotesItsEvidence and records its DoD result as the three paid runs actually read. EXECUTE. (3 pts)";
        :>> createdAt = "2026-09-13"; :>> createdBy = "claudeFable5"; :>> kind = WorkKind::code; :>> priority = WorkPriority::p0; :>> owner = "claudeFable5"; :>> estimatedPoints = 3;
    }

    action def DeliveryRunS685 {
        action storyRouteVerdictQuotesTheRequest;
        verification storyRouteVerdictQuotesTheRequestDoD : Test { :>> id = "e8256db8-0b1f-4e32-89c6-bc245b9702c1"; :>> method = VerificationMethod::test; :>> procedureText = "DELIVERED: .engine/tools/routing_rubric.md (the written rubric, six questions, answer format, the request fenced between markers); routing_probe.py --rubric NAME|all with judge_route (pure), rubric_probe (eight D0388 fixtures including the fabricated quote, the one-character paraphrase, the quoteless yes, the all-no answer, the missing question), rubric_one (stdin, no tools, no hooks, scratch cwd), rubric_finding (DISAGREES with both quotes / REFUSED with the refused reply / VERDICT / AGREES), run_rubric writing .keel/metrics/routing-rubric.json with model, spend, per-run cost and seconds; --probe runs both judges; claude_exe resolved once per process. Three paid runs over the 47 requests recorded; dcRoutingVerdictQuotesItsEvidenceDoD recorded with the outcome the runs support, naming the VERIFY clause that does not hold; issue510 recorded against the rubric with resolver dcRouteRubricQuestionsSeparateOnTheRequest in the backlog."; }
        // RAN: python .engine/tools/routing_probe.py --probe -> 15 PASS 0 FAIL; --rubric all x3 recorded in .keel/metrics/routing-rubric.json (model claude-haiku-4-5-20251001, spendUsd 1.70, perRunUsd 0.0362 on the last run); --rubric all --dry-run quotes the measured figure; --investigate release --dry-run unchanged; keel gate validate . -> 784 clean; keel gate check-engine . -> clean; keel sync-claude --check -> exit 0; dcRoutingVerdictQuotesItsEvidenceDoDR recorded fail naming the clause; issue510 + dcRouteRubricQuestionsSeparateOnTheRequest in the tree
        part storyRouteVerdictQuotesTheRequestDoDR1 : TestResult { :>> id = "a9888b63-9361-4e00-ba8e-59d43e69ae3f"; :>> outcome = VerdictKind::pass; :>> judgedAgainst = "ac38d48"; :>> judgedAt = "2026-09-12"; :>> judgedBy = "claudeFable5"; }
    }

    verification routeVerdictQuotesTheRequestRefineGate : Test { :>> id = "8f262d86-e3ce-45a7-8b3b-b102049b6ae1"; :>> title = "Sprint 685 refine gate (DoR)"; :>> createdAt = "2026-09-13"; :>> createdBy = "claudeFable5"; :>> method = VerificationMethod::inspect; :>> procedureText = "Chartered by D0459. Three points: one Python tool extended (no Rust, no guard, no hook), one written rubric, paid model runs whose cost is read back, and the ceremony. DoR: the DoD is authored on the backlog item; the item's edges (#DerivedFrom us103, #DependsOn d0381) are in the tree; nothing blocks it. NOT A PROCESS CHANGE: the rig is an investigation tool (D0378 C); no workflow, gate, schema, guard or hook changes. NOT A FORK: the shape is the human's instrument in their words and D0381's rule; the one choice inside it - refuse rather than count - is the DoD's own text."; }
    // RAN: the gate's text is the plan carried out in this commit; --probe 15/15, three paid runs recorded, gate validate 784 clean, check-engine clean
    part routeVerdictQuotesTheRequestRefineGateR1 : TestResult { :>> id = "dfa76af7-c763-4127-a061-2993a2897114"; :>> outcome = VerdictKind::proposed; :>> judgedAgainst = "ac38d48"; :>> judgedAt = "2026-09-12"; :>> judgedBy = "claudeFable5"; }
    verification routeVerdictQuotesTheRequestStandupGate : Test { :>> id = "1ff96e59-5980-4935-82a5-6fae16ceada9"; :>> title = "Sprint 685 standup gate"; :>> createdAt = "2026-09-13"; :>> createdBy = "claudeFable5"; :>> method = VerificationMethod::inspect; :>> procedureText = "Order: write the rubric file; add judge_route and its eight fixtures to --probe and make them hold before any model is paid for (D0388); add the runner and the record; run three requests, then all 47, then all 47 again for the disagreement check; critique the rubric from the refused replies and re-run; record D0459 with its edges, issue510 with its resolver task, the sprint, the DoD result with the runs as receipt; gate validate, check-engine, guard --no-receipt, sync-claude --check; commit."; }
    // RAN: the gate's text is the plan carried out in this commit; --probe 15/15, three paid runs recorded, gate validate 784 clean, check-engine clean
    part routeVerdictQuotesTheRequestStandupGateR1 : TestResult { :>> id = "352ff549-c75a-482a-91b0-4cd9230d80dc"; :>> outcome = VerdictKind::proposed; :>> judgedAgainst = "ac38d48"; :>> judgedAt = "2026-09-12"; :>> judgedBy = "claudeFable5"; }
    verification routeVerdictQuotesTheRequestImplementGate : Test { :>> id = "05f332a9-8d09-4856-b4ac-8c6498d526aa"; :>> title = "Sprint 685 implement gate"; :>> createdAt = "2026-09-13"; :>> createdBy = "claudeFable5"; :>> method = VerificationMethod::test; :>> procedureText = "routing_probe.py: RUBRIC, RUBRIC_OUT, ROUTES, RUBRIC_MODEL; judge_route (pure), rubric_probe (8 fixtures, all hold), parse_answer, rubric_one (prompt on stdin because the claude.cmd shim cuts an argument at its first newline; --tools '' because a model with Read went looking for a file - the first run errored 47 of 47 so; --no-session-persistence; hooks emptied; scratch cwd), rubric_finding, last_rubric, run_rubric, --rubric flag, claude_exe memoised and resolved in the main thread. routing_rubric.md written, then fenced (=== REQUEST BEGINS/ENDS ===) after two run-2 replies took the request for the task. Paid runs 2026-09-12 (claude-haiku-4-5-20251001, read from the CLI result): 3 requests $0.53; run 1 all 47 $1.60 - 46 verdicts, element-critique refused (not JSON); run 2 $1.57 - 44 verdicts, intake and engine-triage refused (not JSON: the reader asked for the request), 14 DISAGREES against run 1; run 3 under the fenced rubric $1.70 - 45 verdicts, indicator and repo-push refused (no route affirmed), 19 DISAGREES against run 2, 24 AGREES. Every recorded verdict's quote is a substring of its request by construction (judge_route refuses otherwise)."; }
    // RAN: python .engine/tools/routing_probe.py --probe -> 15 PASS 0 FAIL; --rubric all (run 3) -> 45 verdicts, 2 refused, 19 DISAGREES, model claude-haiku-4-5-20251001, spend 1.70 USD; git diff --stat -> routing_probe.py +~290 lines, routing_rubric.md new
    part routeVerdictQuotesTheRequestImplementGateR1 : TestResult { :>> id = "a9fb8f14-0808-415b-8efb-3c7eb23ab1ab"; :>> outcome = VerdictKind::pass; :>> judgedAgainst = "ac38d48"; :>> judgedAt = "2026-09-12"; :>> judgedBy = "claudeFable5"; }
    verification routeVerdictQuotesTheRequestReviewGate : Test { :>> id = "efc96b25-5762-44e2-8a24-a2e9f6df027d"; :>> title = "Sprint 685 review gate — three passes per D0172"; :>> createdAt = "2026-09-13"; :>> createdBy = "claudeFable5"; :>> method = VerificationMethod::inspect; :>> procedureText = "Three passes (D0172). Correctness: --probe holds 15 of 15 fixtures (7 scorer, 8 rubric) with 0 FAIL; the fabricated-quote fixture and the one-character paraphrase are refused by name. Honesty: the DoD result records the VERIFY clause 'the 47 prompts each produce a verdict' as NOT holding - one or two requests per run were refused as no-route-affirmed - rather than reading the refusals as the instrument working and calling the clause met; the self-disagreement is issue510 against the rubric, never a rate. Scope: the D0418 scorer is untouched except the once-per-process CLI lookup; no guard, hook, skill or process changed; facts.py reads only routing_prompts.toml and is unaffected."; }
    // RAN: the gate's text is the plan carried out in this commit; --probe 15/15, three paid runs recorded, gate validate 784 clean, check-engine clean
    part routeVerdictQuotesTheRequestReviewGateR1 : TestResult { :>> id = "64140b50-f74f-4834-9d63-06c748d78c37"; :>> outcome = VerdictKind::proposed; :>> judgedAgainst = "ac38d48"; :>> judgedAt = "2026-09-12"; :>> judgedBy = "claudeFable5"; }
    verification routeVerdictQuotesTheRequestCloseOutGate : Test { :>> id = "ce92d6be-4049-4e19-b27a-c7dcaf85b2dc"; :>> title = "Sprint 685 closeOut gate (autonomous, D0049)"; :>> createdAt = "2026-09-13"; :>> createdBy = "claudeFable5"; :>> method = VerificationMethod::inspect; :>> procedureText = "Closes on gate validate, gate check-engine, gate guard --no-receipt and sync-claude --check over the tree holding D0459, issue510, the resolver task, the rubric and the probe; on --probe 15/15; on the three paid runs recorded in .keel/metrics/routing-rubric.json with model and measured cost. dcRoutingVerdictQuotesItsEvidenceDoD result recorded with the outcome the runs support."; }
    // RAN: keel gate validate . -> 784 clean; keel gate check-engine . -> clean; keel gate guard --no-receipt . -> retro-backlog red only on the fill placeholder, re-run after the retro text (g685b); keel sync-claude --check -> exit 0; --probe 15/15
    part routeVerdictQuotesTheRequestCloseOutGateR1 : TestResult { :>> id = "93fb2f05-7df7-487a-96a7-6bfafeab8407"; :>> outcome = VerdictKind::proposed; :>> judgedAgainst = "ac38d48"; :>> judgedAt = "2026-09-12"; :>> judgedBy = "claudeFable5"; }
    verification routeVerdictQuotesTheRequestRetroGate : Test { :>> id = "e62893ab-9020-4359-abb3-f4301cb77f2f"; :>> title = "Sprint 685 retro gate (autonomous, D0049)"; :>> createdAt = "2026-09-13"; :>> createdBy = "claudeFable5"; :>> method = VerificationMethod::analyze; :>> procedureText = "AVOIDABLE-ISSUE SCAN, one finding tracked, three fixed at the root in this commit, one not a finding (D0131). TRACKED: the instrument disagreed with itself - three runs of the rubric over the 47 requests read the same quoted span as different routes on 14 then 19 named requests and affirmed no route for one or two each run; per D0381 that is a defect of the CHECK, recorded as issue510 with resolver dcRouteRubricQuestionsSeparateOnTheRequest (added to the backlog in this commit, last in declaration order), and dcRoutingVerdictQuotesItsEvidenceDoD is recorded fail naming the clause rather than read as met. FIXED AT THE ROOT, no item: (1) the first paid run errored 47 of 47 - the claude.cmd shim is run by cmd.exe, which cuts an argument at its first newline, so the model never saw the rubric, and a model holding a Read tool went looking for a file instead of answering; the rubric now goes in on stdin and the run has no tools; (2) a per-run shutil.which raced the CLI updater replacing the shim (The batch file cannot be found) and a worker sys.exit took the run down - claude_exe is memoised and resolved in the main thread for both judges; (3) two run-2 replies took a request about requests arriving as speech for their own task - the rubric fences the request between markers and says it is not addressed to the reader. NOT A FINDING: a cd to an unset temp path fell through and created rubric_try under the repository root; the git status read that the commit procedure already requires caught it before any add, and it was removed - a one-off shell error with no tool behind it to control. Cost of the sprint's paid runs, measured: 0.24 + 0.53 + 1.60 + 1.57 + 1.70 USD."; }
    // RAN: one finding tracked: issue510 with resolver dcRouteRubricQuestionsSeparateOnTheRequest; three root fixes in routing_probe.py / routing_rubric.md; retro-backlog guard read on the working tree (g685b)
    part routeVerdictQuotesTheRequestRetroGateR1 : TestResult { :>> id = "1395d318-9fa0-4720-84b5-5bf1151c8ea9"; :>> outcome = VerdictKind::proposed; :>> judgedAgainst = "ac38d48"; :>> judgedAt = "2026-09-12"; :>> judgedBy = "claudeFable5"; }
}
