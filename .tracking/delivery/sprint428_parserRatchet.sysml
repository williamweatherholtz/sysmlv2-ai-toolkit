// ProjectDeliveryS428 — Sprint 428: the parser TCB gains its ratchet and its property suite: new invisibility goes red, skip-freedom is generated, not assumed (issue231). EXECUTE. 1 pts.
package ProjectDeliveryS428 {
    private import EngineElement::*;
    private import EngineWork::*;
    private import EngineVerification::*;
    private import EngineRelationships::*;

    #CharteredBy dependency from parserRatchetStory to d0187;

    part parserRatchetStory : Story {
        :>> id = "a6e5f8c6-3adf-475a-8c1d-98665c982783";
        :>> title = "Sprint 428: the blind spot gets a fence (1 pts)";
        :>> createdAt = "2026-08-23"; :>> createdBy = "claudeFable5"; :>> kind = WorkKind::code; :>> priority = WorkPriority::p0; :>> owner = "claudeFable5"; :>> estimatedPoints = 1;
    }

    action def DeliveryRunS428 {
        action storyParserRatchet;
        verification storyParserRatchetDoD : Test { :>> id = "fff7e100-49a5-4553-9999-04b8cb3ee519"; :>> method = VerificationMethod::test; :>> procedureText = "DELIVERED: dcParserCoverageRatchet (resolves issue231, the process-value panel's formal-methods finding: the parser is the TCB of every guard and view, and its skipped-statement census was a warning whose count could grow silently). TWO HALVES: (1) THE RATCHET - .engine/contracts/parser-coverage-baseline.toml declares the committed baseline (7, the known legacy successions); the parser-coverage guard now goes RED when the live count EXCEEDS baseline (new invisibility is a violation), keeps warning at any nonzero count (legacy invisibility stays visible), warns to ratchet DOWN when the count shrinks, fails loud on a malformed contract, and states non-adoption when the contract is absent (D0136) - never the D0132 all-or-nothing trap. (2) SKIP-FREEDOM BY GENERATION - the keel-parser proptest suite gains supported_statements_are_never_skipped: random compositions of every supported statement form (parts with attrs, verifications, plain and markered dependencies, satisfy, allocate, actions) must parse with pkg.skipped empty, so a parser regression that silently drops a supported form is caught by generation rather than by whoever next reads the census (the ShardStore lightweight-formal-methods pattern the panel cited). VERIFIED: negative probe - a planted connect statement pushed the count to 8 and turned the guard RED with the exceeds-baseline message, removal green; the PBT runs green in the suite; workspace clippy clean; guards.md synced."; }
        part storyParserRatchetDoDR1 : TestResult { :>> id = "70b4a899-cf1f-4f1f-9ae6-07c6ab1d13ef"; :>> outcome = VerdictKind::pass; :>> judgedAgainst = "f760170eb8b54758875aa8b071a0ccd2139148ca"; :>> judgedAt = "2026-08-22"; :>> judgedBy = "claudeFable5"; }
    }

    verification parserRatchetRefineGate : Test { :>> id = "8dc12675-4468-4ba2-ba7e-7a8d21b958cd"; :>> title = "Sprint 428 refine gate (DoR)"; :>> createdAt = "2026-08-23"; :>> createdBy = "claudeFable5"; :>> method = VerificationMethod::inspect; :>> procedureText = "DoR. Chartered from the panel's issue231. In scope: the baseline contract, the guard ratchet, the generation suite, doc-sync. Out of scope (stated): parse-print round-trip identity - keel-parser has no printer, and building one for the test's sake would be ceremony; skip-freedom is the property that guards the TCB boundary. 1 point."; }
    part parserRatchetRefineGateR1 : TestResult { :>> id = "27d709b4-c56f-4d62-8339-6bc9be55b861"; :>> outcome = VerdictKind::pass; :>> judgedAgainst = "f760170eb8b54758875aa8b071a0ccd2139148ca"; :>> judgedAt = "2026-08-22"; :>> judgedBy = "claudeFable5"; }
    verification parserRatchetStandupGate : Test { :>> id = "9e519392-b93e-4f6c-9046-642a885cd840"; :>> title = "Sprint 428 standup gate"; :>> createdAt = "2026-08-23"; :>> createdBy = "claudeFable5"; :>> method = VerificationMethod::inspect; :>> procedureText = "Approach: exceed-goes-red / presence-warns / shrink-prompts-ratchet - three behaviors, each chosen against a named prior failure (D0132 all-or-nothing, the scroll-past warning class, silent bound decay); the baseline is a contract FILE so raising it is a visible diff in the same commit as its cause. No blockers."; }
    part parserRatchetStandupGateR1 : TestResult { :>> id = "e7f4b7f4-1ba1-4a5e-8828-af8f221e5ac2"; :>> outcome = VerdictKind::pass; :>> judgedAgainst = "f760170eb8b54758875aa8b071a0ccd2139148ca"; :>> judgedAt = "2026-08-22"; :>> judgedBy = "claudeFable5"; }
    verification parserRatchetImplementGate : Test { :>> id = "940fb5b5-1b33-448a-afb9-5b19bd726531"; :>> title = "Sprint 428 implement gate"; :>> createdAt = "2026-08-23"; :>> createdBy = "claudeFable5"; :>> method = VerificationMethod::test; :>> procedureText = "Verified by running: keel guard parser-coverage green at baseline 7; the planted unsupported statement (connect) read count 8, guard FAIL with the issue231 message, revert green; cargo test -p keel-parser including supported_statements_are_never_skipped green; workspace clippy pedantic+nursery clean; all 47 guards pass."; }
    part parserRatchetImplementGateR1 : TestResult { :>> id = "439eb4d0-b75e-4591-afb5-f1d6d3325e9d"; :>> outcome = VerdictKind::pass; :>> judgedAgainst = "f760170eb8b54758875aa8b071a0ccd2139148ca"; :>> judgedAt = "2026-08-22"; :>> judgedBy = "claudeFable5"; }
    verification parserRatchetReviewGate : Test { :>> id = "9e7cb38d-5382-488f-8536-0406448c01a4"; :>> title = "Sprint 428 review gate — three passes per D0172"; :>> createdAt = "2026-08-23"; :>> createdBy = "claudeFable5"; :>> method = VerificationMethod::inspect; :>> procedureText = "PASS 1, CLAIMS: probe outputs quoted from this session. PASS 2, BOUNDARY: the ratchet bounds the COUNT, not the CLASS - seven skipped successions could in principle become seven skipped somethings-else without tripping it; the census head in the warning is what makes that visible, and the PBT bounds the supported side. PASS 3, OWN DIFF: none needed this sprint - the compiler and probes caught nothing because the change reused patterns proven in sprints 422-427. WHAT A REVIEWER SHOULD ATTACK: the strategy list in arb_supported_statement is hand-enumerated - a newly supported form someone forgets to add there is silently un-generated; the honest fix would derive the strategies from the parser's own dispatch table, noted as the residual."; }
    part parserRatchetReviewGateR1 : TestResult { :>> id = "0a5a0b2a-59f4-4a38-a284-cbf1287a100a"; :>> outcome = VerdictKind::pass; :>> judgedAgainst = "f760170eb8b54758875aa8b071a0ccd2139148ca"; :>> judgedAt = "2026-08-22"; :>> judgedBy = "claudeFable5"; }
    verification parserRatchetCloseOutGate : Test { :>> id = "8a6f6720-fdbd-4e2f-b138-55bb62c2c9e3"; :>> title = "Sprint 428 closeOut gate (autonomous, D0049)"; :>> createdAt = "2026-08-23"; :>> createdBy = "claudeFable5"; :>> method = VerificationMethod::inspect; :>> procedureText = "Autonomous closeOut (D0049). issue231 resolves; the panel's chartered slate is now 3 of 5 issues closed same-day (227, 229, 231), with 228 and 230 decision- or design-gated; validate + all 47 guards green."; }
    part parserRatchetCloseOutGateR1 : TestResult { :>> id = "a5c37410-e8eb-4dab-b37d-528691d2333b"; :>> outcome = VerdictKind::pass; :>> judgedAgainst = "f760170eb8b54758875aa8b071a0ccd2139148ca"; :>> judgedAt = "2026-08-22"; :>> judgedBy = "claudeFable5"; }
    verification parserRatchetRetroGate : Test { :>> id = "dbfaee62-d343-441c-b54a-7d1adb00a7c9"; :>> title = "Sprint 428 retro gate (autonomous, D0049)"; :>> createdAt = "2026-08-23"; :>> createdBy = "claudeFable5"; :>> method = VerificationMethod::analyze; :>> procedureText = "Autonomous retro (D0049). AVOIDABLE-ISSUE SCAN under rcRecurrence: the count-can-grow-silently class now has TWO instances closed by the same ratchet pattern (this and the never-one-number discipline) - pattern named for reuse: any census a guard reports should either bound or explain why not. WELL: panel finding to landed fence in one sitting, with both the detection (ratchet) and prevention (generation) halves shipped together. Estimate 1 pt, delivered 1."; }
    part parserRatchetRetroGateR1 : TestResult { :>> id = "f13162cb-3c39-4a0c-a6e6-fe1392103b22"; :>> outcome = VerdictKind::pass; :>> judgedAgainst = "f760170eb8b54758875aa8b071a0ccd2139148ca"; :>> judgedAt = "2026-08-22"; :>> judgedBy = "claudeFable5"; }
}
