// ProjectDeliveryS360 — Sprint 360: my own mangled ids revealed that invariant 3's UUID clause was
// enforced by nothing. Guard 38, with an ENUMERATED grandfather set. EXECUTE. 3 pts.
package ProjectDeliveryS360 {
    private import EngineElement::*;
    private import EngineWork::*;
    private import EngineVerification::*;
    private import EngineRelationships::*;

    #CharteredBy dependency from wellFormedStory to d0168;

    part wellFormedStory : Story {
        :>> id = "0d800630-0814-6630-9b3e-000000300630";
        :>> title = "Sprint 360: guard 38 identity-well-formed — the gap between 'has an id' and 'ids are unique' (3 pts)";
        :>> createdAt = "2026-08-20"; :>> createdBy = "claudeOpus5"; :>> kind = WorkKind::code; :>> priority = WorkPriority::p0; :>> owner = "claudeOpus5"; :>> estimatedPoints = 3;
    }

    action def DeliveryRunS360 {
        action storyWellFormed;
        verification storyWellFormedDoD : Test { :>> id = "0d800631-0814-6631-9b3e-000000300631"; :>> method = VerificationMethod::test; :>> procedureText = "Delivered by dcUuidWellFormed under D0168, resolving issue170. THE DEFECT WAS MINE AND THE GATE MISSED IT: authoring three UserStory items, two of my ids came out mangled - the strings 'a period-placeholder' and '64bc17ea5device' were inside them - and `keel gate --fast` reported 391 files clean. Tested deliberately: an id of 'not-a-uuid-at-all' passes `keel validate` AND all 37 guards. Invariant 3 says identity is an immutable UUID; guard 37 checks an id is PRESENT, `duplicate-identity` checks two items do not SHARE one, and the middle property was enforced by nothing. GUARD 38 closes it: five groups of 8-4-4-4-12 from [0-9a-z], hard-blocking over .tracking and .engine, 9119 declarations scanned, 0 violations clean. SHAPE NOT HEX because the corpus was measured first: 78 ids deliberately carry a mnemonic suffix (`...-000000000i01`, the intake process steps) which is shaped but not hexadecimal, and failing them would demand a migration nobody asked for. 15 historical malformations grandfathered as an EXPLICIT LIST of named strings, size asserted by a test. 215-253ms with `Model::build was never called`. validate 391 clean; check-engine clean; 38 guards ALL PASS; 235 tests; clippy clean."; }
        part storyWellFormedDoDR1 : TestResult { :>> id = "0d800632-0814-6632-9b3e-000000300632"; :>> outcome = VerdictKind::pass; :>> judgedAgainst = "580f839"; :>> judgedAt = "2026-08-20"; :>> judgedBy = "claudeOpus5"; }
    }

    verification wfRefineGate : Test { :>> id = "0d800633-0814-6633-9b3e-000000300633"; :>> title = "Sprint 360 refine gate (DoR)"; :>> createdAt = "2026-08-20"; :>> createdBy = "claudeOpus5"; :>> method = VerificationMethod::inspect; :>> procedureText = "DoR. This sprint was NOT on the frontier - it exists because a defect I committed while answering an unrelated question turned out to be a whole unguarded invariant. THE ROUTING QUESTION WAS ASKED HONESTLY: a mangled id in a file I had just written is a TRIVIAL fix, and fixing it silently is what D0047 forbids, because the next mangled id would be caught by nothing but my attention again. So the route is CHANGE (a new hard-blocking guard is a gate change, needing sign-off) and the trivial fix rides along inside it. estimatedPoints=3."; }
    part wfRefineGateR1 : TestResult { :>> id = "0d800634-0814-6634-9b3e-000000300634"; :>> outcome = VerdictKind::pass; :>> judgedAgainst = "580f839"; :>> judgedAt = "2026-08-20"; :>> judgedBy = "claudeOpus5"; }

    verification wfStandupGate : Test { :>> id = "0d800635-0814-6635-9b3e-000000300635"; :>> title = "Sprint 360 standup gate"; :>> createdAt = "2026-08-20"; :>> createdBy = "claudeOpus5"; :>> method = VerificationMethod::inspect; :>> procedureText = "Approach: MEASURE THE CORPUS BEFORE CHOOSING THE PREDICATE, which is the rule sprint 357 set and the reason this sprint has a defensible grandfather set instead of an argument. Strict hex over 9119 declarations gives 78 violations; shape gives 15. Reading those 78 showed they are a DELIBERATE convention - mnemonic suffixes that make a process file navigable - and the 15 are genuine historical malformations with 7- and 9-character first groups. The predicate was chosen from that measurement rather than from what a UUID 'should' be. No blockers."; }
    part wfStandupGateR1 : TestResult { :>> id = "0d800636-0814-6636-9b3e-000000300636"; :>> outcome = VerdictKind::pass; :>> judgedAgainst = "580f839"; :>> judgedAt = "2026-08-20"; :>> judgedBy = "claudeOpus5"; }

    verification wfImplementGate : Test { :>> id = "0d800637-0814-6637-9b3e-000000300637"; :>> title = "Sprint 360 implement gate"; :>> createdAt = "2026-08-20"; :>> createdBy = "claudeOpus5"; :>> method = VerificationMethod::test; :>> procedureText = "VERIFIED ON THE DEFECTS THAT ACTUALLY HAPPENED, not on invented ones: 'not-a-uuid-at-all' FAILS, '3a86f04d-2c19-4b57-9e80-64bc17ea5device' FAILS (15 characters in the last group), '4b07d2f6-9e35-4c81-a period-placeholder' FAILS (a SPACE, which is how this was found), the clean tree PASSES at 9119 scanned, and the mnemonic convention PASSES. ONE CORRECTNESS DETAIL THAT WOULD HAVE MADE THE GUARD NEARLY USELESS: a sprint record declares an item AND its result on one line each, so a scan stopping at the FIRST `:>> id` on a line would be blind to exactly the files where most ids live. `id_values` returns every id on a line and a test asserts it. THE GRANDFATHER SET IS 15 NAMED STRINGS WITH ITS SIZE ASSERTED. Guard 36's first version - written by me earlier in this same session - keyed its exemption on a DATE and thereby exempted the very defect it existed to catch. A list cannot do that: a sixteenth malformed id fails no matter when it appears, and widening the list means editing a failing test on purpose. The 15 are NOT rewritten, because section 1.3 makes identity immutable and changing a wrong id is a second wrong."; }
    part wfImplementGateR1 : TestResult { :>> id = "0d800638-0814-6638-9b3e-000000300638"; :>> outcome = VerdictKind::pass; :>> judgedAgainst = "580f839"; :>> judgedAt = "2026-08-20"; :>> judgedBy = "claudeOpus5"; }

    verification wfReviewGate : Test { :>> id = "0d800639-0814-6639-9b3e-000000300639"; :>> title = "Sprint 360 review gate"; :>> createdAt = "2026-08-20"; :>> createdBy = "claudeOpus5"; :>> method = VerificationMethod::inspect; :>> procedureText = "Reviewed. THE FINDING WORTH KEEPING IS ABOUT GUARDS, NOT ABOUT IDS: `identity-present` and `duplicate-identity` between them make identity LOOK guarded, and I shipped the first of those two HOURS before writing an id with a space in it. A property split across two guards leaves its gap exactly where neither guard's name suggests anyone should look, and the more guards exist the more confidently that gap is assumed covered. Thirty-seven passing guards is precisely the condition under which I stopped asking whether identity was checked. WHY A MALFORMED ID IS THE WORST KIND OF DEFECT TO LEAVE UNGUARDED: it is still UNIQUE, so it collides with nothing, resolves everywhere, and no view has any reason to complain - and identity is immutable, so by the time anything notices, the honest fix is a grandfather entry rather than a correction. That is the argument for a cheap text guard over a careful convention. WHAT I DID NOT DO: rewrite the 15. They are wrong and they stay, named, in a list a reader can see."; }
    part wfReviewGateR1 : TestResult { :>> id = "0d80063a-0814-663a-9b3e-00000030063a"; :>> outcome = VerdictKind::pass; :>> judgedAgainst = "580f839"; :>> judgedAt = "2026-08-20"; :>> judgedBy = "claudeOpus5"; }

    verification wfCloseOutGate : Test { :>> id = "0d80063b-0814-663b-9b3e-00000030063b"; :>> title = "Sprint 360 closeOut gate (autonomous, D0049)"; :>> createdAt = "2026-08-20"; :>> createdBy = "claudeOpus5"; :>> method = VerificationMethod::inspect; :>> procedureText = "Autonomous closeOut (D0049). Guard 38 is in GUARD_NAMES and hard-blocking. D0168 is PROPOSED and unsigned - a new blocking guard is a gate change. issue170 records the defect and names what caught it (reading my own output, which D0047 says is not a control). Doc-sync rode along in the same commit: CLAUDE.md 37 to 38 guards, a guards.md row stating the shape-not-hex choice and the enumerated grandfather set. Their statement is recorded as st006 with three user stories - us008 (attestation, scoped explicitly to the sprint 359 RESULT and NOT to D0167), us009 (scopeConstraint: the cold burst is closed off), us010 (question, self-terminating). validate 391 clean; check-engine clean; 38 guards ALL PASS; 235 tests; clippy clean."; }
    part wfCloseOutGateR1 : TestResult { :>> id = "0d80063c-0814-663c-9b3e-00000030063c"; :>> outcome = VerdictKind::pass; :>> judgedAgainst = "580f839"; :>> judgedAt = "2026-08-20"; :>> judgedBy = "claudeOpus5"; }

    verification wfRetroGate : Test { :>> id = "0d80063d-0814-663d-9b3e-00000030063d"; :>> title = "Sprint 360 retro gate (autonomous, D0049)"; :>> createdAt = "2026-08-20"; :>> createdBy = "claudeOpus5"; :>> method = VerificationMethod::analyze; :>> procedureText = "Autonomous retro (D0049) under D0131's retroTrack. WELL: (1) the corpus was measured before the predicate was chosen, which is what produced shape-not-hex and a 15-item grandfather set instead of a 78-item argument; (2) the grandfather set is an enumerated LIST with its size asserted, explicitly because my own guard 36 used a date line and exempted the defect it existed for - a mistake from this same session, corrected in the design of the next guard rather than in prose; (3) verified on the defects that actually occurred, including the one with a SPACE in it; (4) the multiple-ids-per-line case was found by asking where ids actually live rather than by a test failing; (5) the perf reading was taken because sprint 347 made it a rule, and `Model::build was never called` confirms the text-scan design; (6) the trivial fix was not made silently - a mangled id in a file I had just written is a one-character correction, and D0047 says the correction is the smaller half of the work. AVOIDABLE-ISSUE: the mangling itself. Two ids were corrupted by authoring through a shell heredoc, which is the THIRD time this session quoting has damaged content I wrote, and the remedy has been recorded twice already - use the Write tool. I used python-in-heredoc again because it was convenient for a mechanical edit. SECOND AVOIDABLE-ISSUE: I passed a description containing BACKTICKS to `keel record issue` through bash, and the shell executed them as command substitution - the recorded text would have silently lost two guard names. Both are the same class: content authored through a shell is content the shell gets to reinterpret. Estimate 3 pts, delivered."; }
    part wfRetroGateR1 : TestResult { :>> id = "0d80063e-0814-663e-9b3e-00000030063e"; :>> outcome = VerdictKind::pass; :>> judgedAgainst = "580f839"; :>> judgedAt = "2026-08-20"; :>> judgedBy = "claudeOpus5"; }
}
