// ProjectDeliveryS634 — Sprint 634: Sprint 634: the guard runner states its warning population as two classes - actionable warnings and counted-history lines - and orient carries the actionable ones in its burndown (dcGuardWarningsAreActionable, issue404, D0413). EXECUTE under the Change Request route: guard source and the runner are the enforcement surface. 2 pts.. EXECUTE. 2 pts.
package ProjectDeliveryS634 {
    private import EngineElement::*;
    private import EngineWork::*;
    private import EngineVerification::*;
    private import EngineRelationships::*;

    #CharteredBy dependency from guardWarningsStateTwoClassesStory to d0413;

    part guardWarningsStateTwoClassesStory : Story {
        :>> id = "cba77c11-ced4-4b21-98df-8f87ff840061";
        :>> title = "Sprint 634: Sprint 634: the guard runner states its warning population as two classes - actionable warnings and counted-history lines - and orient carries the actionable ones in its burndown (dcGuardWarningsAreActionable, issue404, D0413). EXECUTE under the Change Request route: guard source and the runner are the enforcement surface. 2 pts. (2 pts)";
        :>> createdAt = "2026-09-09"; :>> createdBy = "claudeOpus5"; :>> kind = WorkKind::code; :>> priority = WorkPriority::p0; :>> owner = "claudeOpus5"; :>> estimatedPoints = 2;
    }

    action def DeliveryRunS634 {
        action storyGuardWarningsStateTwoClasses;
        verification storyGuardWarningsStateTwoClassesDoD : Test { :>> id = "90e549ef-f464-40ff-8c47-410de9f38582"; :>> method = VerificationMethod::test; :>> procedureText = "DELIVERED (dcGuardWarningsAreActionable, resolves issue404 through that item): guards.rs history_line/is_history mark a counted-history line at construction, GuardReport::actionable and ::history partition on the mark, the printer labels HISTORY, each guard's summary counts the two classes apart, warning_population is the runner's verdict tail, and five sites construct their history lines with the mark; view/mod.rs burndown_summary_json gains guard_warnings from the guard receipt for this tree. PROBED (D0388) before the real tree was read: known-positive a warning built with history_line -> is_history true, actionable 0, history 1; known-negative a plain warning naming a fixable condition -> is_history false, counted actionable; both named in a_counted_history_line_is_history_and_a_plain_warning_is_actionable, which also asserts the two counts are never summed. Live: keel guard . -> ALL PASS - 38 actionable warning(s) across 7 guard(s) ...; 5 counted-history line(s) (actors, ceremony, issues, attestation-substance, decision-scaffolding); keel orient . burndown guard_warnings actionable 38, counted_history 5, seven guards each with count, first line and detail command. Of the 38 actionable, 22 are the issue312 class already tracked; no new item. D0413 records the change (process-change, proposed for the human; SupersedeClause on D0214 clause 1); guards.md states the two classes."; }
        // RAN: cargo test --release -p keel-cli --lib -> 441 passed (probe pair: history_line-built warning -> is_history true, actionable 0, history 1; plain warning naming a fixable condition -> is_history false, counted actionable); keel guard . -> ALL PASS - 38 actionable warning(s) across 7 guard(s); 5 counted-history line(s); keel orient . burndown guard_warnings actionable 38 counted_history 5; clippy -D warnings Finished
        part storyGuardWarningsStateTwoClassesDoDR1 : TestResult { :>> id = "c4898151-de47-402b-a456-6acc122f5e62"; :>> outcome = VerdictKind::pass; :>> judgedAgainst = "e902566"; :>> judgedAt = "2026-09-09"; :>> judgedBy = "claudeOpus5"; }
    }

    verification guardWarningsStateTwoClassesRefineGate : Test { :>> id = "867f885a-c5fe-43d5-93da-d7fee4d97e30"; :>> title = "Sprint 634 refine gate (DoR)"; :>> createdAt = "2026-09-09"; :>> createdBy = "claudeOpus5"; :>> method = VerificationMethod::inspect; :>> procedureText = "Definition of Ready: dcGuardWarningsAreActionable at the head of keel whats-next . after e902566; its DoD names the property (two classes stated apart, actionable ones where work is chosen), the DO (mark at construction, computed partition) and the forbidden alternative (promotion to violations, D0088); no fork; 2 points - three source files, three tests, a guards.md paragraph and a Decision."; }
    // RAN: sprint634 Refine: see the record's section; cargo test --release -p keel-cli --lib -> 441 passed (probe pair: history_line-built warning -> is_history true, actionable 0, history 1; plain warning naming a fixable condition -> is_history false, counted actionable); keel guard . -> ALL PASS - 38 actionable warning(s) across 7 guard(s); 5 counted-history line(s); keel orient . burndown guard_warnings actionable 38 counted_history 5; clippy -D warnings Finished
    part guardWarningsStateTwoClassesRefineGateR1 : TestResult { :>> id = "c553f327-4a9c-4328-9713-a8b6f7012032"; :>> outcome = VerdictKind::pass; :>> judgedAgainst = "e902566"; :>> judgedAt = "2026-09-09"; :>> judgedBy = "claudeOpus5"; }
    verification guardWarningsStateTwoClassesStandupGate : Test { :>> id = "49f58008-593e-4568-81af-25927202dd07"; :>> title = "Sprint 634 standup gate"; :>> createdAt = "2026-09-09"; :>> createdBy = "claudeOpus5"; :>> method = VerificationMethod::inspect; :>> procedureText = "No blocker. One design point settled by reading: classifying at print time by matching prose would put the rule in the reader; marking at construction puts it in the guard that knows, so the five sites carry the mark and every reader partitions on it."; }
    // RAN: sprint634 Standup: see the record's section; cargo test --release -p keel-cli --lib -> 441 passed (probe pair: history_line-built warning -> is_history true, actionable 0, history 1; plain warning naming a fixable condition -> is_history false, counted actionable); keel guard . -> ALL PASS - 38 actionable warning(s) across 7 guard(s); 5 counted-history line(s); keel orient . burndown guard_warnings actionable 38 counted_history 5; clippy -D warnings Finished
    part guardWarningsStateTwoClassesStandupGateR1 : TestResult { :>> id = "fedfe7a2-16c9-4160-b1fc-292dd9adf496"; :>> outcome = VerdictKind::pass; :>> judgedAgainst = "e902566"; :>> judgedAt = "2026-09-09"; :>> judgedBy = "claudeOpus5"; }
    verification guardWarningsStateTwoClassesImplementGate : Test { :>> id = "77780ad5-2973-432f-b5f6-86d38a87f235"; :>> title = "Sprint 634 implement gate"; :>> createdAt = "2026-09-09"; :>> createdBy = "claudeOpus5"; :>> method = VerificationMethod::test; :>> procedureText = "guards.rs, main.rs and view/mod.rs patched through textpatch (guard634.py, burndown634.py, tests634.py, clippy634.py, clippy634b.py); cargo test --release -p keel-cli --lib -> 441 passed; cargo clippy --workspace --all-targets -- -D warnings -> Finished after five pedantic findings (format_push_string x2 -> write!, redundant clone and slice::from_ref in the test, items_after_statements for the use); keel guard . -> ALL PASS with the two-class tail; keel orient . -> guard_warnings populated after a plain keel guard . wrote the receipt (a --no-receipt run writes none, so orient read null until then); keel record decision D0413 --process-change -> proposed, OUTSIDE standing consent."; }
    // RAN: sprint634 Implement: see the record's section; cargo test --release -p keel-cli --lib -> 441 passed (probe pair: history_line-built warning -> is_history true, actionable 0, history 1; plain warning naming a fixable condition -> is_history false, counted actionable); keel guard . -> ALL PASS - 38 actionable warning(s) across 7 guard(s); 5 counted-history line(s); keel orient . burndown guard_warnings actionable 38 counted_history 5; clippy -D warnings Finished
    part guardWarningsStateTwoClassesImplementGateR1 : TestResult { :>> id = "11eee76a-846b-42fb-9f1c-4020f1aa32d0"; :>> outcome = VerdictKind::pass; :>> judgedAgainst = "e902566"; :>> judgedAt = "2026-09-09"; :>> judgedBy = "claudeOpus5"; }
    verification guardWarningsStateTwoClassesReviewGate : Test { :>> id = "0fcd6b76-e37b-4595-88b5-1a8843b56f75"; :>> title = "Sprint 634 review gate — three passes per D0172"; :>> createdAt = "2026-09-09"; :>> createdBy = "claudeOpus5"; :>> method = VerificationMethod::inspect; :>> procedureText = "Three passes per D0172: (1) the partition is asserted on both counts and on the summary text, and the test asserts the two numbers are never summed; (2) the empty case and the one-class cases are tested so a summary never names a class that is absent; (3) the live actor guard is asserted to carry its legacy line as history and zero actionable, so the classification on the real tree is the guard's declaration."; }
    // RAN: sprint634 Review: see the record's section; cargo test --release -p keel-cli --lib -> 441 passed (probe pair: history_line-built warning -> is_history true, actionable 0, history 1; plain warning naming a fixable condition -> is_history false, counted actionable); keel guard . -> ALL PASS - 38 actionable warning(s) across 7 guard(s); 5 counted-history line(s); keel orient . burndown guard_warnings actionable 38 counted_history 5; clippy -D warnings Finished
    part guardWarningsStateTwoClassesReviewGateR1 : TestResult { :>> id = "54ac7995-b6ee-44d8-9566-c01928563b13"; :>> outcome = VerdictKind::pass; :>> judgedAgainst = "e902566"; :>> judgedAt = "2026-09-09"; :>> judgedBy = "claudeOpus5"; }
    verification guardWarningsStateTwoClassesCloseOutGate : Test { :>> id = "78d783be-09b8-475d-872a-2e3c9e572d81"; :>> title = "Sprint 634 closeOut gate (autonomous, D0049)"; :>> createdAt = "2026-09-09"; :>> createdBy = "claudeOpus5"; :>> method = VerificationMethod::inspect; :>> procedureText = "keel validate . clean, keel check-engine . clean, keel gate --fast clean; dcGuardWarningsAreActionable DoD stamped with the probe pair and the live counts named."; }
    // RAN: sprint634 CloseOut: see the record's section; cargo test --release -p keel-cli --lib -> 441 passed (probe pair: history_line-built warning -> is_history true, actionable 0, history 1; plain warning naming a fixable condition -> is_history false, counted actionable); keel guard . -> ALL PASS - 38 actionable warning(s) across 7 guard(s); 5 counted-history line(s); keel orient . burndown guard_warnings actionable 38 counted_history 5; clippy -D warnings Finished
    part guardWarningsStateTwoClassesCloseOutGateR1 : TestResult { :>> id = "489d400b-86fe-43f4-831a-d8aa582259ef"; :>> outcome = VerdictKind::pass; :>> judgedAgainst = "e902566"; :>> judgedAt = "2026-09-09"; :>> judgedBy = "claudeOpus5"; }
    verification guardWarningsStateTwoClassesRetroGate : Test { :>> id = "0521f786-315d-4745-ad48-7a972a4facbc"; :>> title = "Sprint 634 retro gate (autonomous, D0049)"; :>> createdAt = "2026-09-09"; :>> createdBy = "claudeOpus5"; :>> method = VerificationMethod::analyze; :>> procedureText = "Avoidable-issue scan: the mark is opt-in per site and nothing enumerates the unmarked sites, so a new guard that reports history without history_line is counted actionable until someone notices - stated as D0413's limit. Mid-sprint the human said keel is still crazy slow; measured from the ledger and a KEEL_PERF run, recorded as issue429 with resolver dcSlowHookFireExplainsItself and ranked at the head of the not-started frontier by reordering the backlog (D0052). No other new item."; }
    // RAN: sprint634 Retro: see the record's section; cargo test --release -p keel-cli --lib -> 441 passed (probe pair: history_line-built warning -> is_history true, actionable 0, history 1; plain warning naming a fixable condition -> is_history false, counted actionable); keel guard . -> ALL PASS - 38 actionable warning(s) across 7 guard(s); 5 counted-history line(s); keel orient . burndown guard_warnings actionable 38 counted_history 5; clippy -D warnings Finished
    part guardWarningsStateTwoClassesRetroGateR1 : TestResult { :>> id = "85698ee4-a90e-44a8-a916-8f9e09a1f36b"; :>> outcome = VerdictKind::pass; :>> judgedAgainst = "e902566"; :>> judgedAt = "2026-09-09"; :>> judgedBy = "claudeOpus5"; }
}
