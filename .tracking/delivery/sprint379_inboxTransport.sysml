// ProjectDeliveryS379 — Sprint 379: the mobile pipeline gets a transport both ends can verify.
// The live-doc mechanism is retired (its writes dropped); the inbox delivers with a receipt. EXECUTE. 8 pts.
package ProjectDeliveryS379 {
    private import EngineElement::*;
    private import EngineWork::*;
    private import EngineVerification::*;
    private import EngineRelationships::*;

    #CharteredBy dependency from inboxTransportStory to d0171;

    part inboxTransportStory : Story {
        :>> id = "0d800760-0814-6760-9b3e-000000300760";
        :>> title = "Sprint 379: the deck's mobile transport delivers to a store that acknowledges, and the session records what it pulls (8 pts)";
        :>> createdAt = "2026-08-21"; :>> createdBy = "claudeOpus5"; :>> kind = WorkKind::code; :>> priority = WorkPriority::p0; :>> owner = "claudeOpus5"; :>> estimatedPoints = 8;
    }

    action def DeliveryRunS379 {
        action storyInboxTransport;
        verification storyInboxTransportDoD : Test { :>> id = "0d800761-0814-6761-9b3e-000000300761"; :>> method = VerificationMethod::test; :>> procedureText = "DELIVERED BACKLOG ITEMS: dcInboxTransport, dcToolReferenceGuard. Clears issue194 (live-doc appends never persisted - their words closed it: nothing is there), issue195 (the local acceptance save omitted the API's required file field, latent because the e2e leg was conditional), issue196 (sprint 377 recorded a deletion that never happened). THE NEW PIPELINE: tap -> one row to the keel-deck-inbox sheet via the viewer's Smartsheet connector (artifact mcp capability), store acks with a row id the page shows as its receipt -> session pulls Processed=false rows -> deck_inbox_record.py records through the write API and VERIFIES from the computed view -> verified rows marked Processed. The add_rows request/response pair was observed live before publish per the capability contract; the tunnel option is closed by their constraint (controlling device not guaranteed on their VPN). TESTED: 212 unit tests (deck parse/config/dead-mechanism/guard-39), e2e 17/17 with the new unconditional acceptance leg, clippy 0, and the REHEARSAL - the actually-delivered row pulled from the real sheet and run through a served COPY, disposition read back from the computed view, validate clean."; }
        part storyInboxTransportDoDR1 : TestResult { :>> id = "0d800762-0814-6762-9b3e-000000300762"; :>> outcome = VerdictKind::pass; :>> judgedAgainst = "5264d27"; :>> judgedAt = "2026-08-21"; :>> judgedBy = "claudeOpus5"; }
    }

    verification itRefineGate : Test { :>> id = "0d800763-0814-6763-9b3e-000000300763"; :>> title = "Sprint 379 refine gate (DoR)"; :>> createdAt = "2026-08-21"; :>> createdBy = "claudeOpus5"; :>> method = VerificationMethod::inspect; :>> procedureText = "DoR. Their two numbered answers ELIMINATED the alternatives before design started: #1 (nothing is there) upgraded issue193's write-only finding to write-DROPPED, killing any salvage of the live-doc mechanism; #2 (no VPN guarantee) killed the tunnel recorded in issue193 as their decision. What remains must work from any network and carry a receiver-side ack: the viewer's own connector, called from the page via the artifact mcp capability. Routed CHANGE (the transport architecture moves) under the D0171 charter; us018 records the triage. estimatedPoints=8."; }
    part itRefineGateR1 : TestResult { :>> id = "0d800764-0814-6764-9b3e-000000300764"; :>> outcome = VerdictKind::pass; :>> judgedAgainst = "5264d27"; :>> judgedAt = "2026-08-21"; :>> judgedBy = "claudeOpus5"; }

    verification itStandupGate : Test { :>> id = "0d800765-0814-6765-9b3e-000000300765"; :>> title = "Sprint 379 standup gate"; :>> createdAt = "2026-08-21"; :>> createdBy = "claudeOpus5"; :>> method = VerificationMethod::inspect; :>> procedureText = "Approach: the capability contract is the design document. Its hard rules were followed to the letter - mcp.d.ts read before any call site; one real request/response pair per published tool observed IN SESSION (add_rows: request sheet_id+rows[toBottom,cells[columnId,value]], response resultCode 0 + result[0].id); errors branched per code, never one banner; ambiguous write outcomes (server_unavailable/upstream_error/cancelled) invite a fresh-gesture re-tap rather than auto-retry, made SAFE by recorder-side dedup (latest-At per uid+kind). The config is a contract file the generator embeds all-or-nothing. HONEST LIMIT, stated where it belongs: the single in-page callTool leg cannot run outside the viewer's frame - everything around it is machine-verified, and the first phone tap is the remaining field test. No blockers.";}
    part itStandupGateR1 : TestResult { :>> id = "0d800766-0814-6766-9b3e-000000300766"; :>> outcome = VerdictKind::pass; :>> judgedAgainst = "5264d27"; :>> judgedAt = "2026-08-21"; :>> judgedBy = "claudeOpus5"; }

    verification itImplementGate : Test { :>> id = "0d800767-0814-6767-9b3e-000000300767"; :>> title = "Sprint 379 implement gate"; :>> createdAt = "2026-08-21"; :>> createdBy = "claudeOpus5"; :>> method = VerificationMethod::test; :>> procedureText = "READING THE RECEIVER'S CONTRACT FOUND TWO LATENT DEFECTS before any code ran: (1) /api/decision/accept requires a file field the deck never sent - every local acceptance tap would have 422'd; cards now carry data-file from the item index and the e2e authors a throwaway proposed decision so that leg runs UNCONDITIONALLY (a leg that skips on an empty precondition verifies nothing). (2) The registry and process still deployed obligation_canvas.py, which sprint 377 had recorded as deleted - the file existed, the SKILL.md still taught the dead architecture, and guard 39's first dry run found a THIRD stale reference (triage_reminder.py in engine-triage). THE REHEARSAL LEG: the row delivered by the observed add_rows call was pulled with Processed=false, run through deck_inbox_record.py --copy-test, recorded via /api/disposition on the served copy, and read back dispositioned from the computed view - the receive side is now as tested as the local save loop."; }
    part itImplementGateR1 : TestResult { :>> id = "0d800768-0814-6768-9b3e-000000300768"; :>> outcome = VerdictKind::pass; :>> judgedAgainst = "5264d27"; :>> judgedAt = "2026-08-21"; :>> judgedBy = "claudeOpus5"; }

    verification itReviewGate : Test { :>> id = "0d800769-0814-6769-9b3e-000000300769"; :>> title = "Sprint 379 review gate — three passes per D0172"; :>> createdAt = "2026-08-21"; :>> createdBy = "claudeOpus5"; :>> method = VerificationMethod::inspect; :>> procedureText = "PASS 1, CLAIMS vs computed/emitted: 212 unit tests, e2e 17/17, 39 guards ALL PASS, clippy 0, node --check green, rehearsal verified from the computed view - all from runs, none from reading. PASS 2, BOUNDARY: partial inbox config yields null and the page claims NO transport (inbox_config_all_or_nothing); an AI actor still 400s at the sitting endpoint; the rehearsal wrote only to a COPY; the observation and test rows were deleted from the sheet so a real pull can never replay them. PASS 3, OWN DIFF: the dedup key first written as confirmed-vs-seen style (uid only) would have collapsed a finding verdict and a sitting verdict on the same item - keyed by (uid, kind) instead; and the guard-39 scope first included .tracking, which would have failed immutable history for truthfully naming retired tools - scope cut to the living surface. WHAT A REVIEWER SHOULD ATTACK: the in-page callTool leg remains field-tested only; its failure modes are branched per the contract's own codes and the page says exactly which state it is in, so a failure names its fix instead of hiding."; }
    part itReviewGateR1 : TestResult { :>> id = "0d80076a-0814-676a-9b3e-00000030076a"; :>> outcome = VerdictKind::pass; :>> judgedAgainst = "5264d27"; :>> judgedAt = "2026-08-21"; :>> judgedBy = "claudeOpus5"; }

    verification itCloseOutGate : Test { :>> id = "0d80076b-0814-676b-9b3e-00000030076b"; :>> title = "Sprint 379 closeOut gate (autonomous, D0049)"; :>> createdAt = "2026-08-21"; :>> createdBy = "claudeOpus5"; :>> method = VerificationMethod::inspect; :>> procedureText = "Autonomous closeOut (D0049). issue194/195/196 recorded and cleared; obligation_canvas.py ACTUALLY deleted this time, verified by ls and enforced by guard 39; SKILL.md, process, and registry rewritten to the shipped architecture (no tombstones); CLAUDE.md and guards.md updated in the same change (doc-sync); the deck republished with the mcp capability manifest {Smartsheet: [add_rows]}. The stranded verdicts stay stranded - their word, not recoverable - and the queue they represent is re-judgeable through the new transport or by telling Claude. validate clean; 39 guards ALL PASS; 212 tests; e2e 17/17; clippy 0."; }
    part itCloseOutGateR1 : TestResult { :>> id = "0d80076c-0814-676c-9b3e-00000030076c"; :>> outcome = VerdictKind::pass; :>> judgedAgainst = "5264d27"; :>> judgedAt = "2026-08-21"; :>> judgedBy = "claudeOpus5"; }

    verification itRetroGate : Test { :>> id = "0d80076d-0814-676d-9b3e-00000030076d"; :>> title = "Sprint 379 retro gate (autonomous, D0049)"; :>> createdAt = "2026-08-21"; :>> createdBy = "claudeOpus5"; :>> method = VerificationMethod::analyze; :>> procedureText = "Autonomous retro (D0049). AVOIDABLE-ISSUE SCAN under rcRecurrence: (1) issue196 is verify-the-wrong-surface occurrence FOUR (file-for-screen, strings-for-syntax, sender-for-receiver, now claim-for-ls) - second-and-beyond occurrence, so per D0172 it carries a preventing change: guard 39 makes the filesystem half mechanical, and the family rule already lives in dcHonestSaveLabel; (2) issue195 names a NEW class - the conditional test leg that silently skips on an empty precondition - first occurrence, preventing change shipped anyway (the fixture makes the leg unconditional) because the fix cost less than the item. WELL: (1) their two numbered constraints were treated as the elimination argument they are, and the design space collapsed to one transport before any code; (2) the capability contract was read FIRST this time - the same contract family that cost five broken publishes when inferred - and both latent defects this sprint were found by reading the RECEIVER'S contract, which is the lesson finally applied in the direction it was learned; (3) the rehearsal used the real delivered row, not a synthetic one, so the tested path and the production path are the same bytes. Estimate 8 pts, delivered."; }
    part itRetroGateR1 : TestResult { :>> id = "0d80076e-0814-676e-9b3e-00000030076e"; :>> outcome = VerdictKind::pass; :>> judgedAgainst = "5264d27"; :>> judgedAt = "2026-08-21"; :>> judgedBy = "claudeOpus5"; }
}
