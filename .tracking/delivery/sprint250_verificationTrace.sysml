// ProjectDeliveryS250 — Sprint 250: the verification-trace guard + verification-method mix in
// tier-satisfaction (issue082, D0130). Closes the mis-identification that opened this line of work:
// `work done` and `requirement verified` were disconnected, and the metric was narrated wrongly.
// Taken from the top of the ranked frontier per D0052, not chosen. EXECUTE. 3 pts.
package ProjectDeliveryS250 {
    private import EngineElement::*;
    private import EngineWork::*;
    private import EngineVerification::*;
    private import EngineRelationships::*;

    #CharteredBy dependency from verificationTraceStory to d0129;

    part verificationTraceStory : Story {
        :>> id = "0d680001-0813-4801-9b3e-000000180001";
        :>> title = "Sprint 250: verification-trace guard + verifiedByMethod in tier-satisfaction (3 pts)";
        :>> createdAt = "2026-08-13"; :>> createdBy = "claudeOpus5"; :>> kind = WorkKind::code; :>> priority = WorkPriority::p0; :>> owner = "claudeOpus5"; :>> estimatedPoints = 3;
    }

    action def DeliveryRunS250 {
        action storyVerificationTrace;
        verification storyVerificationTraceDoD : Test { :>> id = "0d680002-0813-4802-9b3e-000000180002"; :>> method = VerificationMethod::test; :>> procedureText = "Delivers dcVerificationTrace (issue082/D0130). DEFECT CLOSED: an SR counts as verified only when a Test #Verify-links TO IT, but delivered work's DoD Tests linked to the backlog ACTION — so the model could not distinguish `requirement not yet delivered` from `requirement delivered, verification never traced upward`, and sr_verified_pct=34% was reported to the human as though it meant functional verification. BUILT: (1) guard `verification-trace` (19 guards; 16 hard + 3 warning-only) flagging a DELIVERED verification (a DoD whose highest-numbered result PASSED) that names an SR in procedureText with no #Verify edge reaching it — reusing the decision-requirement-link shape (D0102, prose-names-no-edge); WARNING-level on two independent grounds (completeness is honest-state burndown that must not gate a commit, D0098; and prose matching is heuristic, D0102). (2) `keel tier-satisfaction` now emits verifiedByMethod. PRECISION: first run gave 103 findings, of which 37 were declared PHASE gates merely mentioning a requirement (they verify the sprint PROCESS, not the requirement) — removed by a DECLARED-phase filter, never a hardcoded list, so it adapts to a downstream's own workflow. VERIFY (full cycle demonstrated, not asserted): 66 flagged with all six srDc* present -> authored the six #Verify edges -> 60 flagged with ZERO srDc* remaining; sr_verified_pct 34 -> 43; test-method edges 16 -> 20; verifiedByMethod reads critique 57 / test 20 / inspect 6 / demo 3 / analyze 1, so the ~70%-critique composition is now impossible to misread as functional-test coverage. clippy -D warnings clean; 150 tests incl. four new pure-function tests (flags delivered+untraced; goes clean once linked; whole-token matching only, so srAlpha does not match srAlphaBeta; method mix ignores verify edges to non-SRs and reports a method-less verifier as `unstated` rather than dropping it); keel validate + all 19 guards + check-engine green at af2edd1."; }
        part storyVerificationTraceDoDR1 : TestResult { :>> id = "0d680003-0813-4803-9b3e-000000180003"; :>> outcome = VerdictKind::pass; :>> judgedAgainst = "af2edd1"; :>> judgedAt = "2026-08-13"; :>> judgedBy = "claudeOpus5"; }
    }

    verification vtRefineGate : Test { :>> id = "0d680004-0813-4804-9b3e-000000180004"; :>> title = "Sprint 250 refine gate (DoR)"; :>> createdAt = "2026-08-13"; :>> createdBy = "claudeOpus5"; :>> method = VerificationMethod::inspect; :>> procedureText = "DoR: dcVerificationTrace sat at the TOP of the ranked frontier, so it was taken by ORDER rather than chosen (D0052) — the first sprint this sitting where the next item was determined by the reordered backlog instead of by narration. Scope: the guard + the method mix + closing this thread's own six untraced pairs. EXCLUDED with reason: the ~60 pre-existing viewer-programme pairs (D0108 — authoring #Verify asserts that a DoD's evidence discharges that requirement, which only the delivering thread can judge; tracked as issue087/dcBackfillVerifyEdges). estimatedPoints=3. DoR met."; }
    part vtRefineGateR1 : TestResult { :>> id = "0d680005-0813-4805-9b3e-000000180005"; :>> outcome = VerdictKind::pass; :>> judgedAgainst = "af2edd1"; :>> judgedAt = "2026-08-13"; :>> judgedBy = "claudeOpus5"; }

    verification vtStandupGate : Test { :>> id = "0d680006-0813-4806-9b3e-000000180006"; :>> title = "Sprint 250 standup gate"; :>> createdAt = "2026-08-13"; :>> createdBy = "claudeOpus5"; :>> method = VerificationMethod::inspect; :>> procedureText = "Approach: find the existing pattern before inventing one — decision-requirement-link (D0102) already solves prose-names-no-typed-edge, so the guard reuses its shape and its contains_token whole-word matcher rather than a fresh regex. Key the DELIVERED test on SHAPE (carries procedureText + has a passing latest result) rather than on a type name, so it cannot silently stop matching if verification typing changes. Extract a pure core (untraced_links) for self-test, matching the codebase's pure-function test style. No blockers."; }
    part vtStandupGateR1 : TestResult { :>> id = "0d680007-0813-4807-9b3e-000000180007"; :>> outcome = VerdictKind::pass; :>> judgedAgainst = "af2edd1"; :>> judgedAt = "2026-08-13"; :>> judgedBy = "claudeOpus5"; }

    verification vtImplementGate : Test { :>> id = "0d680008-0813-4808-9b3e-000000180008"; :>> title = "Sprint 250 implement gate"; :>> createdAt = "2026-08-13"; :>> createdBy = "claudeOpus5"; :>> method = VerificationMethod::test; :>> procedureText = "Implemented at af2edd1. The guard was run BEFORE and AFTER authoring the six edges, and the frontier read back afterwards, so every claim in the DoD is a measured transition rather than an expectation. The 37 phase-gate findings were treated as a precision defect and fixed at the source (declared-phase filter) instead of being explained away in the message — a guard whose first run is one-third noise trains people to ignore it, which is the doc-sync/D0102 lesson. clippy clean, 150 tests, all 19 guards green."; }
    part vtImplementGateR1 : TestResult { :>> id = "0d680009-0813-4809-9b3e-000000180009"; :>> outcome = VerdictKind::pass; :>> judgedAgainst = "af2edd1"; :>> judgedAt = "2026-08-13"; :>> judgedBy = "claudeOpus5"; }

    verification vtReviewGate : Test { :>> id = "0d68000a-0813-480a-9b3e-00000018000a"; :>> title = "Sprint 250 review gate"; :>> createdAt = "2026-08-13"; :>> createdBy = "claudeOpus5"; :>> method = VerificationMethod::inspect; :>> procedureText = "Reviewed. The guard does something the burndown could not: it separates `not delivered` from `delivered but untraced`, which were previously the same number. The verifiedByMethod addition is the more important half for honesty — the original error was not a missing edge, it was reporting a critique-dominated percentage as functional verification, and no edge would have prevented that. Scope discipline held twice: the 60 pre-existing pairs were left as visible warnings with a tracked owner rather than mass-asserted, and issue077 was CORRECTED rather than left understating a defect I had already noticed aloud but never fixed in the record. Weakness accepted: prose matching means a DoD that discusses an SR without claiming to verify it will be flagged — hence warning-level, and the fix path (author the edge, or narrow the prose so it stops reading as a claim) is stated in dcBackfillVerifyEdges."; }
    part vtReviewGateR1 : TestResult { :>> id = "0d68000b-0813-480b-9b3e-00000018000b"; :>> outcome = VerdictKind::pass; :>> judgedAgainst = "af2edd1"; :>> judgedAt = "2026-08-13"; :>> judgedBy = "claudeOpus5"; }

    verification vtCloseOutGate : Test { :>> id = "0d68000c-0813-480c-9b3e-00000018000c"; :>> title = "Sprint 250 closeOut gate (autonomous, D0049)"; :>> createdAt = "2026-08-13"; :>> createdBy = "claudeOpus5"; :>> method = VerificationMethod::inspect; :>> procedureText = "Autonomous closeOut (D0049). dcVerificationTrace carries a passing DoD TestResult at af2edd1; validate + all 19 guards + check-engine green; 150 tests; clippy clean. Frontier advanced by order to dcAttestationSubstance (issue083 — the empty-procedureText acceptance, which is live in the human's own d0129Accept). issue087/dcBackfillVerifyEdges added for the 60 pre-existing pairs. D0130 remains PROPOSED: the human said 'agreed, proceed', which in context authorised proceeding with this item and was deliberately NOT recorded as an acceptance attestation for that Decision (D0016/D0106 — a confirmation is never inferred from a general instruction), so no acceptance event was fabricated."; }
    part vtCloseOutGateR1 : TestResult { :>> id = "0d68000d-0813-480d-9b3e-00000018000d"; :>> outcome = VerdictKind::pass; :>> judgedAgainst = "af2edd1"; :>> judgedAt = "2026-08-13"; :>> judgedBy = "claudeOpus5"; }

    verification vtRetroGate : Test { :>> id = "0d68000e-0813-480e-9b3e-00000018000e"; :>> title = "Sprint 250 retro gate (autonomous, D0049)"; :>> createdAt = "2026-08-13"; :>> createdBy = "claudeOpus5"; :>> method = VerificationMethod::analyze; :>> procedureText = "Autonomous retro (D0049), under the issue085 obligation that findings become tracked items. WELL: (1) the guard's own first run was treated as evidence about the GUARD, not just about the model — 103 findings with 37 noise led to fixing precision at the source rather than shipping a control people would learn to ignore; (2) the before/after transition was measured (66 -> 60, zero srDc*, 34% -> 43%) rather than predicted; (3) the metric-honesty half (verifiedByMethod) was recognised as the more important fix, since the original error was mis-reading a number, not a missing edge. AVOIDABLE-ISSUE 1: I predicted the guard would find 6 pairs; it found 103. My estimate was wrong by more than an order of magnitude because I reasoned only from the instance I had personally created and never checked whether the pattern was systemic — the same narrow-sampling error that made the sprint-247 audit understate the duplicate-id count (issue080) and the marker count (issue077). TRACKED: no new item; this is the recurring practice the review gate and dcVerificationTrace itself now guard against, and it is recorded here as the third occurrence so the pattern is visible if it recurs a fourth time. AVOIDABLE-ISSUE 2 (TRACKED as issue087/dcBackfillVerifyEdges, Medium): 60 pre-existing untraced pairs across the viewer programme — pre-existing debt made visible by a new control, exactly as issue080 was. AVOIDABLE-ISSUE 3 (TRACKED as the issue077 CORRECTION): I noticed aloud last sitting that issue077 understated the undeclared-marker set (it omits #Verify, the most-used marker of all, and the one this guard keys on) and did not fix the record then — a finding stated in conversation but not written down, which is the issue085 failure in miniature. Now corrected in the record itself. Estimate 3 pts, delivered."; }
    part vtRetroGateR1 : TestResult { :>> id = "0d68000f-0813-480f-9b3e-00000018000f"; :>> outcome = VerdictKind::pass; :>> judgedAgainst = "af2edd1"; :>> judgedAt = "2026-08-13"; :>> judgedBy = "claudeOpus5"; }
}
