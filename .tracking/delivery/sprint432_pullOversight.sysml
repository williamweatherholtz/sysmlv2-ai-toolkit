// ProjectDeliveryS432 — Sprint 432: pullOversight (D0204): the governance binds the AI, never the human - every surface that scheduled the supervisor is retired, every record stays. EXECUTE. 2 pts.
package ProjectDeliveryS432 {
    private import EngineElement::*;
    private import EngineWork::*;
    private import EngineVerification::*;
    private import EngineRelationships::*;

    #CharteredBy dependency from pullOversightStory to d0204;

    part pullOversightStory : Story {
        :>> id = "3fb06798-938b-40da-a094-a3afd6a44193";
        :>> title = "Sprint 432: the ask dies, the record lives (2 pts)";
        :>> createdAt = "2026-08-23"; :>> createdBy = "claudeFable5"; :>> kind = WorkKind::code; :>> priority = WorkPriority::p0; :>> owner = "claudeFable5"; :>> estimatedPoints = 2;
    }

    action def DeliveryRunS432 {
        action storyPullOversight;
        verification storyPullOversightDoD : Test { :>> id = "b99149f2-5e1c-4ba5-a808-8a1f8044fac0"; :>> method = VerificationMethod::test; :>> procedureText = "DELIVERED: D0204 pullOversight, accepted on their verbatim words ('none of that. I don't need governance, you do. I don't need a schedule, or due items. highlight blockers and the most critical items, but I'm not here to subscribe to your processes') - a direction reversal of the obligation semantics in D0200 clauses 3 and 5 and the D0049 sitting-gate framing, one day after signature, on contact with what OPTION A asked OF THEM. RETIRED (the ask): the deck's sitting section, deep-review sampling labels, and batch-acknowledge solicitation; authority-queue's perSittingReview row (the queue now lists ONLY what genuinely blocks on their judgment); the process-change oversight throttle (nothing gates the AI's work on the human's attention cadence - a deliberate ABSENT-BY-DESIGN comment marks the spot). KEPT (the record): sitting-coverage with its read/batch split, the sittingOverrideRateIndicator, the batch-ack API verdict for voluntary use, and sittings reviewable on demand through the console - pull, never push. CLAUDE.md rewritten: the human's only inherent gates are direction decisions that block work and confirmations they choose to give. Chat reporting contract (memory + D0203 addendum in practice): blockers, then critical items, then stop. VERIFIED: deck read back at 5 items (2 blockers + 3 findings, immediately dispositioned under D0165 to leave 2 true blockers), zero sitting content; authority-queue read back listing only decisions and undispositioned findings; suite 10/10, clippy clean."; }
        part storyPullOversightDoDR1 : TestResult { :>> id = "600760bc-ccc3-4823-899f-7510b343af7d"; :>> outcome = VerdictKind::pass; :>> judgedAgainst = "7ef444399f80b9ee54fe420555d9319607818865"; :>> judgedAt = "2026-08-23"; :>> judgedBy = "claudeFable5"; }
    }

    verification pullOversightRefineGate : Test { :>> id = "1315d307-0f76-49cf-b98e-c46925606701"; :>> title = "Sprint 432 refine gate (DoR)"; :>> createdAt = "2026-08-23"; :>> createdBy = "claudeFable5"; :>> method = VerificationMethod::inspect; :>> procedureText = "DoR. Their words are the charter and the acceptance. In scope: every surface that pushed obligations at them; out of scope: any record or computation - detection strength must be provably unchanged. 2 points."; }
    part pullOversightRefineGateR1 : TestResult { :>> id = "56b755a9-91bb-488c-97ac-57aaf4c85ee4"; :>> outcome = VerdictKind::pass; :>> judgedAgainst = "7ef444399f80b9ee54fe420555d9319607818865"; :>> judgedAt = "2026-08-23"; :>> judgedBy = "claudeFable5"; }
    verification pullOversightStandupGate : Test { :>> id = "deeca605-cdfa-430e-b0fd-17c834fb4626"; :>> title = "Sprint 432 standup gate"; :>> createdAt = "2026-08-23"; :>> createdBy = "claudeFable5"; :>> method = VerificationMethod::inspect; :>> procedureText = "Approach: remove the ASK, keep the RECORD - each removal site gets an absent-by-design comment naming D0204 so a future session cannot mistake the gap for an oversight; the records (split counts, indicator, coverage) continue computing untouched, which is what makes this a supervision-style reversal rather than a governance weakening."; }
    part pullOversightStandupGateR1 : TestResult { :>> id = "4684e9e8-202d-4dc8-94c9-0f455d4d837d"; :>> outcome = VerdictKind::pass; :>> judgedAgainst = "7ef444399f80b9ee54fe420555d9319607818865"; :>> judgedAt = "2026-08-23"; :>> judgedBy = "claudeFable5"; }
    verification pullOversightImplementGate : Test { :>> id = "5f12f454-724d-400c-a2ce-5ffbd1bc41ff"; :>> title = "Sprint 432 implement gate"; :>> createdAt = "2026-08-23"; :>> createdBy = "claudeFable5"; :>> method = VerificationMethod::test; :>> procedureText = "Verified by running: keel authority-queue - awaiting lists only decisionAcceptance and findingDisposition rows, no perSittingReview; regenerated deck - 2 sections (blockers, critical findings), zero sitting strings; keel sitting-coverage still computes covered/read/batch/due unchanged; keel indicators still carries sittingOverrideRateIndicator; cargo test 10/10 result-ok; clippy pedantic+nursery clean; all 47 guards green with the throttle verifiably absent from process-change."; }
    part pullOversightImplementGateR1 : TestResult { :>> id = "a57298ee-efa2-46db-aa0c-04242569d873"; :>> outcome = VerdictKind::pass; :>> judgedAgainst = "7ef444399f80b9ee54fe420555d9319607818865"; :>> judgedAt = "2026-08-23"; :>> judgedBy = "claudeFable5"; }
    verification pullOversightReviewGate : Test { :>> id = "c8e9a136-7215-4764-9d61-3b88a9e0f784"; :>> title = "Sprint 432 review gate — three passes per D0172"; :>> createdAt = "2026-08-23"; :>> createdBy = "claudeFable5"; :>> method = VerificationMethod::inspect; :>> procedureText = "PASS 1, CLAIMS: all read-backs quoted from this session. PASS 2, BOUNDARY: this supersedes parts of a decision the human signed 24 hours earlier - recorded as exactly that, a direction reversal on contact with the built thing, not a drafting error; the panel's rubber-stamp findings REMAIN true and recorded, and the residual is honest: with the ask gone, the override-rate indicator will likely stay at its alarm value indefinitely, which the record states rather than hides. PASS 3, OWN DIFF: the sprint-431 work retired here was one day old - the avoidable half is that OPTION A shipped the conscription clauses without asking whether the supervisor WANTED to be sampled; the D0203 deciding-context rule existed but the cost-to-THEM was buried mid-option. Lesson: a decision option's COST line must separate cost-to-the-system from cost-to-the-human. WHAT A REVIEWER SHOULD ATTACK: whether removing the throttle re-opens unbounded autonomous drift - the answer on record is that hard gates, CI, and the blockers deck are untouched, and the human can halt everything with one word, which is the control that actually binds."; }
    part pullOversightReviewGateR1 : TestResult { :>> id = "2fefe995-1aa9-46c7-b553-ca6eee76062e"; :>> outcome = VerdictKind::pass; :>> judgedAgainst = "7ef444399f80b9ee54fe420555d9319607818865"; :>> judgedAt = "2026-08-23"; :>> judgedBy = "claudeFable5"; }
    verification pullOversightCloseOutGate : Test { :>> id = "ea991137-5239-4355-b104-d58a0bb7d014"; :>> title = "Sprint 432 closeOut gate (autonomous, D0049)"; :>> createdAt = "2026-08-23"; :>> createdBy = "claudeFable5"; :>> method = VerificationMethod::inspect; :>> procedureText = "Autonomous closeOut (D0049, itself reframed by this sprint). The deck holds only true blockers (tap-to-sign, blind-spot fence); validate + all 47 guards green."; }
    part pullOversightCloseOutGateR1 : TestResult { :>> id = "33174c4a-d22b-4683-950f-956ee8cb53e2"; :>> outcome = VerdictKind::pass; :>> judgedAgainst = "7ef444399f80b9ee54fe420555d9319607818865"; :>> judgedAt = "2026-08-23"; :>> judgedBy = "claudeFable5"; }
    verification pullOversightRetroGate : Test { :>> id = "723c08d3-e447-4639-8b4e-05cee2e19883"; :>> title = "Sprint 432 retro gate (autonomous, D0049)"; :>> createdAt = "2026-08-23"; :>> createdBy = "claudeFable5"; :>> method = VerificationMethod::analyze; :>> procedureText = "Autonomous retro (D0049). AVOIDABLE-ISSUE SCAN under rcRecurrence: the conscription class - designing the supervisor INTO the machinery - now has a named kill rule (D0204) and a memory; the recurrence risk is any future control whose enforcement path runs through human attention, and the review checklist question is now 'who pays the attention cost of this control?'. WELL: the reversal cost one sprint because the records and the asks were cleanly separated all along - removing push left pull intact with zero data loss. Estimate 2 pts, delivered 2."; }
    part pullOversightRetroGateR1 : TestResult { :>> id = "919939c9-ddb5-4536-aa49-7f9805840e57"; :>> outcome = VerdictKind::pass; :>> judgedAgainst = "7ef444399f80b9ee54fe420555d9319607818865"; :>> judgedAt = "2026-08-23"; :>> judgedBy = "claudeFable5"; }
}
