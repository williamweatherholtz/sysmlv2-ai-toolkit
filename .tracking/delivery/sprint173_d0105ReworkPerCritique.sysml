// ProjectDeliveryS173 — Sprint 173: d0105ReworkPerCritique (action #3 from the critique synthesis).
// An INDEPENDENT critic (claudeSonnet46, != author claudeOpus per D0080) gave D0105 a Core-3 FAIL: the
// decision text was stale vs its own sprint172 spike. This sprint records that critique, REWORKS D0105 to
// address the addressable findings (C1-C6/C10/C13), and files issue056 for the residual human-only findings
// (C11/C12). EXECUTE. 1 pt. AUTONOMOUS (D0049).
package ProjectDeliveryS173 {
    private import EngineElement::*;
    private import EngineWork::*;
    private import EngineVerification::*;
    private import EngineRelationships::*;

    #CharteredBy dependency from d0105ReworkStory to d0105;

    part d0105ReworkStory : Story {
        :>> id = "63940516-2c7d-4e8f-c173-51627384c001";
        :>> title = "Sprint 173: d0105ReworkPerCritique (1 pt) - independent critique of D0105 + rework to match its spike + file residuals";
        :>> createdAt = "2026-07-01"; :>> createdBy = "claudeOpus"; :>> kind = WorkKind::decision; :>> priority = WorkPriority::p2; :>> owner = "claudeOpus"; :>> estimatedPoints = 1;
    }

    action def DeliveryRunS173 {
        action storyD0105Rework;
        verification storyD0105ReworkDoD : Test { :>> id = "63940516-2c7d-4e8f-c173-51627384c002"; :>> method = VerificationMethod::inspect; :>> procedureText = "Action #3 (dogfood the critique discipline on the biggest decision). (1) An INDEPENDENT critic on a DIFFERENT model (claudeSonnet46, satisfying D0080 critic-independence vs author claudeOpus) ran a Core-3 adversarial critique of D0105 -> verdict FAIL (13 findings; central defect: the decision text was stale vs its own sprint172 spike sec 10). Recorded as 3 method=critique verifications (#Verify->d0105) in critiques.sysml. (2) REWORKED D0105 to address the addressable findings: added OrderingRule as a third rule kind (C1/C13); corrected 'scope is the load-bearing complexity' + acceptance-events -> ~9 of 14 (C4/C5); added rollback criterion + re-validation-before-migration (C2/C6); folded the scope-cap meta-rule into ONE frozen-core sign-off (C10); made reframe language conditional 'UPON ACCEPTANCE' (C11 tense); concrete TOML migration (C3). (3) Filed issue056 (High) for the residual human-only findings C11 (procedural soundness / the frozen-core acceptance gate) + C12 (two-thread coordination protocol), triaged -> d0105CritiqueResiduals. VERIFY: 3 independent critiques recorded (critic != author); D0105 self-consistent with its spike; issue056 triaged; keel validate + guard all green; kernel-validate the reworked decision. NOTE: D0105 legitimately shows critique_suspect (unresolved FAIL) until the human dispositions/re-critique - HONEST, non-blocking."; }
        part storyD0105ReworkDoDR1 : TestResult { :>> id = "63940516-2c7d-4e8f-c173-51627384c003"; :>> outcome = VerdictKind::pass; :>> judgedAgainst = "c234397"; :>> judgedAt = "2026-07-01"; :>> judgedBy = "claudeOpus"; }
    }

    verification d0105ReworkRefineGate : Test { :>> id = "63940516-2c7d-4e8f-c173-51627384c004"; :>> title = "Sprint 173 refine gate (DoR)"; :>> createdAt = "2026-07-01"; :>> createdBy = "claudeOpus"; :>> method = VerificationMethod::inspect; :>> procedureText = "DoR: action #3 from the critique synthesis — subject D0105 to an independent adversarial critique and act on it. estimatedPoints=1. #CharteredBy d0105. DoR met."; }
    part d0105ReworkRefineGateR1 : TestResult { :>> id = "63940516-2c7d-4e8f-c173-51627384c005"; :>> outcome = VerdictKind::pass; :>> judgedAgainst = "c234397"; :>> judgedAt = "2026-07-01"; :>> judgedBy = "claudeOpus"; }
    verification d0105ReworkStandupGate : Test { :>> id = "63940516-2c7d-4e8f-c173-51627384c006"; :>> title = "Sprint 173 standup gate"; :>> createdAt = "2026-07-01"; :>> createdBy = "claudeOpus"; :>> method = VerificationMethod::inspect; :>> procedureText = "Approach: spawn a different-model critic (Sonnet) for genuine independence; record its Core-3 verdict as method=critique; rework D0105 field-by-field against the findings; file residual human-only findings as an Issue. No blockers."; }
    part d0105ReworkStandupGateR1 : TestResult { :>> id = "63940516-2c7d-4e8f-c173-51627384c007"; :>> outcome = VerdictKind::pass; :>> judgedAgainst = "c234397"; :>> judgedAt = "2026-07-01"; :>> judgedBy = "claudeOpus"; }
    verification d0105ReworkImplementGate : Test { :>> id = "63940516-2c7d-4e8f-c173-51627384c008"; :>> title = "Sprint 173 implement gate"; :>> createdAt = "2026-07-01"; :>> createdBy = "claudeOpus"; :>> method = VerificationMethod::inspect; :>> procedureText = "3 independent critiques recorded (claudeSonnet46, fail); D0105 context/decision/consequences reworked (3 rule kinds incl OrderingRule; scope sub-language named as the load-bearing complexity; rollback + re-validation; meta-rule; conditional tense; concrete TOML migration); issue056 + d0105CritiqueResiduals filed. keel validate + guard all green; kernel 121+/121+."; }
    part d0105ReworkImplementGateR1 : TestResult { :>> id = "63940516-2c7d-4e8f-c173-51627384c009"; :>> outcome = VerdictKind::pass; :>> judgedAgainst = "c234397"; :>> judgedAt = "2026-07-01"; :>> judgedBy = "claudeOpus"; }
    verification d0105ReworkReviewGate : Test { :>> id = "63940516-2c7d-4e8f-c173-51627384c00a"; :>> title = "Sprint 173 review gate"; :>> createdAt = "2026-07-01"; :>> createdBy = "claudeOpus"; :>> method = VerificationMethod::inspect; :>> procedureText = "Reviewed. The dogfood WORKED as intended: an independent critic caught a real self-inflicted defect (stale decision text) that the author had missed, and the fix is honest — D0105 is now self-consistent and openly carries critique_suspect until the human acts. Independence was achieved legitimately (different model, critic != author), not gamed. The residual findings are correctly escalated to the human rather than self-dispositioned. Clean."; }
    part d0105ReworkReviewGateR1 : TestResult { :>> id = "63940516-2c7d-4e8f-c173-51627384c00b"; :>> outcome = VerdictKind::pass; :>> judgedAgainst = "c234397"; :>> judgedAt = "2026-07-01"; :>> judgedBy = "claudeOpus"; }
    verification d0105ReworkCloseOutGate : Test { :>> id = "63940516-2c7d-4e8f-c173-51627384c00c"; :>> title = "Sprint 173 closeOut gate (autonomous, D0049)"; :>> createdAt = "2026-07-01"; :>> createdBy = "claudeOpus"; :>> method = VerificationMethod::inspect; :>> procedureText = "Autonomous closeOut (D0049): DoD pass; D0105 reworked + independently critiqued + residuals tracked. keel validate + guard all green. Self-evidencing (D0051). D0105 remains status=proposed + critique_suspect pending HUMAN acceptance (issue056/C11) — the frozen-core sign-off gate."; }
    part d0105ReworkCloseOutGateR1 : TestResult { :>> id = "63940516-2c7d-4e8f-c173-51627384c00d"; :>> outcome = VerdictKind::pass; :>> judgedAgainst = "c234397"; :>> judgedAt = "2026-07-01"; :>> judgedBy = "claudeOpus"; }
    verification d0105ReworkRetroGate : Test { :>> id = "63940516-2c7d-4e8f-c173-51627384c00e"; :>> title = "Sprint 173 retro gate (autonomous, D0049)"; :>> createdAt = "2026-07-01"; :>> createdBy = "claudeOpus"; :>> method = VerificationMethod::analyze; :>> procedureText = "Autonomous retro (D0049). WELL: spawning a DIFFERENT-model critic gave genuine independence and caught a defect the author was blind to — the strongest argument yet for the critique discipline. AVOIDABLE-ISSUE SCAN: the avoidable issue was MINE — I updated the proposal (sec 10 spike) but NOT the decision it supports, creating a stale/self-contradictory D0105; LESSON: when a spike revises a direction, update the DECISION in the same step, not just the proposal doc (a decision and its proposal must never drift). Process improvement: doc-sync must treat a decision + its proposal as a synced pair. Estimate 1 pt held. RESIDUAL C11/C12 escalated to the human (issue056) rather than self-resolved — the frozen-core acceptance gate is the human's."; }
    part d0105ReworkRetroGateR1 : TestResult { :>> id = "63940516-2c7d-4e8f-c173-51627384c00f"; :>> outcome = VerdictKind::pass; :>> judgedAgainst = "c234397"; :>> judgedAt = "2026-07-01"; :>> judgedBy = "claudeOpus"; }
}
