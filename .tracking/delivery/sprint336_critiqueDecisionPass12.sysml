// ProjectDeliveryS336 — Sprint 336: critique pass 12. Under-covered a target for the second time, so the
// batch writer now refuses it. EXECUTE. 3 pts.
package ProjectDeliveryS336 {
    private import EngineElement::*;
    private import EngineWork::*;
    private import EngineVerification::*;
    private import EngineRelationships::*;

    #CharteredBy dependency from critPass12Story to d0080;

    part critPass12Story : Story {
        :>> id = "0d8004b0-0814-64b0-9b3e-0000003004b0";
        :>> title = "Sprint 336: critique pass 12 — 5 viewer-programme Decisions, 7 fail / 8 pass (3 pts)";
        :>> createdAt = "2026-08-17"; :>> createdBy = "claudeOpus5"; :>> kind = WorkKind::modeling; :>> priority = WorkPriority::p0; :>> owner = "claudeOpus5"; :>> estimatedPoints = 3;
    }

    action def DeliveryRunS336 {
        action storyCritPass12;
        verification storyCritPass12DoD : Test { :>> id = "0d8004b1-0814-64b1-9b3e-0000003004b1"; :>> method = VerificationMethod::analyze; :>> procedureText = "Pass 12: d0117, d0118, d0119, d0120, d0121 — the viewer-programme Decisions. 7 fail, 8 pass. THE FINDING: D0119 IS AN ACCEPTED DECISION THAT HAS PRODUCED NOTHING, and I checked both clauses rather than inferring. Clause (1), marked HIGH, asks to align a read endpoint to the standard Systems Modeling API JSON envelope (@type/@id/ownedRelationship) — no @type or ownedRelationship appears anywhere in keel-cli's source. Clause (2), MEDIUM, asks that viewpoint presets be named after the standard view kinds (General, Interconnection, Action, State, Sequence, Requirement, Tree, Table) — the registry's 32 viewpoints carry none of those names. Clause (3) was explicitly optional and is also absent, which is fine. So a Decision whose stated payoff is interoperability with any SysML v2 tool has delivered in neither priority band, and NOTHING RECORDS THAT: it derived no requirement, so no coverage number falls when it goes unbuilt. Its likely cause is in its own completeness gap — the interoperability payoff has no definition of done, and a HIGH-priority clause with no acceptance criterion competes badly against work that has one. SECOND: D0117 assigns keel the job of exposing the model so the viewer can generate itself, and claims a new type becomes 'viewable + manipulable with no viewer code change' — viewable is delivered (item_detail, /api/schema), manipulable is not (`keel record` takes two hardcoded verbs), so the half only partly delivered is the half on keel's side of the seam. READ BACK: Decision coverage 34 -> 39 of 75."; }
        part storyCritPass12DoDR1 : TestResult { :>> id = "0d8004b2-0814-64b2-9b3e-0000003004b2"; :>> outcome = VerdictKind::pass; :>> judgedAgainst = "e6b25d0"; :>> judgedAt = "2026-08-17"; :>> judgedBy = "claudeOpus5"; }
    }

    verification c12RefineGate : Test { :>> id = "0d8004b3-0814-64b3-9b3e-0000003004b3"; :>> title = "Sprint 336 refine gate (DoR)"; :>> createdAt = "2026-08-17"; :>> createdBy = "claudeOpus5"; :>> method = VerificationMethod::inspect; :>> procedureText = "DoR. Five viewer-programme Decisions. Four claims measured before judgment: whether the standard JSON envelope appears anywhere in the source (it does not), whether any viewpoint carries a standard view-kind name (none does), whether attribute_stats supplies what D0120 asks keel for (it does), and whether the review queue and its acceptance endpoints exist (they do). Two of the four turned into feasibility fails and two into passes. estimatedPoints=3."; }
    part c12RefineGateR1 : TestResult { :>> id = "0d8004b4-0814-64b4-9b3e-0000003004b4"; :>> outcome = VerdictKind::pass; :>> judgedAgainst = "e6b25d0"; :>> judgedAt = "2026-08-17"; :>> judgedBy = "claudeOpus5"; }

    verification c12StandupGate : Test { :>> id = "0d8004b5-0814-64b5-9b3e-0000003004b5"; :>> title = "Sprint 336 standup gate"; :>> createdAt = "2026-08-17"; :>> createdBy = "claudeOpus5"; :>> method = VerificationMethod::inspect; :>> procedureText = "Approach: for a Decision that assigns work to two sides of a seam (keel versus the viewer app), judge feasibility only on THIS repository's side and say so — otherwise an unbuilt viewer feature reads as a failure of a Decision that correctly delegated it. Applied to D0120, which passes feasibility because the metadata it asks keel for exists, while its viewer-side encoding engine is a scheduling fact rather than a defect. No blockers."; }
    part c12StandupGateR1 : TestResult { :>> id = "0d8004b6-0814-64b6-9b3e-0000003004b6"; :>> outcome = VerdictKind::pass; :>> judgedAgainst = "e6b25d0"; :>> judgedAt = "2026-08-17"; :>> judgedBy = "claudeOpus5"; }

    verification c12ImplementGate : Test { :>> id = "0d8004b7-0814-64b7-9b3e-0000003004b7"; :>> title = "Sprint 336 implement gate"; :>> createdAt = "2026-08-17"; :>> createdBy = "claudeOpus5"; :>> method = VerificationMethod::test; :>> procedureText = "I UNDER-COVERED A TARGET FOR THE SECOND TIME AND THIS TIME BUILT THE CONTROL. In pass 10 I wrote 14 critiques where 15 were owed and d0109 stayed uncovered; here the same slip left d0121 with two lenses of three. Both times the batch looked complete and only the computed coverage number disagreed. In pass 10's retro I noted that the batch writer COULD check each target's lens set against critique-policy.toml and chose not to build it — a second occurrence makes that the wrong call under D0047, so crit_write.py now reads the policy, unions the batch's lenses with those already declared on file for that target, and REFUSES a batch that would leave the target matching no required set. The union matters: a legitimate COMPLETION batch carries one lens, and a naive check would reject exactly the fix. Verified in both directions — the completion batch passed, and the check names the target and the missing lens when it refuses."; }
    part c12ImplementGateR1 : TestResult { :>> id = "0d8004b8-0814-64b8-9b3e-0000003004b8"; :>> outcome = VerdictKind::pass; :>> judgedAgainst = "e6b25d0"; :>> judgedAt = "2026-08-17"; :>> judgedBy = "claudeOpus5"; }

    verification c12ReviewGate : Test { :>> id = "0d8004b9-0814-64b9-9b3e-0000003004b9"; :>> title = "Sprint 336 review gate"; :>> createdAt = "2026-08-17"; :>> createdBy = "claudeOpus5"; :>> method = VerificationMethod::inspect; :>> procedureText = "Reviewed. AN UNBUILT DECISION THAT DERIVES NO REQUIREMENT IS INVISIBLE, and D0119 is the clean example this corpus needed. Every other unbuilt clause found in these two Decision passes was at least ADJACENT to something computed — D0105's rule kinds show up as a guard count that did not fall, D0106's parallel execution as a frontier that is a ranked list. D0119 derived nothing, so its non-delivery moves no number at all: not coverage, not the burndown, not the frontier. The only reason it surfaced is that a critique pass read its clauses against the source. That is an argument for the critique layer as a control in its own right rather than a quality nicety, and it is worth stating plainly: for a Decision with no derived requirement, examination is the ONLY mechanism that can notice it was never carried out. WHAT I DID NOT DO: raise an Issue. The remedy is either to derive requirements from D0119 or to supersede it, and both are the owner's calls."; }
    part c12ReviewGateR1 : TestResult { :>> id = "0d8004ba-0814-64ba-9b3e-0000003004ba"; :>> outcome = VerdictKind::pass; :>> judgedAgainst = "e6b25d0"; :>> judgedAt = "2026-08-17"; :>> judgedBy = "claudeOpus5"; }

    verification c12CloseOutGate : Test { :>> id = "0d8004bb-0814-64bb-9b3e-0000003004bb"; :>> title = "Sprint 336 closeOut gate (autonomous, D0049)"; :>> createdAt = "2026-08-17"; :>> createdBy = "claudeOpus5"; :>> method = VerificationMethod::inspect; :>> procedureText = "Autonomous closeOut (D0049). Decision coverage 34 -> 39 of 75; 7 critiquable Decisions remain. validate clean; check-engine clean; 35 guards ALL PASS; no engine code changed (the control added this sprint is in the scratch batch writer, outside the model, and is recorded here rather than in guards.md because it governs my authoring rather than the project's artifacts)."; }
    part c12CloseOutGateR1 : TestResult { :>> id = "0d8004bc-0814-64bc-9b3e-0000003004bc"; :>> outcome = VerdictKind::pass; :>> judgedAgainst = "e6b25d0"; :>> judgedAt = "2026-08-17"; :>> judgedBy = "claudeOpus5"; }

    verification c12RetroGate : Test { :>> id = "0d8004bd-0814-64bd-9b3e-0000003004bd"; :>> title = "Sprint 336 retro gate (autonomous, D0049)"; :>> createdAt = "2026-08-17"; :>> createdBy = "claudeOpus5"; :>> method = VerificationMethod::analyze; :>> procedureText = "Autonomous retro (D0049) under D0131's retroTrack. AVOIDABLE-ISSUE, SECOND OCCURRENCE, NOW CONTROLLED: under-covering a target's lens set. Pass 10 was the first; I recorded then that a check was possible and declined it because the computed view catches the error at zero cost. That reasoning was wrong in one specific way and the second occurrence proves it — the computed view only catches it if I LOOK, and I look at the end, after the batch is written and the sprint record drafted, so the cost of the miss is a rewrite rather than a refusal. The control now sits where the error is made. WELL: (1) judging a two-sided Decision only on this repository's side kept D0120's feasibility verdict honest — its keel half shipped and its viewer half is delegated, which is not the same as unbuilt; (2) the D0119 finding names something structural rather than local: a Decision that derives no requirement is invisible to every computed view when it goes unbuilt, so examination is the only control that can notice. Estimate 3 pts, delivered."; }
    part c12RetroGateR1 : TestResult { :>> id = "0d8004be-0814-64be-9b3e-0000003004be"; :>> outcome = VerdictKind::pass; :>> judgedAgainst = "e6b25d0"; :>> judgedAt = "2026-08-17"; :>> judgedBy = "claudeOpus5"; }
}
