// ProjectDeliveryS533 — Sprint 533: config-change refuses the kill switch and restores the file. EXECUTE. 2 pts.
package ProjectDeliveryS533 {
    private import EngineElement::*;
    private import EngineWork::*;
    private import EngineVerification::*;
    private import EngineRelationships::*;

    #CharteredBy dependency from configChangeStory to d0296;

    part configChangeStory : Story {
        :>> id = "315b8a9d-aa60-4b91-8b0f-145ea366510b";
        :>> title = "Sprint 533: the sixth hook - ConfigChange refuses a repo-scope settings change that kills or guts the hooks, and puts the file back (2 pts)";
        :>> createdAt = "2026-09-03"; :>> createdBy = "claudeOpus5"; :>> kind = WorkKind::code; :>> priority = WorkPriority::p0; :>> owner = "claudeOpus5"; :>> estimatedPoints = 2;
    }

    action def DeliveryRunS533 {
        action storyConfigChange;
        verification storyConfigChangeDoD : Test { :>> id = "db5b30d4-f8f4-4d96-bc04-b96ea349bf65"; :>> method = VerificationMethod::test; :>> procedureText = "DELIVERED BACKLOG ITEMS: dcHookConfigChangeRestoresTheFile. DONE: keel_hooks gains ConfigChange (matcher project_settings|local_settings) so both renderings carry it; hook config-change reads the file at the payload's file_path - the payload has no content - and restored_settings decides: settings.json is re-merged (strips the key, restores altered or removed keel entries), settings.local.json loses only the key, a clean file is left alone; refusal is exit 2 with the reason on stderr and a block line in the fire-ledger; unreadable or non-JSON files are reported and allowed. cli facts and commands.sysml carry the new event; control-structure titles it refuses and restores. VERIFY: two new tests (unit decision table; integration - plant, gut, benign, ledger count), 460 pass, clippy clean; live nested session reproduced D0296 run 4 and closed run 5's gap."; }
        // RAN: cargo test --release 460/0; clippy 0; keel sync-claude then --check clean (both renderings); nested claude -p --plugin-dir: agent Write of disableAllHooks:true -> hooks.jsonl config-change block exit 2 -> settings.json on disk = six events, no key -> pre-bash/stop lines continue; the nested agent reported the file replaced by the next tool call
        part storyConfigChangeDoDR1 : TestResult { :>> id = "69b040ce-7753-4808-91d4-b270f2044077"; :>> outcome = VerdictKind::pass; :>> judgedAgainst = "42fa740"; :>> judgedAt = "2026-09-03"; :>> judgedBy = "claudeOpus5"; }
    }

    verification configChangeRefineGate : Test { :>> id = "cd6202cc-7b77-4dcb-93b5-c037a0c4a6c4"; :>> title = "Sprint 533 refine gate (DoR)"; :>> createdAt = "2026-09-03"; :>> createdBy = "claudeOpus5"; :>> method = VerificationMethod::inspect; :>> procedureText = "READY from D0296 runs 3, 4 and 5: the payload shape (no content), the deny's reach (the live session) and its hole (the file survives) were all observed before design; the DoD named read-file_path, deny, restore, ledger."; }
    verification configChangeStandupGate : Test { :>> id = "b8b5b57f-2723-47e6-bf9e-9178603e89d0"; :>> title = "Sprint 533 standup gate"; :>> createdAt = "2026-09-03"; :>> createdBy = "claudeOpus5"; :>> method = VerificationMethod::inspect; :>> procedureText = "ONE CHOICE: restore settings.json to the full merge, not just strip the key - a change that REMOVES the turn gate is the same class of self-modification (D0209) and the same handler sees it for free. Second: settings.local.json is the user's file and only the key leaves it. Third: the restore itself fires ConfigChange again; that second fire finds nothing wrong and allows - no loop, and the ledger shows both."; }
    verification configChangeImplementGate : Test { :>> id = "93aa9c3f-e805-4767-adf0-651bf4fbec55"; :>> title = "Sprint 533 implement gate"; :>> createdAt = "2026-09-03"; :>> createdBy = "claudeOpus5"; :>> method = VerificationMethod::test; :>> procedureText = "RAN: script through the Write tool; build clean; four clippy items (three backtick docs, one redundant clone). The nested fixture was not a keel project so sync-claude refused to seed it - the agent's own Write created the settings file, and the restore wrote the full six-event set into a file that had never held it, which is stronger than the planned receipt."; }
    verification configChangeReviewGate : Test { :>> id = "861b4bf2-6b32-49b1-a9b1-cc7ee699adf6"; :>> title = "Sprint 533 review gate — three passes per D0172"; :>> createdAt = "2026-09-03"; :>> createdBy = "claudeOpus5"; :>> method = VerificationMethod::inspect; :>> procedureText = "THREE PASSES. (1) CAN IT LOOP: the restore is idempotent (merge twice = merge once) and the second fire allows; tested by the ledger count of exactly two blocks over three changes. (2) CAN IT DESTROY THE USER'S ENTRIES: no - merge keeps foreign keys (tested: theirs survives) and local files lose only the key. (3) WHAT IT STILL CANNOT DO: the hook lives in the same repo-scope file it protects; if the agent deletes the file outright the payload arrives with a path that cannot be read and the hook allows - the plugin rendering (dcLaunchPinsHooksOn) is what fires then, and CI's drift guard sees the missing file. Said in the handler's own message."; }
    verification configChangeCloseOutGate : Test { :>> id = "35875834-a303-4965-b271-b29cfa357fea"; :>> title = "Sprint 533 closeOut gate (autonomous, D0049)"; :>> createdAt = "2026-09-03"; :>> createdBy = "claudeOpus5"; :>> method = VerificationMethod::inspect; :>> procedureText = "CLOSED. Both renderings regenerated and committed; guards.md says six events; CLAUDE.md section 5 carries the handler."; }
    verification configChangeRetroGate : Test { :>> id = "750a0e6f-0637-4247-a39b-483fde2bd5cd"; :>> title = "Sprint 533 retro gate (autonomous, D0049)"; :>> createdAt = "2026-09-03"; :>> createdBy = "claudeOpus5"; :>> method = VerificationMethod::analyze; :>> procedureText = "no new item - already tracked: the deleted-file case in the review is covered by the launch item dcLaunchPinsHooksOn (chartered by d0296, next) and by the drift guard in CI; the fixture-not-a-project friction in the nested runs is the same shape as issue269's refusal-over-nothing and is correct behaviour, not a finding."; }
}
