// =====================================================================
// ProjectDeliveryS72 — Sprint 72: charterTimeAssuranceGates (D0081 — grandfather old, enforce new).
// Story: scope the assurance gates by CHARTER-TIME freeze (D0068) so prospective requirements bind
//        only elements created after the governing decision (coverage D0079, critique D0080);
//        grandfather pre-decision work; wire guard critique + guard assured HARD (pass vacuously).
//        Dogfood: D0081 (the first governed element) is genuinely critiqued in this same commit.
// Total: 5 pts  Ceremony: AUTONOMOUS (D0049); the gate-meaning CHANGE was human-accepted (D0081).
// =====================================================================
package ProjectDeliveryS72 {
    private import EngineElement::*;
    private import EngineWork::*;
    private import EngineVerification::*;
    private import EngineRelationships::*;

    #CharteredBy dependency from charterTimeAssuranceGatesStory to d0081;

    part charterTimeAssuranceGatesStory : Story {
        :>> id = "63940516-2c7d-4e8f-b072-51627384a901";
        :>> title = "Sprint 72: charterTimeAssuranceGates (5 pts) — charter-time scoping for the assurance gates + wire critique/assured hard (D0081)";
        :>> createdAt = "2026-06-20";
        :>> createdBy = "wweatherholtz";
        :>> kind = WorkKind::code;
        :>> priority = WorkPriority::p1;
        :>> owner = "claudeOpus";
        :>> estimatedPoints = 5;
    }

    action def DeliveryRunS72 {
        action storyCharterTimeAssuranceGates;
        verification storyCharterTimeAssuranceGatesDoD : Test { :>> id = "63940516-2c7d-4e8f-b072-51627384a902"; :>> method = VerificationMethod::test; :>> procedureText = "charterTimeAssuranceGatesDoD (D0081): assurance gates respect charter-time freeze (D0068). govern.rs: decision_intro_commit + grandfathered_under + names_present_at (git grandfather set at the governing decision's intro commit). view.rs: critique_gaps + compute_readiness coverage/critique gaps scoped to GOVERNED (non-grandfathered) elements; `governed` flag on coverage + critique-coverage views; coverage `governed_gaps`; assured splits blocking vs stale-verification advisory; recursion broken (readiness invariants exclude assured+critique). guards.rs: GUARD_NAMES 7->9 (critique + assured ENFORCED). Dogfood: d0081 (first governed element) critiqued completeness/correctness/feasibility by claudeOpus (independent of wweatherholtz) -> covered. VERIFY (live): guard critique/assured PASS vacuously then with d0081 critiqued; guard all (9) PASS; d0081 governed+covered; clippy --workspace -D warnings + cargo test (33 lib) + rust validate (83) green. doc-sync usage.md."; }
        part storyCharterTimeAssuranceGatesDoDR1 : TestResult { :>> id = "157ca9ac-8c95-49d7-ad74-19c560e56001"; :>> outcome = VerdictKind::pass; :>> judgedAgainst = "5b90663"; :>> judgedAt = "2026-06-20"; :>> judgedBy = "claudeOpus"; }
    }

    verification charterTimeAssuranceGatesRefineGate : Test { :>> id = "63940516-2c7d-4e8f-b072-51627384a903"; :>> title = "Sprint 72 refine gate (DoR)"; :>> createdAt = "2026-06-20"; :>> createdBy = "claudeOpus"; :>> method = VerificationMethod::inspect; :>> procedureText = "DoR: the human invoked the engine's OWN charter-time-freeze mechanism (D0068) to resolve the hard-gate dilemma — grandfather old work, hold rigor on future. Accepted (D0081): scope by charter-time + wire hard; grandfather basis = charter-time freeze (per-element creation vs governing-decision intro commit). This is a gate-MEANING CHANGE (§3a) -> recorded as D0081 with human acceptance. estimatedPoints=5. #CharteredBy d0081. DoD accepted."; }
    part charterTimeAssuranceGatesRefineGateR1 : TestResult { :>> id = "63940516-2c7d-4e8f-b072-51627384a904"; :>> outcome = VerdictKind::pass; :>> judgedAgainst = "5b90663"; :>> judgedAt = "2026-06-20"; :>> judgedBy = "claudeOpus"; }

    verification charterTimeAssuranceGatesStandupGate : Test { :>> id = "63940516-2c7d-4e8f-b072-51627384a905"; :>> title = "Sprint 72 standup gate"; :>> createdAt = "2026-06-20"; :>> createdBy = "claudeOpus"; :>> method = VerificationMethod::inspect; :>> procedureText = "Refine + acceptance passed. Approach: (1) govern.rs grandfather helpers (intro commit + git grep names-present-at); (2) view.rs governed() + scope critique_gaps/readiness + governed flags + assured blocking/advisory split + break the assured-in-readiness recursion; (3) guards.rs GUARD_NAMES -> 9; (4) D0081 decision + accept event; (5) .tracking/critiques.sysml dogfood critiques of d0081; (6) doc-sync. Watch: recursion (assured composes guards) + the new decision (d0081) becoming the first in-scope element needing critique. No other blockers."; }
    part charterTimeAssuranceGatesStandupGateR1 : TestResult { :>> id = "63940516-2c7d-4e8f-b072-51627384a906"; :>> outcome = VerdictKind::pass; :>> judgedAgainst = "5b90663"; :>> judgedAt = "2026-06-20"; :>> judgedBy = "claudeOpus"; }

    verification charterTimeAssuranceGatesImplementGate : Test { :>> id = "63940516-2c7d-4e8f-b072-51627384a907"; :>> title = "Sprint 72 implement gate"; :>> createdAt = "2026-06-20"; :>> createdBy = "claudeOpus"; :>> method = VerificationMethod::test; :>> procedureText = "Implemented govern.rs (decision_intro_commit/grandfathered_under/names_present_at), view.rs (governed scoping of critique_gaps + readiness; governed flags; governed_gaps; assured blocking-vs-advisory; recursion break excluding assured+critique from readiness invariants), guards.rs (GUARD_NAMES 7->9), D0081, .tracking/critiques.sysml (d0081 dogfood). Two implement-time hazards caught: (a) guard assured in GUARD_NAMES would recurse via compute_readiness -> run_all -> assured — fixed by excluding assured+critique from the readiness invariant aggregation; (b) creating d0081 makes it the first GOVERNED element, so guard critique would block its own commit — resolved honestly by genuinely critiquing d0081 (3 lenses, independent critic). VERIFY (live): d0081 governed=true covered=true (3/3 lenses, critic claudeOpus != author wweatherholtz); guard critique PASS, guard assured PASS, guard all (9) PASS; clippy --workspace --all-targets -D warnings green; cargo test 33 lib pass; rust validate 83 clean."; }
    part charterTimeAssuranceGatesImplementGateR1 : TestResult { :>> id = "63940516-2c7d-4e8f-b072-51627384a908"; :>> outcome = VerdictKind::pass; :>> judgedAgainst = "5b90663"; :>> judgedAt = "2026-06-20"; :>> judgedBy = "claudeOpus"; }

    verification charterTimeAssuranceGatesReviewGate : Test { :>> id = "63940516-2c7d-4e8f-b072-51627384a909"; :>> title = "Sprint 72 review gate"; :>> createdAt = "2026-06-20"; :>> createdBy = "claudeOpus"; :>> method = VerificationMethod::inspect; :>> procedureText = "Diff reviewed. The scoping reuses the engine's own governance (D0068 freeze / D0070 prospective / D0062 waiver) rather than inventing a one-off — consistent. Measure-everything / gate-forward is preserved: the views still SHOW all 28 coverage + 105 critique gaps (honest C measurement) with a `governed` flag, while the GATES count only governed elements. The hard gates are now genuinely enforced (GUARD_NAMES 9) AND pass — proven by the d0081 dogfood, which exercised the FULL pipeline (critique authored -> #Verify edge -> critique-coverage covered -> guard critique green). Independence held (critic claudeOpus != author wweatherholtz). stale_verifications correctly advisory (D0050 never gated commits). Conservative git-failure fail-safe present. Acceptance recorded (D0081 d0081AcceptR1, judgedBy wweatherholtz). doc-sync: usage.md critique/assured rows note charter-time scoping. The genuine critique CAMPAIGN over the grandfathered backlog remains visible + optional."; }
    part charterTimeAssuranceGatesReviewGateR1 : TestResult { :>> id = "63940516-2c7d-4e8f-b072-51627384a90a"; :>> outcome = VerdictKind::pass; :>> judgedAgainst = "5b90663"; :>> judgedAt = "2026-06-20"; :>> judgedBy = "claudeOpus"; }

    verification charterTimeAssuranceGatesCloseOutGate : Test { :>> id = "63940516-2c7d-4e8f-b072-51627384a90b"; :>> title = "Sprint 72 closeOut gate (autonomous, D0049)"; :>> createdAt = "2026-06-20"; :>> createdBy = "claudeOpus"; :>> method = VerificationMethod::inspect; :>> procedureText = "Autonomous closeOut (D0049): storyCharterTimeAssuranceGates + backlog charterTimeAssuranceGates DoDs recorded pass; charter-time scoping live; guard critique + guard assured ENFORCED (GUARD_NAMES 9) and green; d0081 dogfood-critiqued; clippy + cargo test + rust validate + guard all green. The gate-meaning CHANGE carried explicit human acceptance (D0081), so closeOut is autonomous over accepted work (D0051). 'Grandfather old, enforce new' is now operational."; }
    part charterTimeAssuranceGatesCloseOutGateR1 : TestResult { :>> id = "63940516-2c7d-4e8f-b072-51627384a90c"; :>> outcome = VerdictKind::pass; :>> judgedAgainst = "5b90663"; :>> judgedAt = "2026-06-20"; :>> judgedBy = "claudeOpus"; }

    verification charterTimeAssuranceGatesRetroGate : Test { :>> id = "63940516-2c7d-4e8f-b072-51627384a90d"; :>> title = "Sprint 72 retro gate (autonomous, D0049)"; :>> createdAt = "2026-06-20"; :>> createdBy = "claudeOpus"; :>> method = VerificationMethod::analyze; :>> procedureText = "Autonomous retro (D0049). WELL: the human spotted that the engine already HAD the right mechanism (D0068 charter-time freeze) for the hard-gate dilemma — reusing it beat inventing a new scoping scheme, and it dissolved the 'block-all vs fabricate' false choice cleanly. The d0081 dogfood is the highlight: wiring the gate hard FORCED the first new decision through the real critique pipeline, which both proved the mechanism end-to-end and produced a genuine (not theater) adversarial review of d0081 itself. CAUGHT (avoidable-issue candidates, both handled in-sprint): (1) assured-in-GUARD_NAMES recursion — anticipated at standup, fixed by excluding assured+critique from readiness invariants; (2) the new decision blocking its own commit — turned into the dogfood rather than a workaround. No new tracked Issue. Estimate 5 pts held. The assurance system is now COMPLETE and SELF-ENFORCING: grandfather old, hold every future requirement/need/decision to Core-3 critique + coverage at commit time, with the full historical gap still visible for a deliberate critique campaign."; }
    part charterTimeAssuranceGatesRetroGateR1 : TestResult { :>> id = "63940516-2c7d-4e8f-b072-51627384a90e"; :>> outcome = VerdictKind::pass; :>> judgedAgainst = "5b90663"; :>> judgedAt = "2026-06-20"; :>> judgedBy = "claudeOpus"; }
}
