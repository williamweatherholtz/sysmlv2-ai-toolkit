// ProjectDeliveryS275 — Sprint 275: dead and stale schema removed from frozen schema/core (D0142).
// The panel's non-marker findings (a)(b)(d)(f)(g); (c) and (e) deliberately excluded. EXECUTE. 4 pts.
package ProjectDeliveryS275 {
    private import EngineElement::*;
    private import EngineWork::*;
    private import EngineVerification::*;
    private import EngineRelationships::*;

    #CharteredBy dependency from leannessStory to d0142;

    part leannessStory : Story {
        :>> id = "0d8000db-0814-60db-9b3e-0000003000db";
        :>> title = "Sprint 275: 19 dead types, duplicate Release, D0100-contradicting ports, stale claims (4 pts)";
        :>> createdAt = "2026-08-14"; :>> createdBy = "claudeOpus5"; :>> kind = WorkKind::modeling; :>> priority = WorkPriority::p0; :>> owner = "claudeOpus5"; :>> estimatedPoints = 4;
    }

    action def DeliveryRunS275 {
        action storyLeanness;
        verification storyLeannessDoD : Test { :>> id = "0d8000dc-0814-60dc-9b3e-0000003000dc"; :>> method = VerificationMethod::demo; :>> procedureText = "Covers dcSchemaLeannessSweep under D0142, applying findings (a)(b)(d)(f)(g) of the three-critic panel. EACH RE-MEASURED FIRST, as the DoD required. (a) `part def Release` had ZERO declarations while `occurrence def Release` had 7, and deploy.sysml imported the empty one, threading it through four action signatures — the Deploy workflow declared an artifact type nobody produced. Deleted and retargeted. (b) NINETEEN types measured at zero declarations and deleted, applying the repo's OWN recorded policy from rules.sysml:63-66 ('removed as dead schema … re-add it THEN, with an instance'). (d) `port def InterfacePort`, its `port ifaces` member and `#View item def ICD` deleted — ACCEPTED D0100 states 'No ports/interfaces enter schema/core' and the repo contains ZERO `connect` statements, so the ICD view advertised a computation over data that never existed. (f) Stale claims inside frozen schema corrected: 8 `query.py` citations (retired at D0074) now name the `keel` commands that exist, '14 guards' becomes 28, and the EdgeKind comment now states plainly that satisfy/allocate/dependency are native while verify/supersede are markers. (g) `metadata def View` moved from workflows/_meta.sysml into relationships.sysml, so the custom vocabulary has one canonical home and an audit no longer undercounts by a marker and 73 uses. A MEASUREMENT ERROR CAUGHT MID-SPRINT: my first census reported `Agent` as having 1 usage, so I nearly kept it — the hit was the string 'console.html: Agent tab' inside a procedureText, the issue099 prose-inflation class again. Re-measured with a declaration-anchored pattern: all 19 are zero. VERIFIED: .engine and .tracking validate clean; all 28 guards pass; a fresh `keel init` project passes its OWN full gate, which is the only test that matters since a downstream project is what this schema ships to; marker-vocabulary passes with 1050 scanned after the View relocation."; }
        part storyLeannessDoDR1 : TestResult { :>> id = "0d8000dd-0814-60dd-9b3e-0000003000dd"; :>> outcome = VerdictKind::pass; :>> judgedAgainst = "5f149bd"; :>> judgedAt = "2026-08-14"; :>> judgedBy = "claudeOpus5"; }
    }

    verification lsRefineGate : Test { :>> id = "0d8000de-0814-60de-9b3e-0000003000de"; :>> title = "Sprint 275 refine gate (DoR)"; :>> createdAt = "2026-08-14"; :>> createdBy = "claudeOpus5"; :>> method = VerificationMethod::inspect; :>> procedureText = "DoR: the human gave the §2.5 frozen-schema sign-off explicitly ('let's do it!') after being told these changes are not reversible by a follow-up commit. Scoped to DELETION and correction only — the two large instance-data migrations the panel also found are excluded, because bundling a 3000-edit migration into a dead-code deletion makes the deletion unreviewable. estimatedPoints=4. DoR met."; }
    part lsRefineGateR1 : TestResult { :>> id = "0d8000df-0814-60df-9b3e-0000003000df"; :>> outcome = VerdictKind::pass; :>> judgedAgainst = "5f149bd"; :>> judgedAt = "2026-08-14"; :>> judgedBy = "claudeOpus5"; }

    verification lsStandupGate : Test { :>> id = "0d8000e0-0814-60e0-9b3e-0000003000e0"; :>> title = "Sprint 275 standup gate"; :>> createdAt = "2026-08-14"; :>> createdBy = "claudeOpus5"; :>> method = VerificationMethod::inspect; :>> procedureText = "Approach: measure every candidate before deleting anything, then check whether any dead type is still REFERENCED by surviving schema — a type with no instances can still be load-bearing. Only InterfacePort was, via `port ifaces` on Component, which finding (d) removes anyway; the rest appeared solely in `doc` prose, corrected in the same commit. No blockers."; }
    part lsStandupGateR1 : TestResult { :>> id = "0d8000e1-0814-60e1-9b3e-0000003000e1"; :>> outcome = VerdictKind::pass; :>> judgedAgainst = "5f149bd"; :>> judgedAt = "2026-08-14"; :>> judgedBy = "claudeOpus5"; }

    verification lsImplementGate : Test { :>> id = "0d8000e2-0814-60e2-9b3e-0000003000e2"; :>> title = "Sprint 275 implement gate"; :>> createdAt = "2026-08-14"; :>> createdBy = "claudeOpus5"; :>> method = VerificationMethod::test; :>> procedureText = "`Assumption` is the one genuine loss and is recorded as such rather than waved through. requirements.sysml argued it was first-class because a broken assumption should make everything derived from it suspect — a real and valuable capability, never built in the year the type existed. Deleting the type does not delete the capability; keeping an unused type does not preserve it either. The precedent the repo already recorded for `OrderingRule` says re-add it WITH its first instance and the suspicion wiring, which is the only version that would actually work."; }
    part lsImplementGateR1 : TestResult { :>> id = "0d8000e3-0814-60e3-9b3e-0000003000e3"; :>> outcome = VerdictKind::pass; :>> judgedAgainst = "5f149bd"; :>> judgedAt = "2026-08-14"; :>> judgedBy = "claudeOpus5"; }

    verification lsReviewGate : Test { :>> id = "0d8000e4-0814-60e4-9b3e-0000003000e4"; :>> title = "Sprint 275 review gate"; :>> createdAt = "2026-08-14"; :>> createdBy = "claudeOpus5"; :>> method = VerificationMethod::inspect; :>> procedureText = "Reviewed. The sweep is the repo applying its OWN policy rather than a new judgement — rules.sysml:63-66 already recorded the dead-schema rule, and 19 types had accumulated in violation of it, which says something about how a rule with no control fares. That is the same lesson D0139(B) drew for markers and D0047 states generally, arriving a third time from a different direction. What is NOT done is stated plainly in D0142's consequences: Process-as-behaviour and provenance-as-refs remain open, and issue104 (workflows absent from the Model) is untouched."; }
    part lsReviewGateR1 : TestResult { :>> id = "0d8000e5-0814-60e5-9b3e-0000003000e5"; :>> outcome = VerdictKind::pass; :>> judgedAgainst = "5f149bd"; :>> judgedAt = "2026-08-14"; :>> judgedBy = "claudeOpus5"; }

    verification lsCloseOutGate : Test { :>> id = "0d8000e6-0814-60e6-9b3e-0000003000e6"; :>> title = "Sprint 275 closeOut gate (autonomous, D0049)"; :>> createdAt = "2026-08-14"; :>> createdBy = "claudeOpus5"; :>> method = VerificationMethod::inspect; :>> procedureText = "Autonomous closeOut (D0049). dcSchemaLeannessSweep carries a passing DoD TestResult; D0142 accepted with the §2.5 sign-off recorded. dcProcessAsBehaviour and dcProvenanceAsRefs declared as the two excluded migrations, each with its own verification criteria including the control totals D0067 requires. validate + all 28 guards + check-engine green; fresh keel init project passes its own gate. No gate bypassed."; }
    part lsCloseOutGateR1 : TestResult { :>> id = "0d8000e7-0814-60e7-9b3e-0000003000e7"; :>> outcome = VerdictKind::pass; :>> judgedAgainst = "5f149bd"; :>> judgedAt = "2026-08-14"; :>> judgedBy = "claudeOpus5"; }

    verification lsRetroGate : Test { :>> id = "0d8000e8-0814-60e8-9b3e-0000003000e8"; :>> title = "Sprint 275 retro gate (autonomous, D0049)"; :>> createdAt = "2026-08-14"; :>> createdBy = "claudeOpus5"; :>> method = VerificationMethod::analyze; :>> procedureText = "Autonomous retro (D0049) under D0131's retroTrack. WELL: (1) every candidate was measured before deletion AND checked for surviving references, which is what caught that InterfacePort was still structurally referenced; (2) the sweep was scoped to deletion and correction, keeping two large instance-data migrations out of a change the human is about to review — a reviewable diff was worth more than a complete one; (3) `Assumption` was recorded as a genuine loss with the re-add path named, rather than deleted silently among eighteen others. AVOIDABLE-ISSUE 1: my first census reported `Agent` at 1 usage and I nearly kept a dead type on that basis. The hit was 'console.html: Agent tab' inside a procedureText — the issue099 prose-inflation class, in the very sprint after building `keel marker-census` to prevent exactly this. NO NEW ITEM, reason stated: issue099 already tracks the class and dcMarkerCensusView delivered the control FOR MARKERS; what this shows is that the control's scope is too narrow — the same prose-inflation applies to any type-usage count, and the census only covers markers. Recorded here as the reason to widen it when a type census is next needed, rather than widening it speculatively now. AVOIDABLE-ISSUE 2: my scripted remover missed `Agent` because I assumed it lived in element.sysml and it is in skills.sysml. The script REPORTED the miss, so nothing was lost. NO NEW ITEM: the script reporting its own failure is the behaviour wanted, and the lesson is the same one as sprint 272's — assuming a file's contents is a measurement. Estimate 4 pts, delivered."; }
    part lsRetroGateR1 : TestResult { :>> id = "0d8000e9-0814-60e9-9b3e-0000003000e9"; :>> outcome = VerdictKind::pass; :>> judgedAgainst = "5f149bd"; :>> judgedAt = "2026-08-14"; :>> judgedBy = "claudeOpus5"; }
}
