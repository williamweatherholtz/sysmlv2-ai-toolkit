// ProjectDeliveryS688 — Sprint 688: A retro that names a Decision the way every document in this repository names one - D0388 - is read by the retro-backlog guard as naming it. Resolves issue424: the guard's named_items read d0388 and not D0388, so sprint 627's justification 'already tracked by D0388 and its probe rule' was refused as naming no item at all, and this session's sprint 687 retro, naming D0131 and D0337, was refused the same way one commit ago. Delivers dcRetroNamesDecisionsAsWritten under D0461 (co-committed #ProspectiveChange, held proposed). EXECUTE.. EXECUTE. 2 pts.
package ProjectDeliveryS688 {
    private import EngineElement::*;
    private import EngineWork::*;
    private import EngineVerification::*;
    private import EngineRelationships::*;

    #CharteredBy dependency from retroNamesDecisionsAsWrittenStory to d0461;

    part retroNamesDecisionsAsWrittenStory : Story {
        :>> id = "8ef2c23b-4cf6-454c-9ba6-e73d60c283b5";
        :>> title = "Sprint 688: A retro that names a Decision the way every document in this repository names one - D0388 - is read by the retro-backlog guard as naming it. Resolves issue424: the guard's named_items read d0388 and not D0388, so sprint 627's justification 'already tracked by D0388 and its probe rule' was refused as naming no item at all, and this session's sprint 687 retro, naming D0131 and D0337, was refused the same way one commit ago. Delivers dcRetroNamesDecisionsAsWritten under D0461 (co-committed #ProspectiveChange, held proposed). EXECUTE. (2 pts)";
        :>> createdAt = "2026-09-13"; :>> createdBy = "claudeFable5"; :>> kind = WorkKind::code; :>> priority = WorkPriority::p0; :>> owner = "claudeFable5"; :>> estimatedPoints = 2;
    }

    action def DeliveryRunS688 {
        action storyRetroNamesDecisionsAsWritten;
        verification storyRetroNamesDecisionsAsWrittenDoD : Test { :>> id = "fa97697b-ff8b-43ed-a04f-c5c99cf6c2f8"; :>> method = VerificationMethod::test; :>> procedureText = "DELIVERED: guards.rs named_items matches a fourth needle - D0 followed by a digit at a word boundary - and returns the match with its first letter lowered, so the exists check hits the tree by the item's real name; only the Decision form folds (Issue and DC in prose stay words, ID0388 is no boundary); the refusal text quotes the forms it accepts in the case it accepts them: `issueNNN`, `dcTaskName`, `d0NNN` (or `D0NNN`). Tests: a_decision_named_in_uppercase_is_read_as_its_real_name (D0388 -> d0388; d0388 and D0388 both read; Issue 42 / DC / ID0388 unmatched; issue424 (D0131) -> both) and a_retro_justified_by_an_uppercase_decision_passes_when_it_exists_and_fails_when_it_does_not (the sprint 627 retro constructed both ways: passes with d0388 known, one violation naming d0388 and 'none of which exists' with d0387 known, the refusal quoting the three accepted forms); the five existing retro-backlog tests unchanged and passing (guards module 102 passed). D0461 recorded with marker process-change and #DependsOn to d0131; guards.md retro-backlog row names the accepted forms. Resolves issue424 through the #Resolves edge already on the Issue."; }
        // RAN: RAN: cargo test --release --lib -- guards -> 102 passed; the D0388 pair test constructs the sprint 627 retro both ways; refusal text quotes issueNNN, dcTaskName, d0NNN (or D0NNN)
        part storyRetroNamesDecisionsAsWrittenDoDR1 : TestResult { :>> id = "7844f4ea-b4a8-4742-b944-595736f31970"; :>> outcome = VerdictKind::pass; :>> judgedAgainst = "c08b6a5"; :>> judgedAt = "2026-09-13"; :>> judgedBy = "claudeFable5"; }
    }

    verification retroNamesDecisionsAsWrittenRefineGate : Test { :>> id = "57b76963-5c92-4f98-9280-3d1f83e79cb4"; :>> title = "Sprint 688 refine gate (DoR)"; :>> createdAt = "2026-09-13"; :>> createdBy = "claudeFable5"; :>> method = VerificationMethod::inspect; :>> procedureText = "Chartered by D0461 (recorded this sprint as the #ProspectiveChange the guard-source change rides, D0209 clause 2). One point: one needle and one case fold, two tests, one Decision, one doc row. DoR: the DoD is on the backlog item (dcRetroNamesDecisionsAsWrittenDoD, method test); issue424 carries #Resolves from this task; no blocker. NOT A FORK: issue424's DO clause names the change (match the Decision form case-insensitively, normalise to the real name) and forbids the alternative (lowercasing the whole retro). The process-change marker sits on D0461, not here: this sprint's ceremony is the standard delivery loop."; }
    // RAN: sprint 688 Refine: examined per the gate text; DoR/plan/three-pass review/close-out/retro read against the working tree
    part retroNamesDecisionsAsWrittenRefineGateR1 : TestResult { :>> id = "a281fa40-2066-481d-89e0-f44a7ae9dbad"; :>> outcome = VerdictKind::proposed; :>> judgedAgainst = "c08b6a5"; :>> judgedAt = "2026-09-13"; :>> judgedBy = "claudeFable5"; }
    verification retroNamesDecisionsAsWrittenStandupGate : Test { :>> id = "337648b0-a98c-4832-abe9-c90a1c4a4eef"; :>> title = "Sprint 688 standup gate"; :>> createdAt = "2026-09-13"; :>> createdBy = "claudeFable5"; :>> method = VerificationMethod::inspect; :>> procedureText = "Order: patch named_items and the refusal text, add the two tests beside the existing retro_tie_tests; clippy; run the guards module; record D0461 from a draft file with the marker and the edge; doc-sync guards.md; rebuild and copy to keel-serve.exe; record the sprint, gates and the DoD result with the test receipt; validate, check-engine, guard --no-receipt, sync-claude --check on the index; commit detached; read git status -sb and the CI conclusion."; }
    // RAN: sprint 688 Standup: examined per the gate text; DoR/plan/three-pass review/close-out/retro read against the working tree
    part retroNamesDecisionsAsWrittenStandupGateR1 : TestResult { :>> id = "d72e4127-9c34-42f2-8b1c-ef36233bde0c"; :>> outcome = VerdictKind::proposed; :>> judgedAgainst = "c08b6a5"; :>> judgedAt = "2026-09-13"; :>> judgedBy = "claudeFable5"; }
    verification retroNamesDecisionsAsWrittenImplementGate : Test { :>> id = "73d49310-7f3d-4338-b0b7-cc76d447adfe"; :>> title = "Sprint 688 implement gate"; :>> createdAt = "2026-09-13"; :>> createdBy = "claudeFable5"; :>> method = VerificationMethod::test; :>> procedureText = "guards.rs: pairs grows from three to four needles with ('D0', digit); a D0 match has its first char replaced by d before it is pushed; the comment names issue424 and why only the Decision form folds. The 'already tracked' refusal text becomes: a justification must point at something real, written as the tree names it: `issueNNN`, `dcTaskName`, `d0NNN` (or `D0NNN`) - the item that carries it (D0131/D0293/issue424). Two tests appended to retro_tie_tests. RAN: cargo clippy --release --lib -> Finished, no warnings; cargo test --release --lib -- guards -> 102 passed 0 failed, the two new tests listed ok. D0461 recorded (proposed, OUTSIDE standing consent per D0337) with #ProspectiveChange marker and #DependsOn to d0131 authored by textpatch. guards.md row 111 rewritten. cargo build --release -> Finished; keel-serve.exe version reads build commit c08b6a5+dirty."; }
    // RAN: RAN: cargo test --release --lib -- guards -> 102 passed 0 failed incl. a_decision_named_in_uppercase_is_read_as_its_real_name and a_retro_justified_by_an_uppercase_decision_passes_when_it_exists_and_fails_when_it_does_not; cargo clippy --release --lib -> Finished, no warnings
    part retroNamesDecisionsAsWrittenImplementGateR1 : TestResult { :>> id = "0aa95f5d-6e63-403b-8aae-0f483f26fd4c"; :>> outcome = VerdictKind::pass; :>> judgedAgainst = "c08b6a5"; :>> judgedAt = "2026-09-13"; :>> judgedBy = "claudeFable5"; }
    verification retroNamesDecisionsAsWrittenReviewGate : Test { :>> id = "fb49f0a5-b26c-4563-ac54-4c5166c639de"; :>> title = "Sprint 688 review gate — three passes per D0172"; :>> createdAt = "2026-09-13"; :>> createdBy = "claudeFable5"; :>> method = VerificationMethod::inspect; :>> procedureText = "Three passes (D0172). Correctness: the fold touches one character of a match that began with the D0 needle and nothing else; the boundary closure is unchanged, so ID0388 and CLAUDE stay unmatched, shown by the lookalike assertions; the sprint 627 case is constructed positive and negative in one test, the D0388 pair. Honesty: the guard still judges form, not relevance - D0461's consequences say so, and the test doc carries the same words as the existing a_justification_that_names_a_real_item test; the DoD result is method test with the cargo receipt, so it lands pass, not proposed. Scope: guard source, its tests, its doc row, its Decision - nothing else in guards.rs moved; no schema, hook or process file touched."; }
    // RAN: sprint 688 Review: examined per the gate text; DoR/plan/three-pass review/close-out/retro read against the working tree
    part retroNamesDecisionsAsWrittenReviewGateR1 : TestResult { :>> id = "a3fffeac-66c2-4a6f-93c0-6f461248a99e"; :>> outcome = VerdictKind::proposed; :>> judgedAgainst = "c08b6a5"; :>> judgedAt = "2026-09-13"; :>> judgedBy = "claudeFable5"; }
    verification retroNamesDecisionsAsWrittenCloseOutGate : Test { :>> id = "b0713eb9-2c8c-43a9-ae32-42efd3b78cf2"; :>> title = "Sprint 688 closeOut gate (autonomous, D0049)"; :>> createdAt = "2026-09-13"; :>> createdBy = "claudeFable5"; :>> method = VerificationMethod::inspect; :>> procedureText = "Closes on the guards test module passing (102), clippy clean, gate validate, gate check-engine, gate guard --no-receipt and sync-claude --check over the index holding guards.rs, guards.md, D0461, this sprint and the DoD result; on the rebuilt binary's guard run over this very sprint file, whose retro names D0461 and issue424 in the documented case and is read as naming them."; }
    // RAN: sprint 688 CloseOut: examined per the gate text; DoR/plan/three-pass review/close-out/retro read against the working tree
    part retroNamesDecisionsAsWrittenCloseOutGateR1 : TestResult { :>> id = "596552b3-ecda-4349-b836-627726971a6c"; :>> outcome = VerdictKind::proposed; :>> judgedAgainst = "c08b6a5"; :>> judgedAt = "2026-09-13"; :>> judgedBy = "claudeFable5"; }
    verification retroNamesDecisionsAsWrittenRetroGate : Test { :>> id = "ad525020-1393-468f-ac59-5544c8350eac"; :>> title = "Sprint 688 retro gate (autonomous, D0049)"; :>> createdAt = "2026-09-13"; :>> createdBy = "claudeFable5"; :>> method = VerificationMethod::analyze; :>> procedureText = "AVOIDABLE-ISSUE SCAN, no new item (D0131): the finding this sprint fixes is issue424, already tracked and resolved here by dcRetroNamesDecisionsAsWritten; nothing new surfaced. ROOT-FIXED IN PASSING: sprint 687's retro was refused by this exact defect one commit ago (it named D0131 and D0337 and the guard read nothing) and was rephrased to name a dc-task instead - with this fix the original wording would have passed, which is the live confirmation issue424 predicted. STATED: this retro itself is the first run of the new reading - it names D0461 and issue424 in the case the documents use, and the guard on the index must read them; if it does not, the commit is refused and this sentence is wrong."; }
    // RAN: sprint 688 Retro: examined per the gate text; DoR/plan/three-pass review/close-out/retro read against the working tree
    part retroNamesDecisionsAsWrittenRetroGateR1 : TestResult { :>> id = "b4ebf440-7d91-4c0c-8229-8b1ca58b161a"; :>> outcome = VerdictKind::proposed; :>> judgedAgainst = "c08b6a5"; :>> judgedAt = "2026-09-13"; :>> judgedBy = "claudeFable5"; }
}
