// ProjectDeliveryS258 — Sprint 258: the in-loop hooks move into the keel binary; python leaves the
// governance path (D0134). Raised by the human challenging the dependency. EXECUTE. 2 pts.
package ProjectDeliveryS258 {
    private import EngineElement::*;
    private import EngineWork::*;
    private import EngineVerification::*;
    private import EngineRelationships::*;

    #CharteredBy dependency from hooksInBinaryStory to d0134;

    part hooksInBinaryStory : Story {
        :>> id = "0d720001-0814-5201-9b3e-000000220001";
        :>> title = "Sprint 258: keel hook <user-prompt|post-edit|stop>; delete the four python wrappers (2 pts)";
        :>> createdAt = "2026-08-14"; :>> createdBy = "claudeOpus5"; :>> kind = WorkKind::code; :>> priority = WorkPriority::p0; :>> owner = "claudeOpus5"; :>> estimatedPoints = 2;
    }

    action def DeliveryRunS258 {
        action storyHooksInBinary;
        verification storyHooksInBinaryDoD : Test { :>> id = "0d720002-0814-5202-9b3e-000000220002"; :>> method = VerificationMethod::demo; :>> procedureText = "Delivers D0134. The human challenged the dependency: 'why are we using python to make code? i thought we were rust on the backend... is this dependency defensible?' It was not. All four governance hooks were python wrappers; the CHECKING was always Rust, so python bought pure stdin/stdout glue while costing a SECOND RUNTIME on every contributor's machine — whose absence means the gate silently does not run (issue076; issue081's eight bypassed commits), with five mixed-OS machines in scope under D0129, and it was about to ship in a release. DELIVERED: `keel hook <user-prompt|post-edit|stop>` in the binary; all four wrappers DELETED (no tombstones); settings.json rewired to probe PATH -> target/release -> target/debug exactly as the portable git hook does. Dependency count goes DOWN by one with nothing added, since `keel` was already mandatory for these gates to mean anything and serde_json was already a dependency. VERIFY: all six paths pipe-tested — post-edit (non-.sysml silent, clean silent, broken parse blocks, marker typo blocks), stop (red blocks, second consecutive red releases with a loud warning so the agent is never trapped); user-prompt emits the route-first checklist plus the out-of-band-writes warning with 0 non-ASCII bytes confirmed by byte count (a non-UTF-8 Windows console would otherwise inject mojibake) and stays silent on a clean tree. Zero python references remain in any hook. clippy clean; validate + all 23 guards + check-engine green at 425145d."; }
        part storyHooksInBinaryDoDR1 : TestResult { :>> id = "0d720003-0814-5203-9b3e-000000220003"; :>> outcome = VerdictKind::pass; :>> judgedAgainst = "425145d"; :>> judgedAt = "2026-08-14"; :>> judgedBy = "claudeOpus5"; }
    }

    verification hbRefineGate : Test { :>> id = "0d720004-0814-5204-9b3e-000000220004"; :>> title = "Sprint 258 refine gate (DoR)"; :>> createdAt = "2026-08-14"; :>> createdBy = "claudeOpus5"; :>> method = VerificationMethod::inspect; :>> procedureText = "DoR: human-raised defect, taken immediately rather than queued, because it would otherwise ship in the imminent release and it contradicts a fix landed only sprints earlier. Scope: the ENFORCEMENT hooks only. EXCLUDED with reason: the kernel validators and utilities stay python — they drive a JVM/Jupyter kernel already being retired (D0112), they are opt-in rather than gating (D0132), and porting them means reimplementing a SysML oracle rather than deleting glue. estimatedPoints=2. DoR met."; }
    part hbRefineGateR1 : TestResult { :>> id = "0d720005-0814-5205-9b3e-000000220005"; :>> outcome = VerdictKind::pass; :>> judgedAgainst = "425145d"; :>> judgedAt = "2026-08-14"; :>> judgedBy = "claudeOpus5"; }

    verification hbStandupGate : Test { :>> id = "0d720006-0814-5206-9b3e-000000220006"; :>> title = "Sprint 258 standup gate"; :>> createdAt = "2026-08-14"; :>> createdBy = "claudeOpus5"; :>> method = VerificationMethod::inspect; :>> procedureText = "Approach: port behaviour EXACTLY rather than improving it in the same step, so any post-migration difference is a bug and not a design change; keep the ASCII-only constraint the python version documented; and pipe-test every path before deleting the wrappers, since deleting first would leave no comparison. No blockers."; }
    part hbStandupGateR1 : TestResult { :>> id = "0d720007-0814-5207-9b3e-000000220007"; :>> outcome = VerdictKind::pass; :>> judgedAgainst = "425145d"; :>> judgedAt = "2026-08-14"; :>> judgedBy = "claudeOpus5"; }

    verification hbImplementGate : Test { :>> id = "0d720008-0814-5208-9b3e-000000220008"; :>> title = "Sprint 258 implement gate"; :>> createdAt = "2026-08-14"; :>> createdBy = "claudeOpus5"; :>> method = VerificationMethod::demo; :>> procedureText = "Implemented at 425145d. The ASCII constraint was verified by counting non-ASCII BYTES in the hook's actual stdout (0), not by reading the source — the python version's own docstring warned about mojibake and that warning is only useful if checked. The probe command was executed as bash with the real payload, so the settings.json string is proven rather than assumed correct."; }
    part hbImplementGateR1 : TestResult { :>> id = "0d720009-0814-5209-9b3e-000000220009"; :>> outcome = VerdictKind::pass; :>> judgedAgainst = "425145d"; :>> judgedAt = "2026-08-14"; :>> judgedBy = "claudeOpus5"; }

    verification hbReviewGate : Test { :>> id = "0d72000a-0814-520a-9b3e-00000022000a"; :>> title = "Sprint 258 review gate"; :>> createdAt = "2026-08-14"; :>> createdBy = "claudeOpus5"; :>> method = VerificationMethod::inspect; :>> procedureText = "Reviewed. The human's challenge was correct and my own reasoning had missed it twice: I added edit_gate.py in python IMMEDIATELY after spending a sprint fixing the identical class (a gate that silently fails where its runtime is absent, issue076). The generalisable lesson is that a fix applied to one instance does not transfer to the next instance by itself — I had the principle and still reached for python because it was the local convention. Also correct: the scope line between ENFORCEMENT (must not depend on an optional runtime) and TOOLING (may) is stated in D0134 rather than left implicit, so the remaining python is defended rather than merely tolerated."; }
    part hbReviewGateR1 : TestResult { :>> id = "0d72000b-0814-520b-9b3e-00000022000b"; :>> outcome = VerdictKind::pass; :>> judgedAgainst = "425145d"; :>> judgedAt = "2026-08-14"; :>> judgedBy = "claudeOpus5"; }

    verification hbCloseOutGate : Test { :>> id = "0d72000c-0814-520c-9b3e-00000022000c"; :>> title = "Sprint 258 closeOut gate (autonomous, D0049)"; :>> createdAt = "2026-08-14"; :>> createdBy = "claudeOpus5"; :>> method = VerificationMethod::inspect; :>> procedureText = "Autonomous closeOut (D0049). D0134 accepted on the human's direction; four wrappers deleted; zero python in any hook. validate + all 23 guards + check-engine green; clippy clean. The governance layer now requires only the keel binary, which the gates already required."; }
    part hbCloseOutGateR1 : TestResult { :>> id = "0d72000d-0814-520d-9b3e-00000022000d"; :>> outcome = VerdictKind::pass; :>> judgedAgainst = "425145d"; :>> judgedAt = "2026-08-14"; :>> judgedBy = "claudeOpus5"; }

    verification hbRetroGate : Test { :>> id = "0d72000e-0814-520e-9b3e-00000022000e"; :>> title = "Sprint 258 retro gate (autonomous, D0049)"; :>> createdAt = "2026-08-14"; :>> createdBy = "claudeOpus5"; :>> method = VerificationMethod::analyze; :>> procedureText = "Autonomous retro (D0049) under D0131's retroTrack. WELL: (1) the challenge was accepted on its merits and fixed in place rather than deferred to the backlog, because the alternative was shipping it in a release; (2) behaviour was ported exactly and every path re-tested before the wrappers were deleted; (3) the ENFORCEMENT-vs-TOOLING scope line is now recorded, so the remaining python is a defended position rather than an unexamined leftover. AVOIDABLE-ISSUE 1 (the substantive one): I introduced edit_gate.py in python immediately AFTER a sprint fixing the identical failure class — a gate that silently fails where its runtime is missing. Having the principle did not stop me reaching for the local convention. NO NEW ITEM: D0134 now records the rule for the governance path and the human caught this instance; a control for 'the AI reached for a convention that contradicts an accepted decision' is what D0130's in-loop tiering and the self-detecting-discipline requirement (srGovSelfDetectingDiscipline) already exist to pursue, and inventing a narrower guard here would be a guess. Recorded as the clearest example yet of why srGovSelfDetectingDiscipline matters. AVOIDABLE-ISSUE 2: two shell-based patches silently failed to match because of an em-dash, and I only noticed by grepping the result; switched to the Edit tool. NO NEW ITEM — same read-back principle, now at four recorded instances. Estimate 2 pts, delivered."; }
    part hbRetroGateR1 : TestResult { :>> id = "0d72000f-0814-520f-9b3e-00000022000f"; :>> outcome = VerdictKind::pass; :>> judgedAgainst = "425145d"; :>> judgedAt = "2026-08-14"; :>> judgedBy = "claudeOpus5"; }
}
