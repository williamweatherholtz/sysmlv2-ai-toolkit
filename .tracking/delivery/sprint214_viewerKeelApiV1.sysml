// ProjectDeliveryS214 — Sprint 214: viewerKeelApiV1 — FIRST build increment for the keel-viewer (shape B):
// version the keel serve read API (KEEL_API_VERSION 1.0.0 + GET /api/version + the committed read-endpoint
// contract) — the enabling foundation a separate viewer app pins to. Also finishes the D0115 scope
// cleanup (supersede the 3 use cases of superseded Needs: UC-7/UC-9/UC-12). EXECUTE. 2 pt. AUTONOMOUS (D0049).
package ProjectDeliveryS214 {
    private import EngineElement::*;
    private import EngineWork::*;
    private import EngineVerification::*;
    private import EngineRequirements::*;
    private import EngineRelationships::*;

    #CharteredBy dependency from viewerKeelApiV1Story to d0114;

    part viewerKeelApiV1Story : Story {
        :>> id = "63940516-2c7d-4e8f-c214-51627384c001";
        :>> title = "Sprint 214: viewerKeelApiV1 (2 pt) - version the serve read API (viewerKeelApi increment 1) + supersede UC-7/9/12";
        :>> createdAt = "2026-07-14"; :>> createdBy = "wweatherholtz"; :>> kind = WorkKind::code; :>> priority = WorkPriority::p2; :>> owner = "claudeOpus"; :>> estimatedPoints = 2;
    }

    action def DeliveryRunS214 {
        action storyViewerKeelApiV1;
        verification storyViewerKeelApiV1DoD : Test { :>> id = "63940516-2c7d-4e8f-c214-51627384c002"; :>> method = VerificationMethod::test; :>> procedureText = "FIRST build increment of viewerKeelApi (N-6 / D0114 shape B): make the keel serve read API a COMMITTED, VERSIONED contract a separate viewer pins to. (1) serve.rs: KEEL_API_VERSION = 1.0.0 (SemVer; breaking read-contract change bumps major) + KEEL_API_READ_ENDPOINTS (the 15 committed read endpoints) + GET /api/version returning {apiVersion, readEndpoints}; startup banner prints the API version. (2) D0047 unit test api_version_contract_is_self_consistent (SemVer-shaped; the contract advertises itself + orient + item-detail). (3) CLEANUP (finishing D0115): #Supersede UC-7 (ucCoverageGapDashboard — obsolete, intent now in UC-15), UC-9 (ucFreshnessNotifications — deferred w/ N-11), UC-12 (ucAuditProvenance — deferred w/ N-14). SCOPE HONESTY: this is INCREMENT 1 — the versioning foundation; the full viewerKeelApi (documented per-endpoint contracts + the temporal/seed-expand endpoints from N-2/N-3) is later increments, so the viewerKeelApi backlog action stays OPEN. VERIFIED LIVE: GET /api/version -> apiVersion 1.0.0 + 15 endpoints. VERIFY: clippy --workspace --all-targets clean; cargo test (84) green incl. the new test; keel validate + guard + check-engine green."; }
        part storyViewerKeelApiV1DoDR1 : TestResult { :>> id = "63940516-2c7d-4e8f-c214-51627384c003"; :>> outcome = VerdictKind::pass; :>> judgedAgainst = "3593689"; :>> judgedAt = "2026-07-14"; :>> judgedBy = "claudeOpus"; }
    }

    verification vk1RefineGate : Test { :>> id = "63940516-2c7d-4e8f-c214-51627384c004"; :>> title = "Sprint 214 refine gate (DoR)"; :>> createdAt = "2026-07-14"; :>> createdBy = "claudeOpus"; :>> method = VerificationMethod::inspect; :>> procedureText = "DoR: human said proceed-as-suggested (build viewerKeelApi first) + supersede the stale use cases. First increment = API versioning (the enabler); + UC cleanup. estimatedPoints=2. #CharteredBy d0114. DoR met."; }
    part vk1RefineGateR1 : TestResult { :>> id = "63940516-2c7d-4e8f-c214-51627384c005"; :>> outcome = VerdictKind::pass; :>> judgedAgainst = "3593689"; :>> judgedAt = "2026-07-14"; :>> judgedBy = "claudeOpus"; }
    verification vk1StandupGate : Test { :>> id = "63940516-2c7d-4e8f-c214-51627384c006"; :>> title = "Sprint 214 standup gate"; :>> createdAt = "2026-07-14"; :>> createdBy = "claudeOpus"; :>> method = VerificationMethod::inspect; :>> procedureText = "Approach: KEEL_API_VERSION + endpoints const + /api/version handler + route + banner; unit test; #Supersede the 3 use cases. No blockers."; }
    part vk1StandupGateR1 : TestResult { :>> id = "63940516-2c7d-4e8f-c214-51627384c007"; :>> outcome = VerdictKind::pass; :>> judgedAgainst = "3593689"; :>> judgedAt = "2026-07-14"; :>> judgedBy = "claudeOpus"; }
    verification vk1ImplementGate : Test { :>> id = "63940516-2c7d-4e8f-c214-51627384c008"; :>> title = "Sprint 214 implement gate"; :>> createdAt = "2026-07-14"; :>> createdBy = "claudeOpus"; :>> method = VerificationMethod::test; :>> procedureText = "/api/version live (1.0.0, 15 endpoints); unit test green; UC-7/9/12 superseded. clippy --workspace --all-targets clean; cargo test (84) green; keel validate + guard + check-engine green."; }
    part vk1ImplementGateR1 : TestResult { :>> id = "63940516-2c7d-4e8f-c214-51627384c009"; :>> outcome = VerdictKind::pass; :>> judgedAgainst = "3593689"; :>> judgedAt = "2026-07-14"; :>> judgedBy = "claudeOpus"; }
    verification vk1ReviewGate : Test { :>> id = "63940516-2c7d-4e8f-c214-51627384c00a"; :>> title = "Sprint 214 review gate"; :>> createdAt = "2026-07-14"; :>> createdBy = "claudeOpus"; :>> method = VerificationMethod::inspect; :>> procedureText = "Reviewed. The FIRST real code toward the viewer landed the right foundation: shape B's whole premise is 'a separate app over a committed, versioned keel API' — so versioning the read surface (a self-describing /api/version contract) is the correct first brick, small and honest (explicitly increment 1; the full contract is later). The scope cleanup (superseding the 3 stale use cases) keeps the model truthful post-revision. Clean."; }
    part vk1ReviewGateR1 : TestResult { :>> id = "63940516-2c7d-4e8f-c214-51627384c00b"; :>> outcome = VerdictKind::pass; :>> judgedAgainst = "3593689"; :>> judgedAt = "2026-07-14"; :>> judgedBy = "claudeOpus"; }
    verification vk1CloseOutGate : Test { :>> id = "63940516-2c7d-4e8f-c214-51627384c00c"; :>> title = "Sprint 214 closeOut gate (autonomous, D0049)"; :>> createdAt = "2026-07-14"; :>> createdBy = "claudeOpus"; :>> method = VerificationMethod::inspect; :>> procedureText = "Autonomous closeOut (D0049): DoD pass; the keel read API is now versioned (v1.0.0, self-describing) — viewerKeelApi increment 1 — and the D0115 scope cleanup is complete. clippy + cargo test + keel validate + guard + check-engine green. Self-evidencing (D0051). viewerKeelApi stays OPEN (increments remain). NEXT: viewerKeelApi increment 2 (per-endpoint contracts + the N-2/N-3 expand/temporal endpoints) then viewerIterativeCritique (N-15)."; }
    part vk1CloseOutGateR1 : TestResult { :>> id = "63940516-2c7d-4e8f-c214-51627384c00d"; :>> outcome = VerdictKind::pass; :>> judgedAgainst = "3593689"; :>> judgedAt = "2026-07-14"; :>> judgedBy = "claudeOpus"; }
    verification vk1RetroGate : Test { :>> id = "63940516-2c7d-4e8f-c214-51627384c00e"; :>> title = "Sprint 214 retro gate (autonomous, D0049)"; :>> createdAt = "2026-07-14"; :>> createdBy = "claudeOpus"; :>> method = VerificationMethod::analyze; :>> procedureText = "Autonomous retro (D0049). WELL: the design->build transition started with the architecturally-correct first brick (a versioned, self-describing API contract — the literal premise of shape B), delivered small + tested + live-verified, and honestly labelled increment 1 rather than over-claiming the whole viewerKeelApi. Ran the AUTHORITATIVE clippy first (the a642269 lesson, now habitual). Also closed the model-cleanup loop (stale use cases superseded). AVOIDABLE-ISSUE SCAN: two doc-lint nits on the new const, caught by clippy pre-commit — cheap. LESSON: build the enabler (the API contract) before the features that consume it. Estimate 2 pt held. NEXT: increment 2 (endpoint contracts + expand/temporal) -> viewerIterativeCritique."; }
    part vk1RetroGateR1 : TestResult { :>> id = "63940516-2c7d-4e8f-c214-51627384c00f"; :>> outcome = VerdictKind::pass; :>> judgedAgainst = "3593689"; :>> judgedAt = "2026-07-14"; :>> judgedBy = "claudeOpus"; }
}
