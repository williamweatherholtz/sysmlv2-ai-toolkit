// ProjectDeliveryS445 — Sprint 445: proactive post-edit guidance - the hook names what an edit broke downstream, non-blocking (D0209 clause 4). EXECUTE. 2 pts.
package ProjectDeliveryS445 {
    private import EngineElement::*;
    private import EngineWork::*;
    private import EngineVerification::*;
    private import EngineRelationships::*;

    #CharteredBy dependency from proactivePostEditStory to d0209;

    part proactivePostEditStory : Story {
        :>> id = "53c69dc3-374d-4fef-b2e0-e523f723fe88";
        :>> title = "Sprint 445: that change just broke X - caught at the edit, not at commit (2 pts)";
        :>> createdAt = "2026-08-24"; :>> createdBy = "claudeFable5"; :>> kind = WorkKind::code; :>> priority = WorkPriority::p0; :>> owner = "claudeFable5"; :>> estimatedPoints = 2;
    }

    action def DeliveryRunS445 {
        action storyProactivePostEdit;
        verification storyProactivePostEditDoD : Test { :>> id = "94c2bac9-d9eb-41ba-80ef-cc60c38a3c4e"; :>> method = VerificationMethod::test; :>> procedureText = "DELIVERED: dcProactivePostEdit (D0209 clause 4, the manager-inversion panel's final increment). When the post-edit fast tier is CLEAN (the model still parses), keel hook post-edit now adds a NON-BLOCKING advisory naming what the edit broke downstream: (a) a typed edge whose endpoint no longer resolves - the committed tree carries ZERO dangling endpoints (edge-endpoints is a hard commit gate), so any dangling endpoint now is attributable to the working edit; (b) a verification criterion the edit CHANGED versus its HEAD blob while its passing TestResult still stands - the pass is now stale. It is advisory only (systemMessage, never a block): the fast tier already blocks a malformed model and D0098 keeps completeness off the commit path; this surfaces the break at the point of the edit rather than at commit. New module proactive.rs (pure core criterion_drift_core + verification_blocks + has_passing_result, all unit-tested); wired into hook_post_edit; not on the enforcement surface, so no marked decision needed and D0209 charters it. VERIFIED end-to-end with the freshly-built binary: editing sprint444's criterion emitted 'criterion drift - storyProcessCursorDoD changed but its verify result still says pass'; reverting silenced it; a temp file with a #Resolves edge to two nonexistent targets emitted both broken-edge lines naming ghostResolverThatDoesNotExist and alsoMissingIssue - all exit 0 (non-blocking), the fast tier (validate 496 clean) staying clean throughout. Six lib unit tests; workspace clippy --all-targets clean."; }
        part storyProactivePostEditDoDR1 : TestResult { :>> id = "c0fd5ed9-59d6-4b75-ac49-9ab3f9bd443a"; :>> outcome = VerdictKind::pass; :>> judgedAgainst = "ea77d8a76f7d747b081861eb62f3d3930c78cf9d"; :>> judgedAt = "2026-08-24"; :>> judgedBy = "claudeFable5"; }
    }

    verification proactivePostEditRefineGate : Test { :>> id = "e3e5e5c6-34d6-4f58-bd7d-ac417643b274"; :>> title = "Sprint 445 refine gate (DoR)"; :>> createdAt = "2026-08-24"; :>> createdBy = "claudeFable5"; :>> method = VerificationMethod::inspect; :>> procedureText = "DoR. Delivers D0209 clause 4, the last panel increment. Scope: a non-blocking proactive layer in the post-edit hook that names downstream breakage (dangling edge / criterion drift) at edit time; advisory only. 2 points."; }
    part proactivePostEditRefineGateR1 : TestResult { :>> id = "2df559b3-47a8-4a22-bbb4-4a73849b579d"; :>> outcome = VerdictKind::pass; :>> judgedAgainst = "ea77d8a76f7d747b081861eb62f3d3930c78cf9d"; :>> judgedAt = "2026-08-24"; :>> judgedBy = "claudeFable5"; }
    verification proactivePostEditStandupGate : Test { :>> id = "d17c797e-0697-4059-aa99-87d466a81a09"; :>> title = "Sprint 445 standup gate"; :>> createdAt = "2026-08-24"; :>> createdBy = "claudeFable5"; :>> method = VerificationMethod::inspect; :>> procedureText = "Approach: reuse view::dangling_edge_endpoints (committed tree is zero by the hard commit gate, so any dangling now = the edit) for broken edges, and a HEAD-blob-vs-working diff of verification bodies for criterion drift (git-ancestry suspect cannot see an uncommitted criterion edit, so a blob diff is the honest edit-time signal). Pure core in proactive.rs, unit-tested; emit via systemMessage (never a block). No blockers."; }
    part proactivePostEditStandupGateR1 : TestResult { :>> id = "a907e87a-4b1f-48a0-93d6-7f5d3b8b5039"; :>> outcome = VerdictKind::pass; :>> judgedAgainst = "ea77d8a76f7d747b081861eb62f3d3930c78cf9d"; :>> judgedAt = "2026-08-24"; :>> judgedBy = "claudeFable5"; }
    verification proactivePostEditImplementGate : Test { :>> id = "d7b75556-4a0d-47b5-873e-3c46acb9c2bd"; :>> title = "Sprint 445 implement gate"; :>> createdAt = "2026-08-24"; :>> createdBy = "claudeFable5"; :>> method = VerificationMethod::test; :>> procedureText = "Verified by running the freshly-built binary end-to-end: sprint444 criterion edit -> drift advisory (exit 0); revert -> silent (exit 0); temp #Resolves edge to two missing targets -> two broken-edge lines naming them (exit 0); validate stays clean (496) so the proactive layer is reached. cargo test --lib proactive -> 6 passed; cargo clippy --workspace --all-targets -D warnings clean (fixed a too_long_first_doc_paragraph nursery lint)."; }
    part proactivePostEditImplementGateR1 : TestResult { :>> id = "9c8c4ed9-7b33-4fa3-8877-0d8366a15e6a"; :>> outcome = VerdictKind::pass; :>> judgedAgainst = "ea77d8a76f7d747b081861eb62f3d3930c78cf9d"; :>> judgedAt = "2026-08-24"; :>> judgedBy = "claudeFable5"; }
    verification proactivePostEditReviewGate : Test { :>> id = "268d613f-a30b-4e69-8463-7f5a6e75b46d"; :>> title = "Sprint 445 review gate — three passes per D0172"; :>> createdAt = "2026-08-24"; :>> createdBy = "claudeFable5"; :>> method = VerificationMethod::inspect; :>> procedureText = "PASS 1, CLAIMS: the two advisory payloads and the six-passed test line are quoted read-backs from the built binary. PASS 2, BOUNDARY: (i) the drift limb needs a HEAD blob, so a NEW file has nothing to compare - correct, a new file's criteria are being authored, not drifting (unit-pinned). (ii) The broken-edge limb reports ALL current dangling edges, not only ones in the edited file - honest because the committed tree is zero, but a PRE-EXISTING working-tree dangle from an earlier unsaved edit would be attributed to this edit; acceptable for advisory. (iii) verification_blocks assumes non-nested braces - true for engine verification declarations. PASS 3, OWN DIFF: I demoed against a STALE binary first (the release build had failed to relink with os-error-5 Access-denied while a cargo lock/AV held keel.exe) and saw a false silent; caught it by grepping the binary for the advisory string, rebuilt, re-demoed. Durable lesson recorded in retro. WHAT A REVIEWER SHOULD ATTACK: whether reporting whole-model dangling edges (vs edited-file-only) is too broad - it is deliberately broad because the committed baseline is zero, but a reviewer may want it scoped to edges touching the edited file's items."; }
    part proactivePostEditReviewGateR1 : TestResult { :>> id = "3f754ca3-dae9-4016-8d33-82277dbc2b71"; :>> outcome = VerdictKind::pass; :>> judgedAgainst = "ea77d8a76f7d747b081861eb62f3d3930c78cf9d"; :>> judgedAt = "2026-08-24"; :>> judgedBy = "claudeFable5"; }
    verification proactivePostEditCloseOutGate : Test { :>> id = "88d2f5a1-b67d-49c6-9f49-177e4487eee1"; :>> title = "Sprint 445 closeOut gate (autonomous, D0049)"; :>> createdAt = "2026-08-24"; :>> createdBy = "claudeFable5"; :>> method = VerificationMethod::inspect; :>> procedureText = "Autonomous closeOut (D0049). D0209 clause 4 delivered and verified end-to-end + unit-tested; validate + all 48 guards + rules --enforce green after this covering sprint; the impl landed at ea77d8a. With this, ALL FOUR D0209 clauses (audit-adherence, freeze-enforcement-surface, process-cursor, proactive-post-edit) are delivered; only the opt-in orchestrator remains DEFERRED by D0209 itself."; }
    part proactivePostEditCloseOutGateR1 : TestResult { :>> id = "70cd7569-9bf9-40f7-9894-dcacc658632f"; :>> outcome = VerdictKind::pass; :>> judgedAgainst = "ea77d8a76f7d747b081861eb62f3d3930c78cf9d"; :>> judgedAt = "2026-08-24"; :>> judgedBy = "claudeFable5"; }
    verification proactivePostEditRetroGate : Test { :>> id = "c6eb4474-58e5-473d-b114-5970b2a317ad"; :>> title = "Sprint 445 retro gate (autonomous, D0049)"; :>> createdAt = "2026-08-24"; :>> createdBy = "claudeFable5"; :>> method = VerificationMethod::analyze; :>> procedureText = "Autonomous retro (D0049). AVOIDABLE-ISSUE SCAN under rcRecurrence: a NEW and costly recurrence of the stale-binary class - the release build reported exit 0 but had FAILED to relink keel.exe (os error 5, Access denied: a cargo package-cache lock plus the exe transiently held), so I demoed clause 4 against the cursor-era binary and saw a false SILENT that looked like a bug in my new code; I burned several diagnostic passes on correct code. Durable rule, now learned hard: after any release build that will be DEMOED, verify the binary actually contains the change (grep the exe for a unique new string, or check mtime > source) before trusting a silent/negative result - a background build's exit-0 is NOT proof the binary was relinked. WELL: both advisory limbs worked on the first correct run once the binary was fresh, and the non-blocking systemMessage channel was exactly right - guidance without gating, matching D0098. Estimate 2 pts, delivered 2. ALL D0209 build clauses now complete."; }
    part proactivePostEditRetroGateR1 : TestResult { :>> id = "6d80acdb-2cc0-4a4f-afaf-d0f911ab7017"; :>> outcome = VerdictKind::pass; :>> judgedAgainst = "ea77d8a76f7d747b081861eb62f3d3930c78cf9d"; :>> judgedAt = "2026-08-24"; :>> judgedBy = "claudeFable5"; }
}
