// ProjectDeliveryS345 — Sprint 345: the human asked whether creating the knowledge graph could be a
// process. It already is one, and that question exposed a defect in D0161 draft 2: it silently
// contradicted three of the accepted process's eight steps. CHANGE (§3a). 2 pts.
package ProjectDeliveryS345 {
    private import EngineElement::*;
    private import EngineWork::*;
    private import EngineVerification::*;
    private import EngineRelationships::*;

    #CharteredBy dependency from knowledgeProcessStory to d0161;

    part knowledgeProcessStory : Story {
        :>> id = "0d800540-0814-6540-9b3e-000000300540";
        :>> title = "Sprint 345: D0161 draft 3 — knowledgeGraphMemory v2 makes the corpus a parameter instead of contradicting it (2 pts)";
        :>> createdAt = "2026-08-18"; :>> createdBy = "claudeOpus5"; :>> kind = WorkKind::decision; :>> priority = WorkPriority::p0; :>> owner = "claudeOpus5"; :>> estimatedPoints = 2;
    }

    action def DeliveryRunS345 {
        action storyKnowledgeProcess;
        verification storyKnowledgeProcessDoD : Test { :>> id = "0d800541-0814-6541-9b3e-000000300541"; :>> method = VerificationMethod::inspect; :>> procedureText = "THE HUMAN ASKED WHETHER CREATING THE KNOWLEDGE GRAPH COULD BE A PROCESS, EXPECTING IT TO CHANGE GOING FORWARD. ANSWER: IT ALREADY IS ONE, and has been since D0153 was accepted - `.engine/processes/knowledge-graph-memory.sysml` declares an eight-step Process, bound to a registered skill at `.engine/skills/knowledge-graph-memory/SKILL.md` by the hard `process-skill` guard (18 processes scanned, PASS). THE QUESTION EXPOSED A DEFECT IN MY OWN DRAFT 2: its out-of-scope clause put 'ingesting external documents' and 'recall injection into the harness prompt path' outside the design, and those are not out-of-scope items - THEY ARE STEP 4 AND STEP 6 OF THAT ACCEPTED PROCESS. Draft 2 proposed a store that three of the eight steps could not produce while claiming to implement the Decision specifying them. A design may amend a process; it may not quietly disagree with one. Draft 3 amends instead: the CORPUS BECOMES A DECLARED PARAMETER with a document case (extract, computed identity) and an already-typed-model case (bind, existing minted UUIDs), step 3 binds fact shapes to existing types where they exist, and step 6 becomes tier-conditional. Steps 1, 2, 7 and 8 unchanged. validate 373 clean; check-engine clean; process-change and process-skill both PASS; no code changed and no process file edited - the amendment awaits acceptance."; }
        part storyKnowledgeProcessDoDR1 : TestResult { :>> id = "0d800542-0814-6542-9b3e-000000300542"; :>> outcome = VerdictKind::pass; :>> judgedAgainst = "af51f3f"; :>> judgedAt = "2026-08-18"; :>> judgedBy = "claudeOpus5"; }
    }

    verification kpRefineGate : Test { :>> id = "0d800543-0814-6543-9b3e-000000300543"; :>> title = "Sprint 345 refine gate (DoR)"; :>> createdAt = "2026-08-18"; :>> createdBy = "claudeOpus5"; :>> method = VerificationMethod::inspect; :>> procedureText = "DoR. The request read as a VIEW ('can it be a process?') and the answer is computable - it is one, here is the file. But answering only that would have left the defect standing, so the sprint is scoped as CHANGE: check the proposed design against the accepted process it claims to implement. Checking that at all was prompted by their question, not by my own review, which is the finding worth recording. estimatedPoints=2."; }
    part kpRefineGateR1 : TestResult { :>> id = "0d800544-0814-6544-9b3e-000000300544"; :>> outcome = VerdictKind::pass; :>> judgedAgainst = "af51f3f"; :>> judgedAt = "2026-08-18"; :>> judgedBy = "claudeOpus5"; }

    verification kpStandupGate : Test { :>> id = "0d800545-0814-6545-9b3e-000000300545"; :>> title = "Sprint 345 standup gate"; :>> createdAt = "2026-08-18"; :>> createdBy = "claudeOpus5"; :>> method = VerificationMethod::inspect; :>> procedureText = "Approach: revise D0161 IN PLACE to a third draft rather than propose a rival, because it is mine, it was never accepted, and one governance home per question (D0105) applies to a question whose answer changed three times as much as to one whose answer held. Do NOT edit the process file or the bound skill yet: amending an accepted process definition needs explicit human sign-off, and editing it before acceptance is the CHANGE route skipped - the same reasoning sprint 341 applied to not creating the directory. Blocker acknowledged and not worked around: D0161 cannot be applied without their acceptance, so the defect in D0153's step set stays recorded and unfixed until then."; }
    part kpStandupGateR1 : TestResult { :>> id = "0d800546-0814-6546-9b3e-000000300546"; :>> outcome = VerdictKind::pass; :>> judgedAgainst = "af51f3f"; :>> judgedAt = "2026-08-18"; :>> judgedBy = "claudeOpus5"; }

    verification kpImplementGate : Test { :>> id = "0d800547-0814-6547-9b3e-000000300547"; :>> title = "Sprint 345 implement gate"; :>> createdAt = "2026-08-18"; :>> createdBy = "claudeOpus5"; :>> method = VerificationMethod::analyze; :>> procedureText = "STEP-BY-STEP RECONCILIATION OF D0161 AGAINST THE EIGHT DECLARED STEPS, which is the substance of this sprint. SURVIVE UNCHANGED, and they are why the process is VERSIONED rather than FORKED: kgQuestions (human, questions before documents) becomes `.knowledge/questions/*.sysml`; kgVocabulary (closed ontology) is already satisfied because the engine schema IS a closed vocabulary; kgVerifyOnATrap is adopted verbatim as D0161's acceptance test; kgRecordLimits is D0161's honest-limit clause. CHANGE: kgLogicalModel's 'one table per fact shape' becomes 'bind each shape to the corpus's existing type, or declare a table where none exists', because for an already-typed corpus the tables exist. kgExtract is the real one - it mandates extraction against the vocabulary with COMPUTED identity, and for keel's own corpus there is nothing to extract and identity is the minted UUID items already carry, so it BINDS. kgInjection mandates wiring recall into the harness prompt-submit path, which made a CLI-only capability read as unfinished, so it becomes tier-conditional. FORKING WAS THE ALTERNATIVE AND IS WORSE: it duplicates six of eight steps, which is dual truth, and costs a second registered skill under the process-skill guard, so it is not even cheaper. WHAT ANSWERS THEIR EXPECTATION OF CHANGE DIRECTLY: `#ProspectiveChange` on the Decision makes it a version boundary the engine already computes against - `keel governing-version <item>` reports which version governed any recorded work, `keel reprocess-candidates` computes what to redo when a change is safety-flagged, and issue068 keeps work correct under an older version from being retro-failed."; }
    part kpImplementGateR1 : TestResult { :>> id = "0d800548-0814-6548-9b3e-000000300548"; :>> outcome = VerdictKind::pass; :>> judgedAgainst = "af51f3f"; :>> judgedAt = "2026-08-18"; :>> judgedBy = "claudeOpus5"; }

    verification kpReviewGate : Test { :>> id = "0d800549-0814-6549-9b3e-000000300549"; :>> title = "Sprint 345 review gate"; :>> createdAt = "2026-08-18"; :>> createdBy = "claudeOpus5"; :>> method = VerificationMethod::inspect; :>> procedureText = "Reviewed. THE PATTERN ACROSS THREE DRAFTS IS THE THING WORTH KEEPING. Draft 1 designed from the PROCESS TEXT I had read and produced a store nobody wanted. Draft 2 designed from the OUTCOME they wanted and produced a store that contradicted the process. Draft 3 reconciles the two, and only exists because they asked a question I should have asked myself: does this agree with what is already accepted? EACH DRAFT WAS COHERENT ON ITS OWN AND WRONG IN RELATION TO SOMETHING ELSE, which is the failure mode of designing against one document at a time. THE CONSEQUENCE CLAUSE NOW CARRIES A CONDITIONAL I would defend hardest: if D0161 is REJECTED, D0153's process still keeps three steps runnable only against a corpus this repository does not have, so a rejection must say whether the process is amended anyway. That defect exists independently of whether `.knowledge/` is ever built, and letting a rejection bury it would be the same quiet disagreement one level up. I ALSO STOPPED CALLING THE DOCUMENT BRANCH 'OUT OF SCOPE': it is the other case of the same parameter, unbuilt here, which is the whole point of parameterising."; }
    part kpReviewGateR1 : TestResult { :>> id = "0d80054a-0814-654a-9b3e-00000030054a"; :>> outcome = VerdictKind::pass; :>> judgedAgainst = "af51f3f"; :>> judgedAt = "2026-08-18"; :>> judgedBy = "claudeOpus5"; }

    verification kpCloseOutGate : Test { :>> id = "0d80054b-0814-654b-9b3e-00000030054b"; :>> title = "Sprint 345 closeOut gate (autonomous, D0049)"; :>> createdAt = "2026-08-18"; :>> createdBy = "claudeOpus5"; :>> method = VerificationMethod::inspect; :>> procedureText = "Autonomous closeOut (D0049). D0161 revised to draft 3 and still PROPOSED. NOTHING WAS APPLIED: the process file and its bound skill are untouched, because amending an accepted process definition needs explicit human sign-off and there is no version of this change that can be half-landed - the process, the skill and the store location are one acceptance. pendingAcceptances d0159, d0161, d0162. The defect in D0153's step set is now RECORDED in D0161's context and consequences rather than sitting undetected in a proposed design, which is the part that could be delivered without their signature. validate 373 clean; check-engine clean; 36 guards ALL PASS; no code changed."; }
    part kpCloseOutGateR1 : TestResult { :>> id = "0d80054c-0814-654c-9b3e-00000030054c"; :>> outcome = VerdictKind::pass; :>> judgedAgainst = "af51f3f"; :>> judgedAt = "2026-08-18"; :>> judgedBy = "claudeOpus5"; }

    verification kpRetroGate : Test { :>> id = "0d80054d-0814-654d-9b3e-00000030054d"; :>> title = "Sprint 345 retro gate (autonomous, D0049)"; :>> createdAt = "2026-08-18"; :>> createdBy = "claudeOpus5"; :>> method = VerificationMethod::analyze; :>> procedureText = "Autonomous retro (D0049) under D0131's retroTrack. AVOIDABLE-ISSUE: I wrote a design whose out-of-scope clause named two steps of an accepted process as if they were features I had chosen to skip, and I did not notice because I never re-read the process against the design after redesigning. Sprint 341's own refine gate records that I read D0153 and its process file FIRST and that doing so changed two central choices - so I had the file open, and then draft 2 changed the target without re-checking against it. THE RULE: when a design's TARGET changes, every accepted artifact the previous target was reconciled against must be re-reconciled; a redesign invalidates its own prior agreement checks. WELL: (1) the human's one-line question was answered as a question first - it IS a process, with the file and the guard that binds it to a skill - rather than treated as a request to build something new; (2) the reconciliation was done step-by-step against all eight steps and recorded, not asserted; (3) forking was rejected for a stated reason (six duplicated steps is dual truth, and it costs a second skill anyway) rather than chosen because it was easier to write; (4) nothing was applied before acceptance, third sprint running. THE UNCOMFORTABLE COUNT: three drafts, each found wanting by a one-line question from the human rather than by my own review. Estimate 2 pts, delivered."; }
    part kpRetroGateR1 : TestResult { :>> id = "0d80054e-0814-654e-9b3e-00000030054e"; :>> outcome = VerdictKind::pass; :>> judgedAgainst = "af51f3f"; :>> judgedAt = "2026-08-18"; :>> judgedBy = "claudeOpus5"; }
}
