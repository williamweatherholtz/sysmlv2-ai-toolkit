// ProjectDeliveryS277 — Sprint 277: Process/ProcessStep become `action def`; `order : Integer` becomes
// native succession (D0143). Panel finding (c). EXECUTE. 5 pts.
package ProjectDeliveryS277 {
    private import EngineElement::*;
    private import EngineWork::*;
    private import EngineVerification::*;
    private import EngineRelationships::*;

    #CharteredBy dependency from processBehaviourStory to d0143;

    part processBehaviourStory : Story {
        :>> id = "0d8000fb-0814-60fb-9b3e-0000003000fb";
        :>> title = "Sprint 277: a procedure is behaviour — 115 instances retyped, 71 successions (5 pts)";
        :>> createdAt = "2026-08-14"; :>> createdBy = "claudeOpus5"; :>> kind = WorkKind::modeling; :>> priority = WorkPriority::p0; :>> owner = "claudeOpus5"; :>> estimatedPoints = 5;
    }

    action def DeliveryRunS277 {
        action storyProcessBehaviour;
        verification storyProcessBehaviourDoD : Test { :>> id = "0d8000fc-0814-60fc-9b3e-0000003000fc"; :>> method = VerificationMethod::demo; :>> procedureText = "Covers dcProcessAsBehaviour (panel finding (c)) under D0143 — the finding all three critics ranked above the marker count. `Process`/`ProcessStep` were `part def` with behaviour in Strings and sequence in `attribute order : Integer`, and process.sysml:5-6 records why in one line: 'Reserved words renamed: action -> actionText, output -> producedArtifact, trigger -> triggerCondition'. The author reached for `action def`, hit reserved keywords, and renamed the FIELDS rather than using the constructs those keywords belong to. KERNEL-VERIFIED FIRST, before rewriting anything (`_spike_process_as_action.py`): `action def Proc :> Base`, typed action usage with attributes, `assert constraint` inside both an action usage and an action def, successions between package-level usages and inside a def, and an abstract action def carrying tracked attributes — all valid; the control (undeclared action type) correctly failed. DELIVERED: `abstract action def TrackedAction` in element.sysml as the fourth per-metaclass base (D0055's cross-metaclass constraint); both definitions retyped and `order` DELETED; 22 Process + 93 ProcessStep usages retyped across 17 files; 71 successions emitted, grouped per Process. PARSER, four increments: typed action usages, untyped action usages with parameter bodies, `:>` on an action def, member features inside action-def bodies, and `in`/`out` member kinds. VERIFIED: `keel activation` output IDENTICAL before and after — 6 units, same guard counts — proving D0141's 14 asserts survived the retype, which was the real risk since they were attached to the very parts being changed; `.engine` and `.tracking` validate clean; all 28 guards pass; clippy clean; 161 tests. The `WorkflowState` parts also carry `order` and were deliberately NOT touched — the transform is scoped to ProcessStep blocks."; }
        part storyProcessBehaviourDoDR1 : TestResult { :>> id = "0d8000fd-0814-60fd-9b3e-0000003000fd"; :>> outcome = VerdictKind::pass; :>> judgedAgainst = "06e9154"; :>> judgedAt = "2026-08-14"; :>> judgedBy = "claudeOpus5"; }
    }

    verification pbRefineGate : Test { :>> id = "0d8000fe-0814-60fe-9b3e-0000003000fe"; :>> title = "Sprint 277 refine gate (DoR)"; :>> createdAt = "2026-08-14"; :>> createdBy = "claudeOpus5"; :>> method = VerificationMethod::inspect; :>> procedureText = "DoR: the human read the summary listing this as excluded work and directed it done — 'required to consider this work finished'. The precondition was the kernel spike: a migration over 115 instances must not begin until the shape it emits is known valid, which is the issue097 lesson applied before the cost rather than after. estimatedPoints=5. DoR met."; }
    part pbRefineGateR1 : TestResult { :>> id = "0d8000ff-0814-60ff-9b3e-0000003000ff"; :>> outcome = VerdictKind::pass; :>> judgedAgainst = "06e9154"; :>> judgedAt = "2026-08-14"; :>> judgedBy = "claudeOpus5"; }

    verification pbStandupGate : Test { :>> id = "0d800100-0814-6100-9b3e-000000300100"; :>> title = "Sprint 277 standup gate"; :>> createdAt = "2026-08-14"; :>> createdBy = "claudeOpus5"; :>> method = VerificationMethod::inspect; :>> procedureText = "Approach: kernel-spike the target shape; add the parser increments; transform instances by script with grouping derived from the file's own structure (a `: Process` declaration opens a group, subsequent steps join it); then prove behaviour-preservation by diffing `keel activation`, since D0141's asserts sit on the parts being retyped and are the thing most likely to be silently lost. No blockers."; }
    part pbStandupGateR1 : TestResult { :>> id = "0d800101-0814-6101-9b3e-000000300101"; :>> outcome = VerdictKind::pass; :>> judgedAgainst = "06e9154"; :>> judgedAt = "2026-08-14"; :>> judgedBy = "claudeOpus5"; }

    verification pbImplementGate : Test { :>> id = "0d800102-0814-6102-9b3e-000000300102"; :>> title = "Sprint 277 implement gate"; :>> createdAt = "2026-08-14"; :>> createdBy = "claudeOpus5"; :>> method = VerificationMethod::test; :>> procedureText = "`order` was DELETED rather than kept alongside the successions. Keeping both would be dual truth — an integer sort key and a succession graph asserting the same sequence, free to disagree — and the engine's premise is that state is computed from one authored fact. The 71 successions carry exactly the orderings the 93 `order` values carried, which is a control total rather than a judgement. The transform is scoped to ProcessStep blocks specifically because `WorkflowState` parts also carry `order` and are unrelated; a blanket `order`-stripping regex would have silently corrupted the workflow state machine."; }
    part pbImplementGateR1 : TestResult { :>> id = "0d800103-0814-6103-9b3e-000000300103"; :>> outcome = VerdictKind::pass; :>> judgedAgainst = "06e9154"; :>> judgedAt = "2026-08-14"; :>> judgedBy = "claudeOpus5"; }

    verification pbReviewGate : Test { :>> id = "0d800104-0814-6104-9b3e-000000300104"; :>> title = "Sprint 277 review gate"; :>> createdAt = "2026-08-14"; :>> createdBy = "claudeOpus5"; :>> method = VerificationMethod::inspect; :>> procedureText = "Reviewed. The retype is complete and behaviour-preserving, and it exposed four parser gaps in sequence — each surfaced by `parser-coverage` rising, each closed, the metric falling 7 -> 1. That the metric moved at all is the argument for having built it: without it, retyping 115 instances would have left their attributes silently unread and every gate would still have been green. NOT DONE, and stated so it is not read as complete: `actionText`, `producedArtifact` and `triggerCondition` remain Strings. Converting `producedArtifact` to a typed `out` parameter plus a `flow` is the step that would let a process connect to its neighbours by typed item flow rather than prose, and it requires deciding each artifact's TYPE — modelling per step, not a mechanical transform."; }
    part pbReviewGateR1 : TestResult { :>> id = "0d800105-0814-6105-9b3e-000000300105"; :>> outcome = VerdictKind::pass; :>> judgedAgainst = "06e9154"; :>> judgedAt = "2026-08-14"; :>> judgedBy = "claudeOpus5"; }

    verification pbCloseOutGate : Test { :>> id = "0d800106-0814-6106-9b3e-000000300106"; :>> title = "Sprint 277 closeOut gate (autonomous, D0049)"; :>> createdAt = "2026-08-14"; :>> createdBy = "claudeOpus5"; :>> method = VerificationMethod::inspect; :>> procedureText = "Autonomous closeOut (D0049). dcProcessAsBehaviour carries a passing DoD TestResult; D0143 accepted with the §2.5 sign-off recorded. keel activation identical before and after; validate + all 28 guards + check-engine green; clippy clean; 161 tests. parser-coverage at 1, down from 7 during this sprint, with the residue visible rather than tolerated. No gate bypassed."; }
    part pbCloseOutGateR1 : TestResult { :>> id = "0d800107-0814-6107-9b3e-000000300107"; :>> outcome = VerdictKind::pass; :>> judgedAgainst = "06e9154"; :>> judgedAt = "2026-08-14"; :>> judgedBy = "claudeOpus5"; }

    verification pbRetroGate : Test { :>> id = "0d800108-0814-6108-9b3e-000000300108"; :>> title = "Sprint 277 retro gate (autonomous, D0049)"; :>> createdAt = "2026-08-14"; :>> createdBy = "claudeOpus5"; :>> method = VerificationMethod::analyze; :>> procedureText = "Autonomous retro (D0049) under D0131's retroTrack. WELL: (1) the target shape was kernel-verified BEFORE 115 instances were rewritten, which is issue097's lesson applied ahead of the cost instead of after it; (2) behaviour-preservation was proven by diffing `keel activation` rather than reasoned about, and it was the right thing to check — D0141's asserts sat on the exact parts being retyped; (3) the transform was scoped to ProcessStep blocks because `WorkflowState` also carries `order`, and a blanket regex would have corrupted the state machine silently. AVOIDABLE-ISSUE 1: I retyped the schema before checking that the parser could READ `action def X :> Y`, so check-engine went to 132 diagnostics. Recovered in one step, but the ordering was backwards — the parser increments should have preceded the schema change, exactly as dcParserReadBase preceded the conversions it enabled. NO NEW ITEM, reason stated: this is the same read-the-consumer-first lesson as sprint 270's flow emission, and the general rule is now twice-recorded; what makes it non-gate-able is that the 'consumer' differs per change. AVOIDABLE-ISSUE 2: nine stale JVMs from earlier runs blocked the kernel spike entirely, and PowerShell reported failure with no output at all, which cost several minutes to attribute. NO NEW ITEM: background-task hygiene is already recorded, and the concrete addition is that a blocked kernel presents as a silent PowerShell failure rather than an error — sweep first when a spike will not start. Estimate 5 pts, delivered."; }
    part pbRetroGateR1 : TestResult { :>> id = "0d800109-0814-6109-9b3e-000000300109"; :>> outcome = VerdictKind::pass; :>> judgedAgainst = "06e9154"; :>> judgedAt = "2026-08-14"; :>> judgedBy = "claudeOpus5"; }
}
