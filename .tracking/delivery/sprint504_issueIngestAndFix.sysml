// ProjectDeliveryS504 — Sprint 504: ingest the open GitHub issues, verify what is already fixed, and fix the flag defect. EXECUTE. 5 pts.
package ProjectDeliveryS504 {
    private import EngineElement::*;
    private import EngineWork::*;
    private import EngineVerification::*;
    private import EngineRelationships::*;

    #CharteredBy dependency from issueIngestAndFixStory to d0268;

    part issueIngestAndFixStory : Story {
        :>> id = "9b37efc2-599d-40ec-904f-4b5c2e886931";
        :>> title = "Sprint 504: 15 issues ingested, 2 verified already fixed, 1 fixed, 33 mis-citations corrected (5 pts)";
        :>> createdAt = "2026-08-31"; :>> createdBy = "claudeOpus5"; :>> kind = WorkKind::code; :>> priority = WorkPriority::p0; :>> owner = "claudeOpus5"; :>> estimatedPoints = 5;
    }

    action def DeliveryRunS504 {
        action storyIssueIngestAndFix;
        verification storyIssueIngestAndFixDoD : Test { :>> id = "b50dab2c-8e64-45aa-8f56-e339ce54aeb9"; :>> method = VerificationMethod::test; :>> procedureText = "The human said 'ingest github issues and fix'. INGESTED: 15 open issues pulled, 10 newly recorded (5 were already present), each verbatim at sourceTrust=untrusted because this repository is public. ROUTED UNDER D0268: their direct instruction is the acceptance guard 56 requires - recorded as a Decision rather than bypassed with --trust, because a boundary that can be stepped over silently is not a boundary. TWO VERIFIED ALREADY FIXED, empirically rather than assumed: GH#30 (a fresh project records d0001 beside 261 ReferenceDecisionNNNN packages, duplicate-identity 368 scanned 0 violations) and GH#39 (a project chartered by d9001 keeps it across a migration - today's project-owned-contracts fix). ONE FIXED: GH#14, where an unrecognised flag became the ROOT so `keel guard --read` reported every guard PASS with 0 scanned - two defects compounding, silent mis-parsing plus pass-at-zero, producing a green run over nothing. VERIFY: unknown_flag_is_refused 2/2 (guard, validate and check-engine all exit 2 with no verdict line; an ordinary root still scans the corpus); the defect reproduced BEFORE the fix.: DELIVERED BACKLOG ITEMS: <items>. <what done means, verified how>."; }
        // RAN: // RAN: github-pull 15 items 10 ingested; GH#30 and GH#39 reproduced-fixed on fresh projects; GH#14 reproduced then fixed, unknown_flag_is_refused 2/2; 33 mis-citations corrected; keel guard 0 violations
        part storyIssueIngestAndFixDoDR1 : TestResult { :>> id = "25bbdaf1-937a-41ba-964b-d3d48d7a80a3"; :>> outcome = VerdictKind::pass; :>> judgedAgainst = "9d349dd"; :>> judgedAt = "2026-08-31"; :>> judgedBy = "claudeOpus5"; }
    }

    verification issueIngestAndFixRefineGate : Test { :>> id = "9348165d-5da8-49ba-9342-c4f61a0c4e3f"; :>> title = "Sprint 504 refine gate (DoR)"; :>> createdAt = "2026-08-31"; :>> createdBy = "claudeOpus5"; :>> method = VerificationMethod::inspect; :>> procedureText = "READY: the pull path and the trust tier already existed from D0263/D0264, so this sprint was ingestion plus triage plus fixes, not new mechanism. The one judgment made up front and recorded: whether the human's 'fix' instruction overrides the untrusted tier. It does not OVERRIDE it - it SATISFIES it, because the tier requires a human's acceptance and the repository owner directing the work in an authenticated channel is exactly that."; }
    verification issueIngestAndFixStandupGate : Test { :>> id = "d955001a-fbc3-491a-b5ea-c3a87e70e083"; :>> title = "Sprint 504 standup gate"; :>> createdAt = "2026-08-31"; :>> createdBy = "claudeOpus5"; :>> method = VerificationMethod::inspect; :>> procedureText = "No blocker. Worth naming: I checked which issues were ALREADY resolved before fixing anything, and two were - both by work landed earlier today. Re-fixing them would have been invisible waste, and closing them without evidence would have been a claim; both were reproduced on fresh projects instead."; }
    verification issueIngestAndFixImplementGate : Test { :>> id = "f359e5a5-d276-4e90-9b44-a52e23c4c3b7"; :>> title = "Sprint 504 implement gate"; :>> createdAt = "2026-08-31"; :>> createdBy = "claudeOpus5"; :>> method = VerificationMethod::test; :>> procedureText = "RAN: github-pull -> 15 items, 10 ingested, 5 already recorded, 0 refused. GH#30 verified fixed (fresh strict project: record decision -> d0001, validate clean, duplicate-identity 368 scanned 0 violations, alongside 261 reference decisions). GH#39 verified fixed (project chartered d9001 survives migrate). GH#14 REPRODUCED (keel guard --read: every guard PASS, 0 scanned) then FIXED and armed: unknown_flag_is_refused 2/2. keel guard -> 0 violations. THE ASSERTION THAT FAILED AND TAUGHT SOMETHING: my first probe asserted the refusal emits no 'PASS' anywhere, and it tripped on the refusal's OWN message, which uses the word while explaining the hazard. Tightened to look for a verdict LINE."; }
    verification issueIngestAndFixReviewGate : Test { :>> id = "49e220e2-00e8-4ecb-8980-144ab03abe3d"; :>> title = "Sprint 504 review gate — three passes per D0172"; :>> createdAt = "2026-08-31"; :>> createdBy = "claudeOpus5"; :>> method = VerificationMethod::inspect; :>> procedureText = "THREE PASSES. (1) DID THE TRUST BOUNDARY HOLD: yes, and visibly - guard 56 reports 14 scanned 0 violations, and the acceptance is a Decision naming the fifteen issues and explicitly NOT granting standing permission for future ones. (2) WERE THE 'ALREADY FIXED' CLAIMS EVIDENCED: both reproduced on fresh projects with numbers, not read off a diff. (3) IS THE FIX THE CLASS OR THE INSTANCE: the class - refuse_flag_as_path is shared across guard, validate and check-engine, because the same shape had already appeared twice in one day (guard --read, and github-ingest reading --at's value as a root)."; }
    verification issueIngestAndFixCloseOutGate : Test { :>> id = "90aef856-83af-4a7e-b4c2-e25c5d0426d1"; :>> title = "Sprint 504 closeOut gate (autonomous, D0049)"; :>> createdAt = "2026-08-31"; :>> createdBy = "claudeOpus5"; :>> method = VerificationMethod::inspect; :>> procedureText = "CLOSED. The backlog task dcUnknownFlagIsRefused is delivered by this sprint and GH#14 resolves; GH#30 and GH#39 are verified fixed and can be closed upstream with evidence. Twelve remain open and triaged. The largest finding of the sprint was not any issue: it was that 33 of my own prose citations of issue ids were off by one."; }
    verification issueIngestAndFixRetroGate : Test { :>> id = "7faacb86-5ee4-41d8-b0e1-9125f355f201"; :>> title = "Sprint 504 retro gate (autonomous, D0049)"; :>> createdAt = "2026-08-31"; :>> createdBy = "claudeOpus5"; :>> method = VerificationMethod::analyze; :>> procedureText = "FINDING, and it is the third instance of one pattern in a single day: I pipe a command's output through a truncating filter and then report on what I did not read. `| head -4` killed a migration mid-apply and left a half-written tree, which I briefly reported as a keel defect before catching it. `| tail -1` discarded the id `record issue` prints on its FIRST line - fourteen times - so every prose citation from issue314 onward was off by one, across four Decisions, CLAUDE.md, four source files, two sprints and a propriety round. The command told me the truth every time. WHAT CAUGHT IT: edge-endpoints, the instant a TYPED edge named a non-existent id - that guard is exactly right. WHAT DID NOT: nothing checks prose citations, and prose is where most cross-references live. Filed as issue320 with the control gap stated and deliberately NOT patched, because a naive resolver-check would flag legitimate discussion of superseded ids and repeat D0261's noise mistake."; }
}
