// ProjectDeliveryS624 — Sprint 624: a pass recorded on a dirty tree is read against the commit that lands its work, not the commit before it (dcResultBindsToItsLandingCommit, issue375 / UCA-A2). EXECUTE. 3 pts.
package ProjectDeliveryS624 {
    private import EngineElement::*;
    private import EngineWork::*;
    private import EngineVerification::*;
    private import EngineRelationships::*;

    #CharteredBy dependency from resultBindsToLandingStory to d0308;

    part resultBindsToLandingStory : Story {
        :>> id = "8a6155cd-8886-485f-b652-89ca09bbbd27";
        :>> title = "Sprint 624: a pass recorded on a dirty tree is read against the commit that lands its work, not the commit before it (dcResultBindsToItsLandingCommit, issue375 / UCA-A2) (3 pts)";
        :>> createdAt = "2026-09-09"; :>> createdBy = "claudeOpus5"; :>> kind = WorkKind::code; :>> priority = WorkPriority::p0; :>> owner = "claudeOpus5"; :>> estimatedPoints = 3;
    }

    action def DeliveryRunS624 {
        action storyResultBindsToLanding;
        verification storyResultBindsToLandingDoD : Test { :>> id = "9b2ea7ab-65bd-4efa-99a3-6291cf00e146"; :>> method = VerificationMethod::test; :>> procedureText = "DELIVERED: keel-cli/src/binding.rs computes, for every latest passing result, the commit that INTRODUCED its id from one first-parent `git log -p` walk over .tracking (cached permanently in gitfacts with the SHA walked to), and binds the result to that commit when judgedAgainst is its ancestor or itself; otherwise judgedAgainst stands, and an uncommitted result keeps judgedAgainst. orient's deliverable suspicion reads the binding, so reverify (which reads orient) inherits it; append-result and append-gate-result say on stderr, when the tree is dirty, that the pass binds to the commit that lands it. VERIFIED: the unit fixture records a pass at a base commit, lands the file in a second commit and reads the binding as the landing commit, an unknown id as absent and a non-ancestor judgedAgainst as unchanged; this repository re-reads with 27 suspects against 74 at 896ef88, the 6 added being exactly the class the DoD names - a done task whose own DoD text was edited after its pass and whose old baseline predated the DoD: dcBatchedGovernanceIndex, storyBatchedGovernance, storyCritiquePass3, storyCritiquePass7, storyDeadFields, storyFederationPlatform. Two latent defects the wider baseline exposed are tracked and controlled in this commit: issue421 (batch git stdin written inline deadlocked orient - feed_stdin thread) and issue422 (the issue044 escape class in the criterion reader - string_literal_body with lexer parity, cache reader version)."; }
        // RAN: keel orient . at 896ef88+dirty: suspect 27 (74 in orient_before at 896ef88), the 6 added being dcBatchedGovernanceIndex, storyBatchedGovernance, storyCritiquePass3, storyCritiquePass7, storyDeadFields, storyFederationPlatform - each a done task whose own DoD text differs from the text at its pass's binding commit; ready set unchanged; done 1225 / outstanding 47; cold and warm orient identical; cargo test --workspace --release 676 passed 0 failed
        part storyResultBindsToLandingDoDR1 : TestResult { :>> id = "51872999-b4b8-4895-a8d9-b4fdfab2bba6"; :>> outcome = VerdictKind::pass; :>> judgedAgainst = "896ef88"; :>> judgedAt = "2026-09-09"; :>> judgedBy = "claudeOpus5"; }
    }

    verification resultBindsToLandingRefineGate : Test { :>> id = "b6394b72-195e-4da6-87f3-0cf50a588245"; :>> title = "Sprint 624 refine gate (DoR)"; :>> createdAt = "2026-09-09"; :>> createdBy = "claudeOpus5"; :>> method = VerificationMethod::inspect; :>> procedureText = "READY. Head of keel whats-next; charter is the backlog item resolving issue375, itself the result-side twin of issue341 that D0308 closed for acceptances. Scope is the engine read path plus the two write commands' stderr note; no schema change. 3 points: a module with a git walk, a cache shape change, an orient change and a fixture."; }
    // RAN: keel whats-next . at 896ef88 leads with dcResultBindsToItsLandingCommit; charter edge to d0308 (the acceptance-side rule this extends to results); estimatedPoints 3
    part resultBindsToLandingRefineGateR1 : TestResult { :>> id = "c106b2a5-f44d-4329-98c0-5da4106feee8"; :>> outcome = VerdictKind::pass; :>> judgedAgainst = "896ef88"; :>> judgedAt = "2026-09-09"; :>> judgedBy = "claudeOpus5"; }
    verification resultBindsToLandingStandupGate : Test { :>> id = "2bfb757b-00d6-4530-a7ad-ef0e8b56d379"; :>> title = "Sprint 624 standup gate"; :>> createdAt = "2026-09-09"; :>> createdBy = "claudeOpus5"; :>> method = VerificationMethod::inspect; :>> procedureText = "Blockers: none. The first wiring hung orient outright - git cat-file alive, keel idle - which was a pipe deadlock in the existing batch callers, not the new code; fixed at the root and tracked (issue421) rather than worked around by shrinking the request."; }
    // RAN: keel orient . at 896ef88: no blocker; the first-wiring hang was diagnosed with Get-CimInstance (git cat-file --batch alive, keel idle) and tracked as issue421
    part resultBindsToLandingStandupGateR1 : TestResult { :>> id = "1a3e7f2d-a5fc-44b0-a270-eb72f4072f6b"; :>> outcome = VerdictKind::pass; :>> judgedAgainst = "896ef88"; :>> judgedAt = "2026-09-09"; :>> judgedBy = "claudeOpus5"; }
    verification resultBindsToLandingImplementGate : Test { :>> id = "a2abffd3-a154-449c-901f-9e4abfc3a4bb"; :>> title = "Sprint 624 implement gate"; :>> createdAt = "2026-09-09"; :>> createdBy = "claudeOpus5"; :>> method = VerificationMethod::test; :>> procedureText = "binding.rs (bind, introducing_commits, walk, ids_on, parents_graph, is_ancestor) with three unit tests; gitfacts gains introduced / introduced_walked_to / criterion_reader; orient builds the asks before the pass loop and stamps verified_at with the binding; feed_stdin in valid_commits and batch_cat_blobs; string_literal_body replaces the cut-at-first-quote extraction at both criterion sites with a lexer-parity test; binding_note in main.rs. Release build, clippy -D warnings and the targeted tests all exit 0; the DoD VERIFY clause was amended to state the true expectation (6 real post-pass DoD edits become visible) instead of hiding the finding. Docs: usage.md carries the binding note; the test-result and sprint-standup skill edits hit the D0070 lock and became dcTestResultSkillNamesTheBinding; sync-claude --check clean."; }
    // RAN: cargo build --release exit 0; cargo clippy --workspace --all-targets -- -D warnings exit 0; cargo test --workspace --release: 676 passed 0 failed across 64 test binaries, exit 0 (one file, accept_honours_delegation, took 1489 s while keel.exe was in concurrent use - the issue150 class, not re-run; every other file under 81 s)
    part resultBindsToLandingImplementGateR1 : TestResult { :>> id = "33b9eff4-dea8-41c7-8669-b9b2fc5c3029"; :>> outcome = VerdictKind::pass; :>> judgedAgainst = "896ef88"; :>> judgedAt = "2026-09-09"; :>> judgedBy = "claudeOpus5"; }
    verification resultBindsToLandingReviewGate : Test { :>> id = "50af2009-8540-44f4-9d3e-1a97f8bc1b42"; :>> title = "Sprint 624 review gate — three passes per D0172"; :>> createdAt = "2026-09-09"; :>> createdBy = "claudeOpus5"; :>> method = VerificationMethod::inspect; :>> procedureText = "Pass 1 (intent): the fixture the DoD names is the unit test a_pass_recorded_before_its_landing_commit_binds_to_the_landing_commit. Pass 2 (defects): the 12 new suspects were split by reading blobs at both SHAs - 6 byte-identical lines (false, issue422) and 6 real edits (true findings); the cache would have served the false texts forever, so the reader version invalidates them on load. Pass 3 (docs): usage.md names the binding; the skills' HEAD-equality claims wait on a process-change Decision (dcTestResultSkillNamesTheBinding) because .engine/skills is locked and standing consent does not reach a process edit (D0337)."; }
    // RAN: three passes per D0172: fixture a_pass_recorded_before_its_landing_commit_binds_to_the_landing_commit is the DoD's named case; the 12 new suspects split by git show of the DoD line at both SHAs into 6 byte-identical (issue422) and 6 real edits; grep judgedAgainst over .engine/skills and .engine/docs: usage.md carries the binding note; the two skill edits were refused by the process-change guard (D0070 lock) and reverted, tracked as dcTestResultSkillNamesTheBinding in this commit; sync-claude --check exit 0
    part resultBindsToLandingReviewGateR1 : TestResult { :>> id = "b6fcd6ef-261d-4b2e-ab26-6170bfa389b2"; :>> outcome = VerdictKind::pass; :>> judgedAgainst = "896ef88"; :>> judgedAt = "2026-09-09"; :>> judgedBy = "claudeOpus5"; }
    verification resultBindsToLandingCloseOutGate : Test { :>> id = "a579313e-8ffa-4e42-b647-0a02b49b45d5"; :>> title = "Sprint 624 closeOut gate (autonomous, D0049)"; :>> createdAt = "2026-09-09"; :>> createdBy = "claudeOpus5"; :>> method = VerificationMethod::inspect; :>> procedureText = "Suspects 74 to 27 with the ready set unchanged; cold and warm orient identical; done 1225 / outstanding 47 read back from keel orient. The 6 real DoD edits stay on the suspect frontier for reverify to judge - they are the defect this item was chartered to make visible, not a regression."; }
    // RAN: keel orient . counts done 1225 outstanding 47, suspect 27; the 6 real DoD edits remain on the suspect frontier for reverify
    part resultBindsToLandingCloseOutGateR1 : TestResult { :>> id = "d100508b-5eb9-4a91-b035-243b815c4468"; :>> outcome = VerdictKind::pass; :>> judgedAgainst = "896ef88"; :>> judgedAt = "2026-09-09"; :>> judgedBy = "claudeOpus5"; }
    verification resultBindsToLandingRetroGate : Test { :>> id = "3e87dbdc-2040-4c56-bd52-82cf4f818137"; :>> title = "Sprint 624 retro gate (autonomous, D0049)"; :>> createdAt = "2026-09-09"; :>> createdBy = "claudeOpus5"; :>> method = VerificationMethod::analyze; :>> procedureText = "Retro held; avoidable-issue scan: widening a baseline exposed two dormant defects in code the change did not touch (a pipe deadlock, an unescaped read) - both tracked as issue421 and issue422 with their controls in this commit. Finding: the batch stdin pattern had no test that crossed pipe capacity, and the criterion reader had no parity test against the lexer; each now has one, and any further batch caller that writes stdin inline is the issue421 class."; }
    // RAN: retro finding tracked in this commit: issue421 (feed_stdin control) and issue422 (string_literal_body + criterion_reader control), both #Resolves from dcResultBindsToItsLandingCommit; git status shows .tracking/issues-claudeOpus5.sysml modified
    part resultBindsToLandingRetroGateR1 : TestResult { :>> id = "7cc656a5-f1e1-47e6-ad99-03d8ea4892bf"; :>> outcome = VerdictKind::pass; :>> judgedAgainst = "896ef88"; :>> judgedAt = "2026-09-09"; :>> judgedBy = "claudeOpus5"; }
}
