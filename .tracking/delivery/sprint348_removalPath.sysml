// ProjectDeliveryS348 — Sprint 348: three questions about the knowledge graph. Two had answers already;
// the third exposed that no feature in this engine states how it comes back out. CHANGE (§3a). 3 pts.
package ProjectDeliveryS348 {
    private import EngineElement::*;
    private import EngineWork::*;
    private import EngineVerification::*;
    private import EngineRelationships::*;

    #CharteredBy dependency from removalPathStory to d0163;

    part removalPathStory : Story {
        :>> id = "0d800570-0814-6570-9b3e-000000300570";
        :>> title = "Sprint 348: activation surface made truthful (issue149); D0161 draft 4 and D0163 give capability an exit (3 pts)";
        :>> createdAt = "2026-08-19"; :>> createdBy = "claudeOpus5"; :>> kind = WorkKind::decision; :>> priority = WorkPriority::p0; :>> owner = "claudeOpus5"; :>> estimatedPoints = 3;
    }

    action def DeliveryRunS348 {
        action storyRemovalPath;
        verification storyRemovalPathDoD : Test { :>> id = "0d800571-0814-6571-9b3e-000000300571"; :>> method = VerificationMethod::test; :>> procedureText = "THREE QUESTIONS, ANSWERED AGAINST THE CODE RATHER THAN FROM MEMORY. (1) IS THERE A PROCESS FOR CREATING THE KNOWLEDGE GRAPH? YES - `.engine/processes/knowledge-graph-memory.sysml`, eight steps, D0153, bound to a registered skill by the hard `process-skill` guard. (2) IS THERE A MEANS OF UPDATING IT? YES, and it is better than I expected: `#ProspectiveChange`/`#SafetyChange` on a Decision makes it a VERSION BOUNDARY the engine computes against, so `keel governing-version <item>` reports which version governed any recorded work, `keel reprocess-candidates` computes what to redo when a change is safety-flagged, issue068 keeps older work from being retro-failed, and `keel process export/import` moves the process to another project. (3) IS THERE A MEANS OF UNPLUGGING IT? NO, AND THE ANSWER HAD TWO LAYERS. `keel deactivate` exists (D0138) but switches GUARDS, so it reaches only a process asserting a constraint - 6 of 18 here - and `keel activation` listed those 6 with nothing to indicate the other 12 existed, while `keel deactivate knowledge-graph-memory` answered `not a declared process unit`, which reads as NO SUCH PROCESS. That surface defect is issue149, fixed and controlled. The deeper layer is a design gap: NOTHING in `.engine/decisions/` states a removal path for anything it added - 162 Decisions answer 'what if we do this' and 'what if we do not', none answers 'what if we do this and then want it gone'. D0161 draft 4 supplies one for its own feature at three levels and makes the rollback part of its ACCEPTANCE test; D0163 proposes the general rule. validate 377 clean; check-engine clean; 36 guards ALL PASS; 189 tests; clippy clean."; }
        part storyRemovalPathDoDR1 : TestResult { :>> id = "0d800572-0814-6572-9b3e-000000300572"; :>> outcome = VerdictKind::pass; :>> judgedAgainst = "a6d6545"; :>> judgedAt = "2026-08-19"; :>> judgedBy = "claudeOpus5"; }
    }

    verification rpRefineGate : Test { :>> id = "0d800573-0814-6573-9b3e-000000300573"; :>> title = "Sprint 348 refine gate (DoR)"; :>> createdAt = "2026-08-19"; :>> createdBy = "claudeOpus5"; :>> method = VerificationMethod::inspect; :>> procedureText = "DoR. Three questions, all reading as VIEW, and two of them were - the answers were in the code and I had answered the first from memory in the previous turn. The third turned out to be a CHANGE, because the honest answer was 'no', and a question whose answer is a gap is not a view request. Scoped as: verify all three against the code, fix the misleading surface, and give the feature an exit before it is built rather than after. estimatedPoints=3."; }
    part rpRefineGateR1 : TestResult { :>> id = "0d800574-0814-6574-9b3e-000000300574"; :>> outcome = VerdictKind::pass; :>> judgedAgainst = "a6d6545"; :>> judgedAt = "2026-08-19"; :>> judgedBy = "claudeOpus5"; }

    verification rpStandupGate : Test { :>> id = "0d800575-0814-6575-9b3e-000000300575"; :>> title = "Sprint 348 standup gate"; :>> createdAt = "2026-08-19"; :>> createdBy = "claudeOpus5"; :>> method = VerificationMethod::inspect; :>> procedureText = "Approach: check each claim against the binary before answering, including the one I had already answered - which is how the 6-of-18 discrepancy surfaced, because `keel activation` printed a list I had not actually read. Then check whether the deactivation gap was a REGRESSION before calling it one: `git show` of the retired `process-units.toml` proved it listed the same six units, so the model-derived replacement (D0139(D)) reproduced the old set faithfully and the mechanism was never broken. That distinction changed the fix from 'restore lost behaviour' to 'stop the surface overstating what the mechanism is'. No blockers."; }
    part rpStandupGateR1 : TestResult { :>> id = "0d800576-0814-6576-9b3e-000000300576"; :>> outcome = VerdictKind::pass; :>> judgedAgainst = "a6d6545"; :>> judgedAt = "2026-08-19"; :>> judgedBy = "claudeOpus5"; }

    verification rpImplementGate : Test { :>> id = "0d800577-0814-6577-9b3e-000000300577"; :>> title = "Sprint 348 implement gate"; :>> createdAt = "2026-08-19"; :>> createdBy = "claudeOpus5"; :>> method = VerificationMethod::test; :>> procedureText = "issue149, A SURFACE FIX WITH NO SEMANTIC CHANGE, which is the discipline worth noting: not one guard changed state. `activation::declared_processes` reports every file in `.engine/processes/`; `keel activation` now lists 18 where it listed 6, marking the guard-less ones `[always] asserts no guard - nothing to switch off`; and the refusal distinguishes an unknown name from a declared-but-unswitchable one and says what to do instead - remove the facts the process authors, or give it an `assert constraint` to make it switchable. Verified live BOTH WAYS: `deactivate knowledge-graph-memory` and `deactivate no-such-process` now give different and correct answers. Controlled by declared_processes_is_every_file_not_only_the_guard_bearing_units, which asserts the declared set strictly EXCEEDS the unit set and that every unit is also declared - so the two counts can never silently collapse into one again. THE UNIT SET IS DELIBERATELY NARROWER AND STAYS THAT WAY: activation governs guards, and widening it to mean 'process on/off' would have changed what D0138 promises in order to fix a printing bug. D0161 DRAFT 4 adds the three-level rollback (data: delete the authored questions and lexicon, both commands report nothing declared; declared: give the process an asserted constraint so `keel deactivate` works; code: an ordinary §3a CHANGE with doc-sync) and, more importantly, makes the rollback part of ACCEPTANCE - exercised, not described. D0163 generalises it and satisfies its own rule in its own consequences clause."; }
    part rpImplementGateR1 : TestResult { :>> id = "0d800578-0814-6578-9b3e-000000300578"; :>> outcome = VerdictKind::pass; :>> judgedAgainst = "a6d6545"; :>> judgedAt = "2026-08-19"; :>> judgedBy = "claudeOpus5"; }

    verification rpReviewGate : Test { :>> id = "0d800579-0814-6579-9b3e-000000300579"; :>> title = "Sprint 348 review gate"; :>> createdAt = "2026-08-19"; :>> createdBy = "claudeOpus5"; :>> method = VerificationMethod::inspect; :>> procedureText = "Reviewed. THE ARGUMENT I WOULD DEFEND HARDEST IS WHY D0163's GUARD IS WARNING-LEVEL, because it contradicts what I argued four sprints ago. Sprint 344 made `impossible-evidence-date` HARD and gave a reason: it checks whether a recorded fact is POSSIBLE, which is arithmetic. `removal-path` checks whether PROSE IS ADEQUATE, which is judgment - and a hard gate on judgment gets SATISFIED rather than met, by adding the word 'remove'. D0102's promote-once-low-noise pattern exists for precisely that distinction, and applying it consistently means accepting a weaker control here even though a stronger one was right there. WHY THE THREE LEVELS ARE RANKED RATHER THAN LISTED: a capability inert without authored input needs no mechanism at all, so 'can this be shaped so its only input is authored?' is a design question worth asking BEFORE building - and asking it of D0161 is what made draft 4 better than draft 3 rather than merely longer. THE EVIDENCE THAT THIS GAP IS REAL AND NOT MY INVENTION: D0132 already records the harder version, a kernel validator that could only be turned off all-or-nothing, so it was turned off and took every other validation layer with it. An unremovable control cost more than the control was worth, and that is the same failure this rule is cheap insurance against. HONEST NOTE: D0163 is PROPOSED and its guard is NOT built, so today the rule binds nothing. That is deliberate - building enforcement for an unaccepted policy is the CHANGE route skipped - but it means the gap stands until they sign."; }
    part rpReviewGateR1 : TestResult { :>> id = "0d80057a-0814-657a-9b3e-00000030057a"; :>> outcome = VerdictKind::pass; :>> judgedAgainst = "a6d6545"; :>> judgedAt = "2026-08-19"; :>> judgedBy = "claudeOpus5"; }

    verification rpCloseOutGate : Test { :>> id = "0d80057b-0814-657b-9b3e-00000030057b"; :>> title = "Sprint 348 closeOut gate (autonomous, D0049)"; :>> createdAt = "2026-08-19"; :>> createdBy = "claudeOpus5"; :>> method = VerificationMethod::inspect; :>> procedureText = "Autonomous closeOut (D0049). issue149 recorded, triaged to dcActivationSurface, delivered with a control. D0161 revised to draft 4 - still PROPOSED, now with a tested rollback. D0163 PROPOSED and its guard NOT BUILT, stated plainly rather than implied: the rule binds nothing until accepted. NOTHING WAS APPLIED to the knowledge process itself - no `.knowledge/` directory, no asserted constraint, no `keel why` - because the process amendment, the store location and the rollback design are one acceptance and half-landing them would leave the process disagreeing with itself. pendingAcceptances d0159, d0161, d0162, d0163. validate 377 clean; check-engine clean; 36 guards ALL PASS; 189 tests; clippy clean."; }
    part rpCloseOutGateR1 : TestResult { :>> id = "0d80057c-0814-657c-9b3e-00000030057c"; :>> outcome = VerdictKind::pass; :>> judgedAgainst = "a6d6545"; :>> judgedAt = "2026-08-19"; :>> judgedBy = "claudeOpus5"; }

    verification rpRetroGate : Test { :>> id = "0d80057d-0814-657d-9b3e-00000030057d"; :>> title = "Sprint 348 retro gate (autonomous, D0049)"; :>> createdAt = "2026-08-19"; :>> createdBy = "claudeOpus5"; :>> method = VerificationMethod::analyze; :>> procedureText = "Autonomous retro (D0049) under D0131's retroTrack. AVOIDABLE-ISSUE: in the previous turn I answered 'is creating the knowledge graph a process?' by finding the file and the registered skill, and reported that the machinery for change was all present - without running `keel activation`, which would have shown 6 of 18 in one line. I answered the question that was asked and stopped at the first confirming evidence. The human then asked the NEXT question and the same surface produced a wrong-sounding answer. The rule: when answering 'does this mechanism exist', RUN IT, do not merely locate it - existence and adequacy are different claims and only one of them was checked. FOURTH DRAFT OF D0161, AND THE TALLY IS THE FINDING: draft 1 wrong target, draft 2 contradicted an accepted process, draft 3 missing an exit, each caught by a one-line question from the human rather than by my own review. What their questions have in common is that they come from the position of someone who has to LIVE with the thing - use it, change it, abandon it - and mine came from the position of someone building it. That is not a reviewing technique I can adopt by resolving to; the closest thing available is D0163, which turns one of those questions into a required clause so it gets asked without depending on anyone remembering. WELL: (1) every claim was checked against the binary this time, including one I had already made, which is what surfaced issue149; (2) I checked whether the deactivation gap was a regression before calling it one, and it was not - which changed the fix; (3) the surface was fixed without widening what D0138 promises, resisting the tempting version that would have made `deactivate` mean 'process on/off'; (4) D0163 satisfies its own rule in its own consequences clause, since a policy that exempted itself would prove it was ceremony. Estimate 3 pts, delivered."; }
    part rpRetroGateR1 : TestResult { :>> id = "0d80057e-0814-657e-9b3e-00000030057e"; :>> outcome = VerdictKind::pass; :>> judgedAgainst = "a6d6545"; :>> judgedAt = "2026-08-19"; :>> judgedBy = "claudeOpus5"; }
}
