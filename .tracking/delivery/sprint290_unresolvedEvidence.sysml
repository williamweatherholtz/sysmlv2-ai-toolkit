// ProjectDeliveryS290 — Sprint 290: unverifiable-from-here is not unverified — the evidence classes
// split (dcUnresolvedEvidence, D0129). EXECUTE. 5 pts.
package ProjectDeliveryS290 {
    private import EngineElement::*;
    private import EngineWork::*;
    private import EngineVerification::*;
    private import EngineRelationships::*;

    #CharteredBy dependency from unresolvedEvidenceStory to d0144;

    part unresolvedEvidenceStory : Story {
        :>> id = "0d8001cd-0814-61cd-9b3e-0000003001cd";
        :>> title = "Sprint 290: unsynchronized evidence is not invalid evidence (5 pts)";
        :>> createdAt = "2026-08-15"; :>> createdBy = "claudeOpus5"; :>> kind = WorkKind::code; :>> priority = WorkPriority::p0; :>> owner = "claudeOpus5"; :>> estimatedPoints = 5;
    }

    action def DeliveryRunS290 {
        action storyUnresolvedEvidence;
        verification storyUnresolvedEvidenceDoD : Test { :>> id = "0d8001ce-0814-61ce-9b3e-0000003001ce"; :>> method = VerificationMethod::test; :>> procedureText = "Delivers dcUnresolvedEvidence (srDcUnresolvedEvidenceClass, D0129). Under PARTIAL SYNCHRONIZATION — the normal state of a distributed team — an anchor may be missing from this clone simply because it has not been fetched. Collapsing that into `invalidEvidence` treats finished work as not-done, so it re-enters the ready frontier and a second contributor redoes it. DELIVERED: `orient` now reports `unsynchronizedEvidence` separately, and those tasks stay DONE; `keel sync`, which has actually fetched, reports the definitive `invalidEvidence` classification. THE PREDICATE IS THE FINDING. The obvious rule — 'this clone is current if behind == 0' — is WRONG, and the fixture proved it before any conclusion was drawn from it: `behind` is measured against the remote-tracking ref, which is only as fresh as the last fetch, so a clone that has NEVER fetched reports `behind 0` while being arbitrarily stale, and would confidently declare another contributor's evidence invalid. The honest predicate is about whether this run actually LOOKED: an anchor is genuinely dangling only when a fetch has just confirmed there is nothing to find, or when there is no upstream at all and therefore nothing that could be fetched. VERIFIED ON TWO REAL CLONES, all four cases: (1) an anchor present on the remote but unfetched reports `unsynchronized`, NOT invalid, and the task stays done — counts 1 done / 0 outstanding, and it is not re-listed as ready; (2) after `git fetch`, the unsynchronized set empties with no other change; (3) an anchor NOBODY has is reported by `keel sync` as 'genuinely dangling, not unfetched' with the issue071 consequence stated; (4) a repo with no upstream judges directly and reports it as invalid and outstanding, so a single-clone project keeps the full protection. clippy clean; 133 lib tests; validate + 29 guards green."; }
        part storyUnresolvedEvidenceDoDR1 : TestResult { :>> id = "0d8001cf-0814-61cf-9b3e-0000003001cf"; :>> outcome = VerdictKind::pass; :>> judgedAgainst = "33aa053"; :>> judgedAt = "2026-08-15"; :>> judgedBy = "claudeOpus5"; }
    }

    verification ueRefineGate : Test { :>> id = "0d8001d0-0814-61d0-9b3e-0000003001d0"; :>> title = "Sprint 290 refine gate (DoR)"; :>> createdAt = "2026-08-15"; :>> createdBy = "claudeOpus5"; :>> method = VerificationMethod::inspect; :>> procedureText = "DoR. CONSUMER CHECK (dorConsumer, D0144): the consumers of this classification are `ready` and the `outstanding` count, and both had to be considered together — moving a task out of `invalid` is only correct if it also stays DONE, otherwise the split renames the problem instead of fixing it. The sprint-289 `sync::divergence` work is the input, which is why this item ranked after it rather than before. estimatedPoints=5. DoR met."; }
    part ueRefineGateR1 : TestResult { :>> id = "0d8001d1-0814-61d1-9b3e-0000003001d1"; :>> outcome = VerdictKind::pass; :>> judgedAgainst = "33aa053"; :>> judgedAt = "2026-08-15"; :>> judgedBy = "claudeOpus5"; }

    verification ueStandupGate : Test { :>> id = "0d8001d2-0814-61d2-9b3e-0000003001d2"; :>> title = "Sprint 290 standup gate"; :>> createdAt = "2026-08-15"; :>> createdBy = "claudeOpus5"; :>> method = VerificationMethod::inspect; :>> procedureText = "Approach: build the two-clone fixture FIRST and let it adjudicate the predicate, rather than reasoning about git semantics and testing afterwards. That ordering is what caught the `behind == 0` error — I wrote the obvious predicate, ran it, and the fixture reported `behind 0` for a clone that demonstrably did not have the object. No blockers."; }
    part ueStandupGateR1 : TestResult { :>> id = "0d8001d3-0814-61d3-9b3e-0000003001d3"; :>> outcome = VerdictKind::pass; :>> judgedAgainst = "33aa053"; :>> judgedAt = "2026-08-15"; :>> judgedBy = "claudeOpus5"; }

    verification ueImplementGate : Test { :>> id = "0d8001d4-0814-61d4-9b3e-0000003001d4"; :>> title = "Sprint 290 implement gate"; :>> createdAt = "2026-08-15"; :>> createdBy = "claudeOpus5"; :>> method = VerificationMethod::test; :>> procedureText = "The design cost is real and worth stating: because `orient` never fetches, it can no longer report `invalidEvidence` in a repo that HAS an upstream — it reports `unsynchronized` and names `keel sync` as the remedy. That is a genuine reduction in what my most-used command asserts, and it is the correct trade: the alternative is a command that declares other contributors' evidence invalid on the strength of a stale ref, which is precisely the machine-dependent computed state issue071 exists to prevent. The protection is not lost, it MOVES to `keel sync` — which the post-commit path already runs via `keel land` — and stays immediate for a single-clone project with no upstream."; }
    part ueImplementGateR1 : TestResult { :>> id = "0d8001d5-0814-61d5-9b3e-0000003001d5"; :>> outcome = VerdictKind::pass; :>> judgedAgainst = "33aa053"; :>> judgedAt = "2026-08-15"; :>> judgedBy = "claudeOpus5"; }

    verification ueReviewGate : Test { :>> id = "0d8001d6-0814-61d6-9b3e-0000003001d6"; :>> title = "Sprint 290 review gate"; :>> createdAt = "2026-08-15"; :>> createdBy = "claudeOpus5"; :>> method = VerificationMethod::inspect; :>> procedureText = "Reviewed. The unit test deliberately asserts only the degenerate case — that nothing is invented either way on an empty tree — and says so, because the substantive distinction is about git OBJECT VISIBILITY and cannot be faked in-process. Claiming unit coverage of the four real cases would have been the more comfortable record and a false one; they are exercised end-to-end against two real clones and that is where the evidence lives."; }
    part ueReviewGateR1 : TestResult { :>> id = "0d8001d7-0814-61d7-9b3e-0000003001d7"; :>> outcome = VerdictKind::pass; :>> judgedAgainst = "33aa053"; :>> judgedAt = "2026-08-15"; :>> judgedBy = "claudeOpus5"; }

    verification ueCloseOutGate : Test { :>> id = "0d8001d8-0814-61d8-9b3e-0000003001d8"; :>> title = "Sprint 290 closeOut gate (autonomous, D0049)"; :>> createdAt = "2026-08-15"; :>> createdBy = "claudeOpus5"; :>> method = VerificationMethod::inspect; :>> procedureText = "Autonomous closeOut (D0049). dcUnresolvedEvidence carries a passing DoD TestResult. All four cases demonstrated on real clones; the design cost recorded rather than glossed. clippy clean; 133 lib tests; validate clean; check-engine clean; 29 guards green. No gate bypassed."; }
    part ueCloseOutGateR1 : TestResult { :>> id = "0d8001d9-0814-61d9-9b3e-0000003001d9"; :>> outcome = VerdictKind::pass; :>> judgedAgainst = "33aa053"; :>> judgedAt = "2026-08-15"; :>> judgedBy = "claudeOpus5"; }

    verification ueRetroGate : Test { :>> id = "0d8001da-0814-61da-9b3e-0000003001da"; :>> title = "Sprint 290 retro gate (autonomous, D0049)"; :>> createdAt = "2026-08-15"; :>> createdBy = "claudeOpus5"; :>> method = VerificationMethod::analyze; :>> procedureText = "Autonomous retro (D0049) under D0131's retroTrack. WELL: (1) the fixture was built before the predicate was trusted, and it immediately falsified the obvious one — `behind == 0` looked exactly like 'this clone is current' and is not, which no amount of reading the code would have shown; (2) the design COST is recorded in the implement gate rather than omitted: `orient` now asserts less than it did, and a reader deserves to know that was chosen rather than overlooked; (3) the unit test states what it does NOT cover instead of implying otherwise. AVOIDABLE-ISSUE 1: my first two attempts at case 3 failed on fixture hygiene rather than on the code — an uncommitted edit blocked a merge, then a half-merged clone from the previous attempt blocked the next. Both were my test setup, not the tool, and I nearly read the second as a `keel sync` defect before checking the tree state. NO NEW ITEM, reason stated: it cost two commands and no wrong conclusion was recorded; the operational lesson is that a fixture reused across cases carries state, so a case that must start clean should start from a fresh clone — which is what case 3 finally did. Estimate 5 pts, delivered."; }
    part ueRetroGateR1 : TestResult { :>> id = "0d8001db-0814-61db-9b3e-0000003001db"; :>> outcome = VerdictKind::pass; :>> judgedAgainst = "33aa053"; :>> judgedAt = "2026-08-15"; :>> judgedBy = "claudeOpus5"; }
}
