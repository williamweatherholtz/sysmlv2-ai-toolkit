// ProjectDeliveryS230 — Sprint 230: encodingEngine — the viewer-side axis→visual-encoding engine
// (N-18/D0120). keel-side: /api/slice items now carry their `attrs` (so the viewer can encode by value).
// viewer-side (sysmlv2-viewer@9069110): an Encode panel maps attributes to visual channels (colour /
// x-position / swimlane / nested), DATA-DRIVEN from /api/schema semantics + auto-defaulted + overridable.
// Satisfies srEncodingSpec + srEncodingRender. EXECUTE. 5 pts.
package ProjectDeliveryS230 {
    private import EngineElement::*;
    private import EngineWork::*;
    private import EngineVerification::*;
    private import EngineRequirements::*;
    private import EngineRelationships::*;

    #CharteredBy dependency from encodingEngineStory to d0120;

    part encodingEngineStory : Story {
        :>> id = "63940516-2c7d-4e8f-c230-51627384c001";
        :>> title = "Sprint 230: encodingEngine (5 pts) - viewer maps attributes to visual channels (colour/x/swimlane/nested), auto-defaulted from schema semantics";
        :>> createdAt = "2026-07-15"; :>> createdBy = "wweatherholtz"; :>> kind = WorkKind::code; :>> priority = WorkPriority::p1; :>> owner = "claudeOpus"; :>> estimatedPoints = 5;
    }

    satisfy srEncodingSpec by encodingEngineStory;
    satisfy srEncodingRender by encodingEngineStory;

    action def DeliveryRunS230 {
        action storyEncodingEngine;
        verification storyEncodingEngineDoD : Test { :>> id = "63940516-2c7d-4e8f-c230-51627384c002"; :>> method = VerificationMethod::demo; :>> procedureText = "Satisfies srEncodingSpec + srEncodingRender (N-18/D0120). KEEL-SIDE: section_subgraph_json now emits each item's `attrs` (all authored values), so /api/slice carries the data to encode by. VIEWER-SIDE (sysmlv2-viewer@9069110): an Encode panel binds visual CHANNELS to attributes — colour (enum -> categorical palette over declared members from /api/schema enums; numeric -> gradient over [min,max]; categorical -> distinct), x-position (numeric/temporal linear; enum/categorical ordinal), swimlane rows (enum/categorical bands), and a nested swimlane layer. Bindings AUTO-DEFAULT from the graph's dominant type's schema semantics (attributeStats kind) and are OVERRIDABLE via selects; a legend shows the mappings; edges hide while encoding; positions set manually (x = scaled channel value, y = swimlane band). Options are node-attr-derived (∪ schema), so even types without a schema def are encodable (generative). VERIFY (demo, live browser): accumulated 117 nodes -> encoded 42 Story nodes into 6 swimlane bands by `kind` (code/decision/documentation/modeling/refactor/research), coloured by `priority`, positioned by `estimatedPoints`; legend rendered; distinct y-rows per band confirmed; 0 console errors. keel clippy + validate + guard + check-engine green. FOLLOW-ON (srEncodingOverride): fine-grained value-level overrides (reorder enum, pin palette, edit bins) beyond the channel-binding overrides."; }
        part storyEncodingEngineDoDR1 : TestResult { :>> id = "63940516-2c7d-4e8f-c230-51627384c003"; :>> outcome = VerdictKind::pass; :>> judgedAgainst = "b6b720d"; :>> judgedAt = "2026-07-15"; :>> judgedBy = "claudeOpus"; :>> notes = "viewer code at sysmlv2-viewer@9069110; keel slice-attrs at keel@b6b720d+."; }
    }

    verification eeRefineGate : Test { :>> id = "63940516-2c7d-4e8f-c230-51627384c004"; :>> title = "Sprint 230 refine gate (DoR)"; :>> createdAt = "2026-07-15"; :>> createdBy = "claudeOpus"; :>> method = VerificationMethod::inspect; :>> procedureText = "DoR: N-18 accepted, semantics foundation shipped (S229). Build the viewer-side encoder consuming /api/schema stats. Enabling keel change: add per-item attrs to /api/slice. #CharteredBy d0120. estimatedPoints=5. DoR met."; }
    part eeRefineGateR1 : TestResult { :>> id = "63940516-2c7d-4e8f-c230-51627384c005"; :>> outcome = VerdictKind::pass; :>> judgedAgainst = "b6b720d"; :>> judgedAt = "2026-07-15"; :>> judgedBy = "claudeOpus"; }
    verification eeStandupGate : Test { :>> id = "63940516-2c7d-4e8f-c230-51627384c006"; :>> title = "Sprint 230 standup gate"; :>> createdAt = "2026-07-15"; :>> createdBy = "claudeOpus"; :>> method = VerificationMethod::inspect; :>> procedureText = "Approach: keel emits attrs in slice items; viewer stores enums+stats, derives encode options from node attrs, auto-defaults channels from stat kind, renders via manual positions (x scale + swimlane y-bands) + colour scales + legend; hide edges while encoding. No blockers."; }
    part eeStandupGateR1 : TestResult { :>> id = "63940516-2c7d-4e8f-c230-51627384c007"; :>> outcome = VerdictKind::pass; :>> judgedAgainst = "b6b720d"; :>> judgedAt = "2026-07-15"; :>> judgedBy = "claudeOpus"; }
    verification eeImplementGate : Test { :>> id = "63940516-2c7d-4e8f-c230-51627384c008"; :>> title = "Sprint 230 implement gate"; :>> createdAt = "2026-07-15"; :>> createdBy = "claudeOpus"; :>> method = VerificationMethod::demo; :>> procedureText = "Encode panel + colourScale/attrDomain/xValue/applyEncoding/renderEncodeLegend/resetEncoding implemented; keel section_subgraph_json attrs added. keel clippy -D warnings clean; live browser demo verified (42 Story nodes, swimlanes by kind, colour by priority, x by estimatedPoints). validate/guard/check-engine green."; }
    part eeImplementGateR1 : TestResult { :>> id = "63940516-2c7d-4e8f-c230-51627384c009"; :>> outcome = VerdictKind::pass; :>> judgedAgainst = "b6b720d"; :>> judgedAt = "2026-07-15"; :>> judgedBy = "claudeOpus"; }
    verification eeReviewGate : Test { :>> id = "63940516-2c7d-4e8f-c230-51627384c00a"; :>> title = "Sprint 230 review gate"; :>> createdAt = "2026-07-15"; :>> createdBy = "claudeOpus"; :>> method = VerificationMethod::inspect; :>> procedureText = "Reviewed. The encoder is genuinely DATA-DRIVEN (scale per attribute from /api/schema semantics; options from actual node attrs) — the grammar-of-graphics channel model realised on cytoscape, and it evolves with the model (generative, D0117). Delivered colour/x/swimlane/nested + auto-default + overridable bindings + legend — the core of N-18. Honest scope: fine-grained value overrides (srEncodingOverride) remain, and the visual is MVP (band separators/labels in-graph are a polish follow-on; the legend carries them today). Clean."; }
    part eeReviewGateR1 : TestResult { :>> id = "63940516-2c7d-4e8f-c230-51627384c00b"; :>> outcome = VerdictKind::pass; :>> judgedAgainst = "b6b720d"; :>> judgedAt = "2026-07-15"; :>> judgedBy = "claudeOpus"; }
    verification eeCloseOutGate : Test { :>> id = "63940516-2c7d-4e8f-c230-51627384c00c"; :>> title = "Sprint 230 closeOut gate (autonomous, D0049)"; :>> createdAt = "2026-07-15"; :>> createdBy = "claudeOpus"; :>> method = VerificationMethod::inspect; :>> procedureText = "Autonomous closeOut (D0049): DoD pass; the encoding engine (srEncodingSpec + srEncodingRender) is delivered + browser-verified. Self-evidencing. NEXT: srEncodingOverride (value-level overrides) + in-graph band labels/separators polish; and the remaining keel-side viewer bricks (viewerChangeImpact/ExportShare/BaselineCompare)."; }
    part eeCloseOutGateR1 : TestResult { :>> id = "63940516-2c7d-4e8f-c230-51627384c00d"; :>> outcome = VerdictKind::pass; :>> judgedAgainst = "b6b720d"; :>> judgedAt = "2026-07-15"; :>> judgedBy = "claudeOpus"; }
    verification eeRetroGate : Test { :>> id = "63940516-2c7d-4e8f-c230-51627384c00e"; :>> title = "Sprint 230 retro gate (autonomous, D0049)"; :>> createdAt = "2026-07-15"; :>> createdBy = "claudeOpus"; :>> method = VerificationMethod::analyze; :>> procedureText = "Autonomous retro (D0049). WELL: built the highest-value viewer feature (encoding viewpoints) data-driven from the semantics foundation (S229), verified live in a browser, and kept it generative (encode options from actual node attrs, scales from schema stats — no hardcoded per-type logic). Enabling keel change (attrs in /api/slice) was minimal + reused across slice+section. AVOIDABLE-ISSUE (banked): slice neighbourhoods are small, so a good encoding demo needed accumulating many seeds — a future 'load all of type T' loader would make type-scoped encoding first-class (candidate backlog). LESSON: encode from the DATA the model exposes; the scale is a function of declared semantics, not code. Estimate 5 pts. NEXT: overrides + polish, or the other viewer bricks."; }
    part eeRetroGateR1 : TestResult { :>> id = "63940516-2c7d-4e8f-c230-51627384c00f"; :>> outcome = VerdictKind::pass; :>> judgedAgainst = "b6b720d"; :>> judgedAt = "2026-07-15"; :>> judgedBy = "claudeOpus"; }
}
