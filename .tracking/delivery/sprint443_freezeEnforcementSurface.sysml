// ProjectDeliveryS443 — Sprint 443: freeze the enforcement surface - guard source, hooks, CI join the keystone lock (D0209 clause 2). EXECUTE. 2 pts.
package ProjectDeliveryS443 {
    private import EngineElement::*;
    private import EngineWork::*;
    private import EngineVerification::*;
    private import EngineRelationships::*;

    #CharteredBy dependency from freezeEnforcementSurfaceStory to d0209;

    part freezeEnforcementSurfaceStory : Story {
        :>> id = "3f311cfc-5b0c-4c21-ab13-33d6812d4d95";
        :>> title = "Sprint 443: a control changes only with a signed Decision (2 pts)";
        :>> createdAt = "2026-08-24"; :>> createdBy = "claudeFable5"; :>> kind = WorkKind::code; :>> priority = WorkPriority::p0; :>> owner = "claudeFable5"; :>> estimatedPoints = 2;
    }

    action def DeliveryRunS443 {
        action storyFreezeEnforcementSurface;
        verification storyFreezeEnforcementSurfaceDoD : Test { :>> id = "e66975c3-4d09-4b3b-8de8-cec9e33b4d69"; :>> method = VerificationMethod::test; :>> procedureText = "DELIVERED: dcFreezeEnforcementSurface (D0209 clause 2, the manager-inversion panel's second increment). issue236 proved a control could be silently disarmed by editing its DEFINITION; dcRulesUnderKeystone closed only the declared-rule leg (.engine/rules/). This extends the keystone lock (process_change guard) to the ENFORCEMENT SURFACE: a staged change to guard SOURCE (files defining any -> GuardReport guard: keel-cli/src/guards.rs, adherence.rs), to .githooks/, or to .github/workflows/*.yml now requires a co-committed #ProspectiveChange/#SafetyChange-marked Decision - a human-signed act. A SEPARATE is_enforcement_surface predicate keeps the intent legible next to is_process_def; keystone_violations and the scanned-count cover both. A COVERAGE AUDIT (unit test enforcement_surface_covers_every_guard_source) scans the real src/ tree for -> GuardReport and fails CI if any guard-defining file sits outside GUARD_SOURCE_FILES, so a NEW guard file cannot be added to escape the lock. D0211 (marked #ProspectiveChange) co-commits, satisfying the very lock it installs. VERIFIED: negative probe - staging keel-cli/src/guards.rs alone turned process-change RED naming the file (the exact issue236 self-modification shape, now caught); positive - co-staging marked D0211 turned it GREEN; two new lib tests pass; workspace clippy --all-targets clean; the impl landed at 087afa2f. RESIDUAL (stated, not hidden): the lock ensures a control CHANGES only by a signed act, not that a guard's logic was not gutted while keeping its name and severity - that stays with code review and the recurring control evaluation."; }
        part storyFreezeEnforcementSurfaceDoDR1 : TestResult { :>> id = "45287c6f-1951-4fc1-8a62-33437abeee33"; :>> outcome = VerdictKind::pass; :>> judgedAgainst = "087afa2f10c2dfdde6b014ebeab60c744da08d1d"; :>> judgedAt = "2026-08-23"; :>> judgedBy = "claudeFable5"; }
    }

    verification freezeEnforcementSurfaceRefineGate : Test { :>> id = "920bff74-749a-44d0-971b-fd05f76531db"; :>> title = "Sprint 443 refine gate (DoR)"; :>> createdAt = "2026-08-24"; :>> createdBy = "claudeFable5"; :>> method = VerificationMethod::inspect; :>> procedureText = "DoR. Delivers D0209 clause 2. issue236/sprint440 found the self-modification gap and closed only .engine/rules/; the guard source, hook config and CI workflows were still freely editable. Scope: extend the keystone to those three surfaces + a self-checking coverage audit. 2 points."; }
    part freezeEnforcementSurfaceRefineGateR1 : TestResult { :>> id = "e0002910-73c5-4ffc-b4d0-ea3d19eef1b3"; :>> outcome = VerdictKind::pass; :>> judgedAgainst = "087afa2f10c2dfdde6b014ebeab60c744da08d1d"; :>> judgedAt = "2026-08-23"; :>> judgedBy = "claudeFable5"; }
    verification freezeEnforcementSurfaceStandupGate : Test { :>> id = "c1761ce4-1c4d-4e58-8668-23cc00ff2066"; :>> title = "Sprint 443 standup gate"; :>> createdAt = "2026-08-24"; :>> createdBy = "claudeFable5"; :>> method = VerificationMethod::inspect; :>> procedureText = "Approach: a SEPARATE is_enforcement_surface predicate (not overloading is_process_def, whose name means process DEFINITION) that keystone_violations also honors; a hand-list GUARD_SOURCE_FILES for guard source, re-derived and checked by a unit test that scans for -> GuardReport so the list cannot silently rot. Co-commit a marked D0211 to pass the lock this very commit installs. No blockers."; }
    part freezeEnforcementSurfaceStandupGateR1 : TestResult { :>> id = "7228676f-6c24-44a0-b6ac-183fd64ccbd3"; :>> outcome = VerdictKind::pass; :>> judgedAgainst = "087afa2f10c2dfdde6b014ebeab60c744da08d1d"; :>> judgedAt = "2026-08-23"; :>> judgedBy = "claudeFable5"; }
    verification freezeEnforcementSurfaceImplementGate : Test { :>> id = "c6b4aa4c-bdda-4592-ac22-96bf3532fb57"; :>> title = "Sprint 443 implement gate"; :>> createdAt = "2026-08-24"; :>> createdBy = "claudeFable5"; :>> method = VerificationMethod::test; :>> procedureText = "Verified by running: negative probe - git add keel-cli/src/guards.rs alone, keel guard -> process-change FAIL naming the file; positive - git add marked D0211 -> process-change PASS; cargo test --lib enforcement_surface -> 2 passed; cargo clippy --workspace --all-targets -D warnings clean (one doc_markdown lint on is_process_def fixed); the pre-commit hook (which runs the release binary's keel guard) passed the impl commit with D0211 co-staged."; }
    part freezeEnforcementSurfaceImplementGateR1 : TestResult { :>> id = "5d77e254-e66b-4332-a113-e691a9d62ffc"; :>> outcome = VerdictKind::pass; :>> judgedAgainst = "087afa2f10c2dfdde6b014ebeab60c744da08d1d"; :>> judgedAt = "2026-08-23"; :>> judgedBy = "claudeFable5"; }
    verification freezeEnforcementSurfaceReviewGate : Test { :>> id = "86396ddf-e602-40a5-bb4e-a8ac9b93f633"; :>> title = "Sprint 443 review gate — three passes per D0172"; :>> createdAt = "2026-08-24"; :>> createdBy = "claudeFable5"; :>> method = VerificationMethod::inspect; :>> procedureText = "PASS 1, CLAIMS: the RED-then-GREEN process-change read-backs and the 2-passed test line are quoted. PASS 2, BOUNDARY: the lock covers guard SOURCE by a hand-list re-derived from -> GuardReport (guards.rs, adherence.rs today) - a guard defined via a different signature (a free fn returning something else, or a macro) would not be scanned; the audit scans the actual marker so the common case is covered, stated. Also: the residual named in sprint440's own review recurs here deliberately - a guard kept blocking but rewritten to check nothing passes both the keystone (it is a signed edit if committed properly) and audit-adherence (name+severity unchanged); that is review + control-eval's job, not this lock's. PASS 3, OWN DIFF: the reflexive tightening is real and intended - my own remaining clauses (3, 4) that touch .githooks/ or workflows now need a marked decision each; that is the D0209 thesis, not an accident. WHAT A REVIEWER SHOULD ATTACK: GUARD_SOURCE_FILES is a two-entry hand-list; if adherence.rs is ever split, the new file needs adding or the coverage test fails - which is the intended failure, but a reviewer should confirm the test actually walks subdirs (it does - recursive collect)."; }
    part freezeEnforcementSurfaceReviewGateR1 : TestResult { :>> id = "b81252f1-fce6-48ad-ad0f-e30498d28611"; :>> outcome = VerdictKind::pass; :>> judgedAgainst = "087afa2f10c2dfdde6b014ebeab60c744da08d1d"; :>> judgedAt = "2026-08-23"; :>> judgedBy = "claudeFable5"; }
    verification freezeEnforcementSurfaceCloseOutGate : Test { :>> id = "ff4b9445-2363-4bc8-91c4-b7613b38f0d4"; :>> title = "Sprint 443 closeOut gate (autonomous, D0049)"; :>> createdAt = "2026-08-24"; :>> createdBy = "claudeFable5"; :>> method = VerificationMethod::inspect; :>> procedureText = "Autonomous closeOut (D0049). D0209 clause 2 delivered and negative-probed; validate + all 48 guards + rules --enforce green after this covering sprint; the impl + D0211 + doc-sync (guards.md, CLAUDE.md) landed at 087afa2f; clauses 3 and 4 remain on the frontier."; }
    part freezeEnforcementSurfaceCloseOutGateR1 : TestResult { :>> id = "6eae37a2-4660-4841-a6b7-3e3321c45dee"; :>> outcome = VerdictKind::pass; :>> judgedAgainst = "087afa2f10c2dfdde6b014ebeab60c744da08d1d"; :>> judgedAt = "2026-08-23"; :>> judgedBy = "claudeFable5"; }
    verification freezeEnforcementSurfaceRetroGate : Test { :>> id = "031dd860-e48d-4359-9083-7976b9d867f0"; :>> title = "Sprint 443 retro gate (autonomous, D0049)"; :>> createdAt = "2026-08-24"; :>> createdBy = "claudeFable5"; :>> method = VerificationMethod::analyze; :>> procedureText = "Autonomous retro (D0049). AVOIDABLE-ISSUE SCAN under rcRecurrence: (1) the ciClippyGreen class recurred - a doc_markdown lint on an unbackticked is_process_def would have failed CI clippy; caught locally BEFORE commit this time by running cargo clippy --workspace --all-targets first, which is now the habit. (2) The re-run-full-guards-after-append-result lesson from sprint442 was applied: full validate+guard+rules before land, not just validate. WELL: the negative probe reproduced the exact issue236 bypass (a lone guard-source edit) and the lock caught it on the first try - the twice-learned probe-must-reproduce-the-real-bypass rule held. Estimate 2 pts, delivered 2."; }
    part freezeEnforcementSurfaceRetroGateR1 : TestResult { :>> id = "cbd4f3f0-80ab-4ced-a5f6-57d2f9b04f3a"; :>> outcome = VerdictKind::pass; :>> judgedAgainst = "087afa2f10c2dfdde6b014ebeab60c744da08d1d"; :>> judgedAt = "2026-08-23"; :>> judgedBy = "claudeFable5"; }
}
