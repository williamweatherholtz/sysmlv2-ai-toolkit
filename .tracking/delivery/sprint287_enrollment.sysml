// ProjectDeliveryS287 — Sprint 287: `keel enroll` — one command from unknown machine to attributable,
// uniformly-gated contributor (dcEnrollment, D0129). EXECUTE. 5 pts.
package ProjectDeliveryS287 {
    private import EngineElement::*;
    private import EngineWork::*;
    private import EngineVerification::*;
    private import EngineRelationships::*;

    #CharteredBy dependency from enrollmentStory to d0144;

    part enrollmentStory : Story {
        :>> id = "0d80019c-0814-619c-9b3e-00000030019c";
        :>> title = "Sprint 287: keel enroll — identity, kind, binding and a PROVEN gate, or refuse (5 pts)";
        :>> createdAt = "2026-08-15"; :>> createdBy = "claudeOpus5"; :>> kind = WorkKind::code; :>> priority = WorkPriority::p0; :>> owner = "claudeOpus5"; :>> estimatedPoints = 5;
    }

    action def DeliveryRunS287 {
        action storyEnrollment;
        verification storyEnrollmentDoD : Test { :>> id = "0d80019d-0814-619d-9b3e-00000030019d"; :>> method = VerificationMethod::demo; :>> procedureText = "Delivers dcEnrollment; deploys `.engine/processes/actor-enrollment.sysml` (D0129). Every remote contributor starts unenrolled, and enrollment is the gate through which attribution, acceptance authority and gate uniformity are all established. DELIVERED `keel enroll --actor I --name N --kind human|ai [--email E]`, covering the process's steps: establish identity explicitly or refuse; record KIND explicitly; register without duplicating; bind the machine; PROVE the gate runs; hand off. GIT IDENTITY IS DELIBERATELY NOT CONSULTED — on an agent's machine it is whatever that machine was configured with, which is exactly how an enrolling AI gets recorded as a human (issue073). Two design commitments carry the module: the Person and Actor branches are SEPARATE code paths rather than one parameterised writer, so 'AI registered as Person' cannot be a one-character bug; and the gate is verified BEFORE anything is written, since registering onto a gate that does not execute records a contributor as ready while holding them to no standard at all (issue076). VERIFIED END TO END ON A FRESH `keel init` PROJECT, every VERIFY line of the item: no arguments REFUSES with exit 2 and names why kind cannot be inferred; `--kind robot` refuses with exit 2 rather than guessing; an AI reaches READY in ONE command and is written `part buildBot : Actor { kind = ActorKind::ai }` with no `Person` anywhere; re-enrolling re-binds and the registry still holds exactly ONE entry; a human enrolls as `Person` and is told they MAY attest, an AI is told plainly it may NOT; a project with a broken gate reports NOT READY with the remedy, exits 1, and registers NOTHING — the refusal is atomic, not half-applied; the fresh project passes its own validate + guard afterwards. The binding is proven by READ-BACK through `actor::resolve`, because issue072 was precisely a capture step that printed an actor id which nothing consumed. clippy clean; 179 tests; validate 309 clean; 29 guards green."; }
        part storyEnrollmentDoDR1 : TestResult { :>> id = "0d80019e-0814-619e-9b3e-00000030019e"; :>> outcome = VerdictKind::pass; :>> judgedAgainst = "1b69544"; :>> judgedAt = "2026-08-15"; :>> judgedBy = "claudeOpus5"; }
    }

    verification enRefineGate : Test { :>> id = "0d80019f-0814-619f-9b3e-00000030019f"; :>> title = "Sprint 287 refine gate (DoR)"; :>> createdAt = "2026-08-15"; :>> createdBy = "claudeOpus5"; :>> method = VerificationMethod::inspect; :>> procedureText = "DoR. CONSUMER CHECK (dorConsumer, D0144), and it found a blocker BEFORE any code was written: the process step `enrollKindRole` requires ROLE to be recorded as model data, and `part def Actor` has no `role` attribute — name, email and kind, and nothing else. Had the schema been checked AFTER building the command, `keel enroll --role` would exist and would be writing role into a display-name string or a comment: model data somewhere no view can query, which is the dual-truth defect this engine exists to prevent, introduced while implementing the process that forbids it. Recorded as issue110 with D0146 PROPOSED; role stays unrecorded and the command SAYS SO. Note that role is not in this item's VERIFY list, so the item completes honestly. estimatedPoints=5. DoR met."; }
    part enRefineGateR1 : TestResult { :>> id = "0d8001a0-0814-61a0-9b3e-0000003001a0"; :>> outcome = VerdictKind::pass; :>> judgedAgainst = "1b69544"; :>> judgedAt = "2026-08-15"; :>> judgedBy = "claudeOpus5"; }

    verification enStandupGate : Test { :>> id = "0d8001a1-0814-61a1-9b3e-0000003001a1"; :>> title = "Sprint 287 standup gate"; :>> createdAt = "2026-08-15"; :>> createdBy = "claudeOpus5"; :>> method = VerificationMethod::inspect; :>> procedureText = "Approach: non-interactive by design. The process permits an interactive answer, but an agent shell has no usable stdin, and a prompt that reads EOF and proceeds would DEFAULT precisely the fields that must never be defaulted — turning a safeguard into its opposite. Required arguments are the same explicitness by a different route. Test on a fresh `keel init` project rather than this repo, because 'a fresh clone reaches ready in one command' is the claim, and this repo is already enrolled. No blockers."; }
    part enStandupGateR1 : TestResult { :>> id = "0d8001a2-0814-61a2-9b3e-0000003001a2"; :>> outcome = VerdictKind::pass; :>> judgedAgainst = "1b69544"; :>> judgedAt = "2026-08-15"; :>> judgedBy = "claudeOpus5"; }

    verification enImplementGate : Test { :>> id = "0d8001a3-0814-61a3-9b3e-0000003001a3"; :>> title = "Sprint 287 implement gate"; :>> createdAt = "2026-08-15"; :>> createdBy = "claudeOpus5"; :>> method = VerificationMethod::test; :>> procedureText = "Order of operations is the substantive decision: the gate is verified FIRST, before the registry is touched. Registering and then discovering the gate is red would leave a contributor recorded as enrolled on a project they cannot actually be held to — and worse, the failure would look like a project problem rather than an enrollment one. Verified atomic: on a broken gate, exit 1 and ZERO entries written. Second decision: the machine binding is proven by asking `actor::resolve` what the write path would attribute to, rather than by trusting that the file was written. issue072 was exactly a capture step that printed an actor id which nothing consumed, so the write paths kept defaulting; asking the resolver is the only evidence the binding governs anything. It also catches a real case — a `KEEL_ACTOR` set in the shell OVERRIDES the file binding, and the command reports NOT READY naming that rather than silently enrolling into a different identity."; }
    part enImplementGateR1 : TestResult { :>> id = "0d8001a4-0814-61a4-9b3e-0000003001a4"; :>> outcome = VerdictKind::pass; :>> judgedAgainst = "1b69544"; :>> judgedAt = "2026-08-15"; :>> judgedBy = "claudeOpus5"; }

    verification enReviewGate : Test { :>> id = "0d8001a5-0814-61a5-9b3e-0000003001a5"; :>> title = "Sprint 287 review gate"; :>> createdAt = "2026-08-15"; :>> createdBy = "claudeOpus5"; :>> method = VerificationMethod::inspect; :>> procedureText = "Reviewed, and it closed a loop three sprints wide: D0146 is the FIRST proposed Decision this repo has carried, so `keel orient` now reports `pendingAcceptances: ['d0146']` — the surface built in sprint 284 against a repo that had zero proposed decisions, exercised for the first time by real work rather than by a temporary test. That is the strongest available evidence sprint 284 built the right thing: the case it was designed for arrived three sprints later and it reported it without any further edit. RESIDUAL, stated: enrollment does not record role, and the process step that requires it stays unsatisfiable until D0146 is decided either way. Both outcomes resolve it — accept and the schema grows the field, reject and the process step must be amended — and the current state is the only one that must not persist."; }
    part enReviewGateR1 : TestResult { :>> id = "0d8001a6-0814-61a6-9b3e-0000003001a6"; :>> outcome = VerdictKind::pass; :>> judgedAgainst = "1b69544"; :>> judgedAt = "2026-08-15"; :>> judgedBy = "claudeOpus5"; }

    verification enCloseOutGate : Test { :>> id = "0d8001a7-0814-61a7-9b3e-0000003001a7"; :>> title = "Sprint 287 closeOut gate (autonomous, D0049)"; :>> createdAt = "2026-08-15"; :>> createdBy = "claudeOpus5"; :>> method = VerificationMethod::inspect; :>> procedureText = "Autonomous closeOut (D0049). dcEnrollment carries a passing DoD TestResult; issue110 recorded and triaged to D0146, which is PROPOSED and awaits the human — an AI cannot sign off frozen core, and D0146 is not applied. Every VERIFY line demonstrated against a fresh `keel init` project. clippy clean; 179 tests; validate 309 clean; check-engine clean; 29 guards green. No gate bypassed."; }
    part enCloseOutGateR1 : TestResult { :>> id = "0d8001a8-0814-61a8-9b3e-0000003001a8"; :>> outcome = VerdictKind::pass; :>> judgedAgainst = "1b69544"; :>> judgedAt = "2026-08-15"; :>> judgedBy = "claudeOpus5"; }

    verification enRetroGate : Test { :>> id = "0d8001a9-0814-61a9-9b3e-0000003001a9"; :>> title = "Sprint 287 retro gate (autonomous, D0049)"; :>> createdAt = "2026-08-15"; :>> createdBy = "claudeOpus5"; :>> method = VerificationMethod::analyze; :>> procedureText = "Autonomous retro (D0049) under D0131's retroTrack. WELL: (1) the consumer check found the role gap BEFORE the command was written, which is the difference between recording an honest limitation and shipping role into a display-name string — the second would have been a dual-truth defect introduced while implementing the process that forbids it; (2) the Person and Actor branches were kept as separate code paths specifically so that the one error this module must never make cannot be a one-character bug, and the test asserts the absence of 'Person' in an AI declaration rather than only the presence of 'Actor'; (3) the gate is verified before the registry is touched, and the refusal was tested to be ATOMIC — a half-registered contributor on a red gate is worse than no enrollment. AVOIDABLE-ISSUE 1: I read exit codes through a pipe twice while testing refusals, printing `exit=0` where the command had actually returned 2 and 1, and had to re-run each directly to state the codes truthfully. The reports would have been WRONG had I not re-checked, and this is the same read-the-exit-code-not-the-output confusion as issue107, arriving from the opposite direction. NO NEW ITEM, reason stated: issue107 already names the class and its residual — that a summary I skim can differ from what actually happened — and this instance adds an operational rule rather than a new defect: never read an exit code through a pipe, since it belongs to the last command in the chain. Estimate 5 pts, delivered."; }
    part enRetroGateR1 : TestResult { :>> id = "0d8001aa-0814-61aa-9b3e-0000003001aa"; :>> outcome = VerdictKind::pass; :>> judgedAgainst = "1b69544"; :>> judgedAt = "2026-08-15"; :>> judgedBy = "claudeOpus5"; }
}
