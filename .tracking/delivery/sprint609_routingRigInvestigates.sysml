// ProjectDeliveryS609 — Sprint 609: Sprint 609 resolves issue392 under D0378 C, D0381 and D0382: the routing probe becomes an investigation rig with no standing number. It runs a named case several times, reports each sample's verdict and whether the samples agree, names a self-disagreeing case as a defect of the check to record as an Issue, records what the run cost as measured from the model's own receipts, and writes no rate, no indicator and no TestResult. The one-sample sweep that produced an authoritative-looking coverage number is gone, and dcSkillsRouteBehaviourally's criterion says so and why.. EXECUTE. 2 pts.
package ProjectDeliveryS609 {
    private import EngineElement::*;
    private import EngineWork::*;
    private import EngineVerification::*;
    private import EngineRelationships::*;

    #CharteredBy dependency from routingRigInvestigatesStory to d0378;

    part routingRigInvestigatesStory : Story {
        :>> id = "9f52588a-73f6-4007-a073-e9b3980847e6";
        :>> title = "Sprint 609: Sprint 609 resolves issue392 under D0378 C, D0381 and D0382: the routing probe becomes an investigation rig with no standing number. It runs a named case several times, reports each sample's verdict and whether the samples agree, names a self-disagreeing case as a defect of the check to record as an Issue, records what the run cost as measured from the model's own receipts, and writes no rate, no indicator and no TestResult. The one-sample sweep that produced an authoritative-looking coverage number is gone, and dcSkillsRouteBehaviourally's criterion says so and why. (2 pts)";
        :>> createdAt = "2026-09-08"; :>> createdBy = "claudeOpus5"; :>> kind = WorkKind::code; :>> priority = WorkPriority::p0; :>> owner = "claudeOpus5"; :>> estimatedPoints = 2;
    }

    action def DeliveryRunS609 {
        action storyRoutingRigInvestigates;
        verification storyRoutingRigInvestigatesDoD : Test { :>> id = "f243669c-efc5-4e69-b195-e9eb5825f64c"; :>> method = VerificationMethod::test; :>> procedureText = "DONE MEANS: `python .engine/tools/routing_probe.py --investigate <case> --samples 3` runs three samples of one authored prompt and prints per-sample verdicts, a one-line agree/disagree finding, and the measured spend; `--samples 1` is accepted but every non-routing verdict is printed as a suspicion, never a finding; a run with no --investigate and no --dry-run refuses and says why (D0378 C: no whole-set view); the output file holds the samples and the measured cost and nothing that reads as a coverage rate; a real investigation of the case issue392 named (release) was run and its receipt recorded on this sprint; dcSkillsRouteBehaviourally's DoD no longer asks for a published number; the instrument record says where the rig's output goes; keel guard ALL PASS."; }
        // RAN: python .engine/tools/routing_probe.py (no args) -> refusing: name the case(s) ... no whole-set sweep and no standing routing number (D0378 C) exit 1; --investigate release --dry-run -> estimate from the last measured run (per run 0.65 USD, 40s, measured 2026-09-08); --investigate release --samples 3 -> #1 WRONG intake 49.4s 0.635 USD, #2 ROUTED 35.7s 0.669 USD, #3 WRONG intake 35.6s 0.635 USD; finding: DISAGREES release: 1 routed, 2 wrong - the CHECK is the defect (D0381); spend 1.95 USD over 3 runs, 49s wall, measured per run 0.6489 USD 40.2s; wrote .keel/metrics/routing-investigation.json (kind investigation, no rate field); issue415 recorded against the check, resolver dcRoutingVerdictReadsTheWholeTurn; dcSkillsRouteBehaviourally DoD re-read: no published number; keel validate 693 clean; keel guard ALL PASS
        part storyRoutingRigInvestigatesDoDR1 : TestResult { :>> id = "969d3b74-b4d9-4fe4-b5c7-e98d5ee9849c"; :>> outcome = VerdictKind::pass; :>> judgedAgainst = "fe82629"; :>> judgedAt = "2026-09-08"; :>> judgedBy = "claudeOpus5"; }
    }

    verification routingRigInvestigatesRefineGate : Test { :>> id = "e052bef1-f262-49ae-9877-469bfce071ee"; :>> title = "Sprint 609 refine gate (DoR)"; :>> createdAt = "2026-09-08"; :>> createdBy = "claudeOpus5"; :>> method = VerificationMethod::inspect; :>> procedureText = "Scope: routing_probe.py (the CLI, the sampling loop, the finding lines, the output file, the docstring), the dcSkillsRouteBehaviourally criterion text, the snRoutingProbe comment in engine-instruments.sysml. No Rust, no schema. 2 points: a tool change plus one paid model run. DoR: estimatedPoints set; chartered to d0378; depends on d0381 and d0382, both accepted 2026-09-08; DoD above."; }
    // RAN: python .engine/tools/routing_probe.py (no args) -> refusing: name the case(s) ... no whole-set sweep and no standing routing number (D0378 C) exit 1; --investigate release --dry-run -> estimate from the last measured run (per run 0.65 USD, 40s, measured 2026-09-08); --investigate release --samples 3 -> #1 WRONG intake 49.4s 0.635 USD, #2 ROUTED 35.7s 0.669 USD, #3 WRONG intake 35.6s 0.635 USD; finding: DISAGREES release: 1 routed, 2 wrong - the CHECK is the defect (D0381); spend 1.95 USD over 3 runs, 49s wall, measured per run 0.6489 USD 40.2s; wrote .keel/metrics/routing-investigation.json (kind investigation, no rate field); issue415 recorded against the check, resolver dcRoutingVerdictReadsTheWholeTurn; dcSkillsRouteBehaviourally DoD re-read: no published number; keel validate 693 clean; keel guard ALL PASS
    part routingRigInvestigatesRefineGateR1 : TestResult { :>> id = "ea9a1b4d-5bb9-42af-a3de-6d5331af3e43"; :>> outcome = VerdictKind::pass; :>> judgedAgainst = "fe82629"; :>> judgedAt = "2026-09-08"; :>> judgedBy = "claudeOpus5"; }
    verification routingRigInvestigatesStandupGate : Test { :>> id = "01d7aee7-d0a5-4ae0-b28a-d28000bc6ca2"; :>> title = "Sprint 609 standup gate"; :>> createdAt = "2026-09-08"; :>> createdBy = "claudeOpus5"; :>> method = VerificationMethod::inspect; :>> procedureText = "Plan: (1) rewrite the probe's entry point around --investigate and --samples, keeping load_cases, claude_exe, probe_settings and run_one; (2) --dry-run lists the cases named, the estimate from the last measured run, and cases naming an undeployed skill; (3) run the release case three times for real and read the cost from the result events; (4) amend the criterion and the instrument comment; (5) record the receipt and close."; }
    // RAN: python .engine/tools/routing_probe.py (no args) -> refusing: name the case(s) ... no whole-set sweep and no standing routing number (D0378 C) exit 1; --investigate release --dry-run -> estimate from the last measured run (per run 0.65 USD, 40s, measured 2026-09-08); --investigate release --samples 3 -> #1 WRONG intake 49.4s 0.635 USD, #2 ROUTED 35.7s 0.669 USD, #3 WRONG intake 35.6s 0.635 USD; finding: DISAGREES release: 1 routed, 2 wrong - the CHECK is the defect (D0381); spend 1.95 USD over 3 runs, 49s wall, measured per run 0.6489 USD 40.2s; wrote .keel/metrics/routing-investigation.json (kind investigation, no rate field); issue415 recorded against the check, resolver dcRoutingVerdictReadsTheWholeTurn; dcSkillsRouteBehaviourally DoD re-read: no published number; keel validate 693 clean; keel guard ALL PASS
    part routingRigInvestigatesStandupGateR1 : TestResult { :>> id = "d5a2926d-57b9-42b8-83da-7eeee49a2853"; :>> outcome = VerdictKind::pass; :>> judgedAgainst = "fe82629"; :>> judgedAt = "2026-09-08"; :>> judgedBy = "claudeOpus5"; }
    verification routingRigInvestigatesImplementGate : Test { :>> id = "a1ac72c3-d999-4116-af0b-e855b3b12943"; :>> title = "Sprint 609 implement gate"; :>> createdAt = "2026-09-08"; :>> createdBy = "claudeOpus5"; :>> method = VerificationMethod::test; :>> procedureText = "RAN: Write on .engine/tools/routing_probe.py; python .engine/tools/routing_probe.py (no args) -> refused with the D0378 C reason; --dry-run --investigate release; --investigate release --samples 3 against a real model; the receipt is the RAN line on this sprint's results."; }
    // RAN: python .engine/tools/routing_probe.py (no args) -> refusing: name the case(s) ... no whole-set sweep and no standing routing number (D0378 C) exit 1; --investigate release --dry-run -> estimate from the last measured run (per run 0.65 USD, 40s, measured 2026-09-08); --investigate release --samples 3 -> #1 WRONG intake 49.4s 0.635 USD, #2 ROUTED 35.7s 0.669 USD, #3 WRONG intake 35.6s 0.635 USD; finding: DISAGREES release: 1 routed, 2 wrong - the CHECK is the defect (D0381); spend 1.95 USD over 3 runs, 49s wall, measured per run 0.6489 USD 40.2s; wrote .keel/metrics/routing-investigation.json (kind investigation, no rate field); issue415 recorded against the check, resolver dcRoutingVerdictReadsTheWholeTurn; dcSkillsRouteBehaviourally DoD re-read: no published number; keel validate 693 clean; keel guard ALL PASS
    part routingRigInvestigatesImplementGateR1 : TestResult { :>> id = "da3c912f-439a-4cf4-a913-6a1d0fbe78d1"; :>> outcome = VerdictKind::pass; :>> judgedAgainst = "fe82629"; :>> judgedAt = "2026-09-08"; :>> judgedBy = "claudeOpus5"; }
    verification routingRigInvestigatesReviewGate : Test { :>> id = "17a0833a-7667-4321-9495-c219e04fb89f"; :>> title = "Sprint 609 review gate — three passes per D0172"; :>> createdAt = "2026-09-08"; :>> createdBy = "claudeOpus5"; :>> method = VerificationMethod::inspect; :>> procedureText = "Reviewed against the DoD: the refusal fires with no --investigate; the one-sample path labels a non-route as suspicion; the finding for a mixed case names the check and cites D0381; the output file carries samples, verdicts and measured spend and no rate field; the criterion and instrument comment were re-read after the edit."; }
    // RAN: python .engine/tools/routing_probe.py (no args) -> refusing: name the case(s) ... no whole-set sweep and no standing routing number (D0378 C) exit 1; --investigate release --dry-run -> estimate from the last measured run (per run 0.65 USD, 40s, measured 2026-09-08); --investigate release --samples 3 -> #1 WRONG intake 49.4s 0.635 USD, #2 ROUTED 35.7s 0.669 USD, #3 WRONG intake 35.6s 0.635 USD; finding: DISAGREES release: 1 routed, 2 wrong - the CHECK is the defect (D0381); spend 1.95 USD over 3 runs, 49s wall, measured per run 0.6489 USD 40.2s; wrote .keel/metrics/routing-investigation.json (kind investigation, no rate field); issue415 recorded against the check, resolver dcRoutingVerdictReadsTheWholeTurn; dcSkillsRouteBehaviourally DoD re-read: no published number; keel validate 693 clean; keel guard ALL PASS
    part routingRigInvestigatesReviewGateR1 : TestResult { :>> id = "4153bdd0-6ad4-430b-b003-a5f4a24d8559"; :>> outcome = VerdictKind::pass; :>> judgedAgainst = "fe82629"; :>> judgedAt = "2026-09-08"; :>> judgedBy = "claudeOpus5"; }
    verification routingRigInvestigatesCloseOutGate : Test { :>> id = "e6d3dd42-52dc-41f9-8744-05f0dade48d2"; :>> title = "Sprint 609 closeOut gate (autonomous, D0049)"; :>> createdAt = "2026-09-08"; :>> createdBy = "claudeOpus5"; :>> method = VerificationMethod::inspect; :>> procedureText = "Sprint 609 closes when dcRoutingNumberIsStableDoD carries a pass at the commit that carries the rig, and issue392 leaves keel show open-issues."; }
    // RAN: python .engine/tools/routing_probe.py (no args) -> refusing: name the case(s) ... no whole-set sweep and no standing routing number (D0378 C) exit 1; --investigate release --dry-run -> estimate from the last measured run (per run 0.65 USD, 40s, measured 2026-09-08); --investigate release --samples 3 -> #1 WRONG intake 49.4s 0.635 USD, #2 ROUTED 35.7s 0.669 USD, #3 WRONG intake 35.6s 0.635 USD; finding: DISAGREES release: 1 routed, 2 wrong - the CHECK is the defect (D0381); spend 1.95 USD over 3 runs, 49s wall, measured per run 0.6489 USD 40.2s; wrote .keel/metrics/routing-investigation.json (kind investigation, no rate field); issue415 recorded against the check, resolver dcRoutingVerdictReadsTheWholeTurn; dcSkillsRouteBehaviourally DoD re-read: no published number; keel validate 693 clean; keel guard ALL PASS
    part routingRigInvestigatesCloseOutGateR1 : TestResult { :>> id = "f769dee7-5d42-4d38-bf66-f3ba9fdfd6f3"; :>> outcome = VerdictKind::pass; :>> judgedAgainst = "fe82629"; :>> judgedAt = "2026-09-08"; :>> judgedBy = "claudeOpus5"; }
    verification routingRigInvestigatesRetroGate : Test { :>> id = "feb25b6d-e1e6-434e-99bb-ad05b0d8da73"; :>> title = "Sprint 609 retro gate (autonomous, D0049)"; :>> createdAt = "2026-09-08"; :>> createdBy = "claudeOpus5"; :>> method = VerificationMethod::analyze; :>> procedureText = "Retro held; avoidable-issue scan: one finding surfaced while this sprint was open - the rig's first investigation (release x3: 1 routed, 2 wrong via intake) showed the check itself at fault, since intake is declared to run first on any human direction and the rig scored the first Skill call; tracked in this commit as issue415 with the new backlog item dcRoutingVerdictReadsTheWholeTurn. Process improvement: none beyond D0381/D0382 - the finding took the D0381 path (an Issue against the check, no averaging) on its first use."; }
    // RAN: python .engine/tools/routing_probe.py (no args) -> refusing: name the case(s) ... no whole-set sweep and no standing routing number (D0378 C) exit 1; --investigate release --dry-run -> estimate from the last measured run (per run 0.65 USD, 40s, measured 2026-09-08); --investigate release --samples 3 -> #1 WRONG intake 49.4s 0.635 USD, #2 ROUTED 35.7s 0.669 USD, #3 WRONG intake 35.6s 0.635 USD; finding: DISAGREES release: 1 routed, 2 wrong - the CHECK is the defect (D0381); spend 1.95 USD over 3 runs, 49s wall, measured per run 0.6489 USD 40.2s; wrote .keel/metrics/routing-investigation.json (kind investigation, no rate field); issue415 recorded against the check, resolver dcRoutingVerdictReadsTheWholeTurn; dcSkillsRouteBehaviourally DoD re-read: no published number; keel validate 693 clean; keel guard ALL PASS
    part routingRigInvestigatesRetroGateR1 : TestResult { :>> id = "0f4d3b4d-3561-4753-bf4a-3c4fc7fa1ee1"; :>> outcome = VerdictKind::pass; :>> judgedAgainst = "fe82629"; :>> judgedAt = "2026-09-08"; :>> judgedBy = "claudeOpus5"; }
}
