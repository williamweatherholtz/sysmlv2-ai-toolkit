// ProjectDeliveryS681 — Sprint 681: The record sub-verbs become control actions. The D0451 fold collapsed seven never-analysed write paths into one computed action (issue497, sprint 680 retro); under D0454 the control structure derives one action per sub-verb of a routing write command from the fact's own invocation, and stpa-self run 4 analyses the thirteen keel record sub-verbs it exposes - so the D0452 and D0453 folds land on a structure that grows when a verb moves under a router instead of hiding it.. EXECUTE. 5 pts.
package ProjectDeliveryS681 {
    private import EngineElement::*;
    private import EngineWork::*;
    private import EngineVerification::*;
    private import EngineRelationships::*;

    #CharteredBy dependency from recordSubVerbsAreControlActionsStory to d0454;

    part recordSubVerbsAreControlActionsStory : Story {
        :>> id = "ee2e18b4-42d3-4ab3-a1af-94334f58ba12";
        :>> title = "Sprint 681: The record sub-verbs become control actions. The D0451 fold collapsed seven never-analysed write paths into one computed action (issue497, sprint 680 retro); under D0454 the control structure derives one action per sub-verb of a routing write command from the fact's own invocation, and stpa-self run 4 analyses the thirteen keel record sub-verbs it exposes - so the D0452 and D0453 folds land on a structure that grows when a verb moves under a router instead of hiding it. (5 pts)";
        :>> createdAt = "2026-09-12"; :>> createdBy = "claudeFable5"; :>> kind = WorkKind::code; :>> priority = WorkPriority::p0; :>> owner = "claudeFable5"; :>> estimatedPoints = 5;
    }

    action def DeliveryRunS681 {
        action storyRecordSubVerbsAreControlActions;
        verification storyRecordSubVerbsAreControlActionsDoD : Test { :>> id = "508580f7-3cf2-4541-9f6d-d665e22d1fe6"; :>> method = VerificationMethod::test; :>> procedureText = "DELIVERED: keel show control-structure lists cmdRecordDecision, cmdRecordIssue, cmdRecordStatement, cmdRecordStory, cmdRecordTask, cmdRecordSprint, cmdRecordResult, cmdRecordGateResult, cmdRecordReview, cmdRecordMeasurement, cmdRecordIndicatorSnapshot, cmdRecordReverify and cmdRecordMint, no bare cmdRecord, and the same rule gives 8 cmdProcess* and 3 cmdLibrary* (63 actions where the fold left 42); the sub-verb reader is one function (cli_facts::sub_verb_segments) read by the structure and by the_record_sub_verbs_match_the_fact; a control_structure.rs unit test holds a three-segment fixture to three actions and a plain one to one; stpa-self run 4 is recorded in engine-ucas.sysml with ANALYSED: naming all thirteen, five new UCAs bound to controls or Issues, run 1's cmdRecord / cmdAppendResult records carried by name; keel guard stpa-currency names none of the thirteen; every finding of the run is a tracked Issue with a resolver."; }
        // RAN: keel show control-structure . on the sprint build (cs681_final.json): 63 actions, 44 of them cmd* (the VERIFIER counted that subset), exactly the 13 cmdRecord* present (cmdRecordDecision, cmdRecordGateResult, cmdRecordIndicatorSnapshot, cmdRecordIssue, cmdRecordMeasurement, cmdRecordMint, cmdRecordResult, cmdRecordReverify, cmdRecordReview, cmdRecordSprint, cmdRecordStatement, cmdRecordStory, cmdRecordTask), none of cmdRecord / cmdProcess / cmdLibrary; cargo test --release -p keel-cli --lib sub_verb_tests 3 passed, control_structure 11 passed incl. a_routing_write_command_is_one_action_per_sub_verb; --test control_structure_is_computed 3 passed; --test capability_refusal_bites 6 passed (the_record_sub_verbs_match_the_fact reads cli_facts::sub_verbs_of); keel guard stpa-currency --no-receipt .: 41 of 62 open, none of the 13 in OPEN EDGES; engine-ucas.sysml stpaRun4 ANALYSED: names all 13, stpaRun4R1 pass at 76b106e; keel guard issues --no-receipt .: PASS 510 scanned after the four resolver DoDs named issue498-501; keel suite --touched: pass 619 / 0 failed in 252s, stems cli_facts control_structure guards, at 1789180957 > launch 1789180701
        part storyRecordSubVerbsAreControlActionsDoDR1 : TestResult { :>> id = "4f8e533e-aef8-4536-bfa7-3420f94c5b85"; :>> outcome = VerdictKind::pass; :>> judgedAgainst = "76b106e"; :>> judgedAt = "2026-09-12"; :>> judgedBy = "claudeFable5"; }
    }

    verification recordSubVerbsAreControlActionsRefineGate : Test { :>> id = "986b5a05-782e-4d57-94a0-18907c923945"; :>> title = "Sprint 681 refine gate (DoR)"; :>> createdAt = "2026-09-12"; :>> createdBy = "claudeFable5"; :>> method = VerificationMethod::inspect; :>> procedureText = "Chartered by D0454 (proposed - it carries the process-change marker because guards.rs, the shared CLI-fact reader, is on the enforcement surface; HELD for the human under D0337, no plan cover). Resolver of issue497, moved under D0052 to sit directly after dcRemainingCliFamilies in EngineBuild, the program it unblocks. Five points: a derivation change with one shared reader and four test surfaces, plus a full stpa-self run over thirteen actions with the code read behind each claim. DoR: DoD in the backlog (amended by its owner this sprint for the cmdRecordMint clause - no declared fact says a sub-verb writes nothing, so it is emitted and recorded considered-safe, issue501); no blocking dependency; the D0388 pair chosen before the tree was read - positive: the live record fact yields exactly the thirteen sub-verbs in fact order; negative: claim's `<item> | --list | --mine` yields none and no bare router action exists."; }
    // RAN: keel show whats-next . before the reorder; reorder681.py moved dcRecordSubVerbsAreControlActions under dcRemainingCliFamiliesDoD (2 insertions / 2 deletions, validate 778 clean); keel record decision --from draft_d0454.md: recorded D0454 proposed, HELD outside standing consent (D0337, process-change marker); DependsOn d0284 / d0451 appended, check-engine clean; estimatedPoints 5; CharteredBy d0454 at sprint681_recordSubVerbsAreControlActions.sysml:8; the D0388 pair named in the gate text before the tree was read
    part recordSubVerbsAreControlActionsRefineGateR1 : TestResult { :>> id = "ff3e8a40-35d0-4817-b8f1-3f6e41af2136"; :>> outcome = VerdictKind::proposed; :>> judgedAgainst = "76b106e"; :>> judgedAt = "2026-09-12"; :>> judgedBy = "claudeFable5"; }
    verification recordSubVerbsAreControlActionsStandupGate : Test { :>> id = "310c4edd-bb33-4b34-a5f5-c392b0c4f545"; :>> title = "Sprint 681 standup gate"; :>> createdAt = "2026-09-12"; :>> createdBy = "claudeFable5"; :>> method = VerificationMethod::inspect; :>> procedureText = "Order: reorder the backlog first (reorder681.py, 2 insertions / 2 deletions, validate 778 clean) so the frontier says what is being worked; capture the pre-change structure (cs681_before.json, 42 actions); write sub_verb_segments with its three unit tests and fix the classifier when `--task` counted as a verb (first char must be lowercase); carry invocation into AuthoredCliFact; derive the actions; rewrite the two integration asserts against the new names; rebuild and refresh keel-serve.exe; read the structure back (cs681_after.json, 63 actions); then and only then the run: census read first (stpa2b), code read before every UCA, UCAs, constraints, two controls declared in control-map, the run record, the guard read back."; }
    // RAN: cs681_before.json: 42 actions on the D0451 build before any edit; subverbs681.py: sub_verb_segments + sub_verbs_of + 3 unit tests written first, the --task-as-verb classifier defect found by the fixture and fixed (bare lowercase first char); cargo build --release -p keel-cli then cp to keel-serve.exe; cs681_after.json: 63 actions; stpa2b census (census681.json) read before the run: 87 controls / 2 / 60 / 25, 16 UCAs 5 open 11 bound, 9 removal candidates
    part recordSubVerbsAreControlActionsStandupGateR1 : TestResult { :>> id = "090d7c79-cd14-4d65-ae17-9c349df518da"; :>> outcome = VerdictKind::proposed; :>> judgedAgainst = "76b106e"; :>> judgedAt = "2026-09-12"; :>> judgedBy = "claudeFable5"; }
    verification recordSubVerbsAreControlActionsImplementGate : Test { :>> id = "dda7a31d-57f9-40b9-815e-1b0fda2c0ce8"; :>> title = "Sprint 681 implement gate"; :>> createdAt = "2026-09-12"; :>> createdBy = "claudeFable5"; :>> method = VerificationMethod::test; :>> procedureText = "keel-cli/src/cli_facts.rs: sub_verb_segments (routing invocation = opens with a bare lowercase token, `|` separates two or more such segments; a flag, placeholder or bracket segment continues the sub-verb before it) and sub_verbs_of; mod sub_verb_tests (3). keel-cli/src/guards.rs: AuthoredCliFact.invocation from the fact. keel-cli/src/view/control_structure.rs: the writes/both arm emits one Action per segment, cmd<Command><SubVerb>, title `keel <command> <sub-verb>`, the segment as data; unit test a_routing_write_command_is_one_action_per_sub_verb. keel-cli/tests/control_structure_is_computed.rs:74 asserts cmdRecordTask present and cmdRecord absent (D0454); keel-cli/tests/capability_refusal_bites.rs the_record_sub_verbs_match_the_fact reads sub_verbs_of. .tracking/architecture/engine-ucas.sysml: run 4 - UCA-RS1, UCA-RB1, UCA-RV1, UCA-RV2, UCA-RR1, CC-RS1, CC-RB1, CC-RV1, CC-RV2, CC-RR1, stpaRun4 + result. .tracking/architecture/control-map.sysml: ctlResultBinding (ehz4), ctlHumanJudgmentAsk (ehz3, ehz7). Backlog: four resolver tasks in NextWork; issues 498-501 with #Resolves edges. .engine/decisions/0454 with DependsOn d0284, d0451."; }
    // RAN: cargo clippy --release -p keel-cli --all-targets -- -D warnings: pass; cargo test --release -p keel-cli --lib sub_verb_tests 3 passed, control_structure 11 passed; --test control_structure_is_computed 3 passed; --test capability_refusal_bites 6 passed; keel suite --touched: pass 619 passed 0 failed 252s, changed set cli_facts.rs control_structure.rs guards.rs capability_refusal_bites.rs control_structure_is_computed.rs MATCH; keel validate . 779 clean after the sprint file; keel check-engine . clean; git show ceaabdd 76b106e -- .tracking: 15 records createdBy claudeOpus5 under Fable 5 trailers (the UCA-RB1 incident); reverify.rs 365 read for UCA-RV2; write.rs 526-544 WRITE_OPS read for UCA-RR1
    part recordSubVerbsAreControlActionsImplementGateR1 : TestResult { :>> id = "79c0f632-e4f6-4cc2-819e-c148085e5f06"; :>> outcome = VerdictKind::pass; :>> judgedAgainst = "76b106e"; :>> judgedAt = "2026-09-12"; :>> judgedBy = "claudeFable5"; }
    verification recordSubVerbsAreControlActionsReviewGate : Test { :>> id = "fca090a8-6f80-4a42-92cf-34e338f1163a"; :>> title = "Sprint 681 review gate — three passes per D0172"; :>> createdAt = "2026-09-12"; :>> createdBy = "claudeFable5"; :>> method = VerificationMethod::inspect; :>> procedureText = "Read back, not asserted: keel show control-structure . 63 actions, the thirteen cmdRecord* present, no cmdRecord / cmdProcess / cmdLibrary, stepTwoGate 8 of 8; keel guard stpa-currency --no-receipt . WARN 41 of 62 open (was 54 of 62 on the D0454 tree before the run, 32 of 41 before D0454), OPEN EDGES naming none of the thirteen; validate 778 clean; check-engine clean; ownership PASS 1804 after the owner's DoD amendment; cargo test -p keel-cli --lib control_structure 11 passed, sub_verb_tests 3 passed, --test control_structure_is_computed 3 passed, --test capability_refusal_bites 6 passed; clippy -D warnings clean. The run's five UCAs each name the code line the claim rests on and one (UCA-RB1) an observed incident verified by git show before it was written."; }
    // RAN: VERIFIER receipt (verify681/): validate 778 clean, check-engine clean, sync-claude --check matches 46 skills, clippy pass, probe pair positive 3 + 11 passed, negative no forbidden names and exactly 13 cmdRecord*, stpa-currency 41 of 62 none of the 13; its one discrepancy - guard:issues FAIL 4 (resolvers not naming issue498-501) - was fixed at the record (name_issues.py, 4 DoDs) and read back PASS 510 scanned 0 violations, ownership PASS 1804, keel guard --no-receipt . ALL PASS
    part recordSubVerbsAreControlActionsReviewGateR1 : TestResult { :>> id = "5374c196-04d0-4fcc-9537-d0ec168dc2a8"; :>> outcome = VerdictKind::proposed; :>> judgedAgainst = "76b106e"; :>> judgedAt = "2026-09-12"; :>> judgedBy = "claudeFable5"; }
    verification recordSubVerbsAreControlActionsCloseOutGate : Test { :>> id = "668f27b3-b28c-476d-923d-be04c7576c4c"; :>> title = "Sprint 681 closeOut gate (autonomous, D0049)"; :>> createdAt = "2026-09-12"; :>> createdBy = "claudeFable5"; :>> method = VerificationMethod::inspect; :>> procedureText = "Sprint 681 closes on the VERIFIER receipt (haiku, skill test-verify, D0438, verify681/): keel suite --touched detached with the receipt read after exit, validate, check-engine, guard --no-receipt, sync-claude --check, clippy, and the D0388 pair as dispatched; the DoD result and every gate result carry their RAN receipts (D0424); D0454 stays proposed in the authority queue with D0452 and D0453 - the folds that need this rule wait on all three."; }
    // RAN: keel guard --no-receipt . ALL PASS after the resolver fix; keel sync-claude . stamped 0.4.1 76b106e, --check matches; git status: 10 modified + 2 untracked, no .keel/ path staged; keel show authority-queue: d0452, d0453, d0454 pending for the human; touched receipt at=1789180957 read after cargo exit (D0387)
    part recordSubVerbsAreControlActionsCloseOutGateR1 : TestResult { :>> id = "32321716-e2b4-48d3-9ff9-a6ed550f148c"; :>> outcome = VerdictKind::proposed; :>> judgedAgainst = "76b106e"; :>> judgedAt = "2026-09-12"; :>> judgedBy = "claudeFable5"; }
    verification recordSubVerbsAreControlActionsRetroGate : Test { :>> id = "4d77e2f5-b60d-49cf-a4ee-de313797df7a"; :>> title = "Sprint 681 retro gate (autonomous, D0049)"; :>> createdAt = "2026-09-12"; :>> createdBy = "claudeFable5"; :>> method = VerificationMethod::analyze; :>> procedureText = "AVOIDABLE-ISSUE SCAN: four findings, four tracked. FINDING 1: the session's actor binding named claudeOpus5 under a Fable 5 prompt - ceaabdd and 76b106e carry 15 records attributed to a model that was not running (verified by git show against the trailers before the claim) - issue498, resolver dcSessionActorFollowsTheModel; rebound for this session before the first run-4 record. FINDING 2: a chat Statement typed by the AI reads with a speaker's authority - issue499, resolver dcChatStatementsAwaitTheirSpeaker. FINDING 3: record reverify stamps judgedAt with HEAD's commit date (reverify.rs 365) - issue500, resolver dcReverifyStampsTheRunDate. FINDING 4: sub-verbs inherit the router's single effect, so four process reads and record mint are write actions - issue501, resolver dcSubVerbEffectIsDeclared (a Change Request: cli.sysml is engine schema). FINDING 5 (tooling, fixed at the root in the sprint): textpatch insert-after with a prefix anchor splits the anchor line mid-line - the control-map insert landed inside ctlHeredocBackslash's line and was rejoined by rejoin_ctl.py; validate did not see it because SysML is whitespace-insensitive; no new item - the existing guidance (an anchor is a whole line) held, the operator erred; recurrence would make it an Issue. CARRY: the eleven cmdProcess* / cmdLibrary* actions stay unanalysed until issue501 settles which of them write."; }
    // RAN: keel show open-issues . (oi.json): issue498-501 open, each with one resolver of kind task, complete false; keel guard issues --no-receipt .: PASS after the four DoDs named their issue (the D0304 control caught the omission at the stop hook - control held, no new item); keel guard retro-backlog --no-receipt . run below in the same script
    part recordSubVerbsAreControlActionsRetroGateR1 : TestResult { :>> id = "3b2cd1ca-b5e4-40f9-bd32-e1c5ec763450"; :>> outcome = VerdictKind::proposed; :>> judgedAgainst = "76b106e"; :>> judgedAt = "2026-09-12"; :>> judgedBy = "claudeFable5"; }
}
