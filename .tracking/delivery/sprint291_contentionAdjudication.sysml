// ProjectDeliveryS291 — Sprint 291: `keel record issue` + a computed contention view — the sanctioned
// path D0108 clause 5 mandates and nothing implemented (dcContentionAdjudication, D0129). EXECUTE. 5 pts.
package ProjectDeliveryS291 {
    private import EngineElement::*;
    private import EngineWork::*;
    private import EngineVerification::*;
    private import EngineRelationships::*;

    #CharteredBy dependency from contentionStory to d0144;

    part contentionStory : Story {
        :>> id = "0d8001dd-0814-61dd-9b3e-0000003001dd";
        :>> title = "Sprint 291: record issue + contentions — the mandated path gets an implementation (5 pts)";
        :>> createdAt = "2026-08-15"; :>> createdBy = "claudeOpus5"; :>> kind = WorkKind::code; :>> priority = WorkPriority::p0; :>> owner = "claudeOpus5"; :>> estimatedPoints = 5;
    }

    action def DeliveryRunS291 {
        action storyContention;
        verification storyContentionDoD : Test { :>> id = "0d8001de-0814-61de-9b3e-0000003001de"; :>> method = VerificationMethod::demo; :>> procedureText = "Delivers dcContentionAdjudication (srDcContentionAdjudication, D0129). D0108 clause 5 MANDATES that conflicting conclusions across contributors be recorded as an Issue for human adjudication with neither side silently winning — and there was no command that records an Issue at all: `record decision` existed, `record issue` did not, so the sanctioned path was reachable only by hand-editing a 1300-line file. A mandated path with no implementation is the friction that guarantees non-compliance (D0054). DELIVERED (a) `keel record issue --title --description --severity --resolver --date [--related-task] [--marker] [--in-field] [--by]`, producing a TRIAGED Issue plus its `#Resolves` edge in one call — triage-on-arrival because the `issues` guard fails on an untriaged Issue, so a command that omitted it would hand the caller a red gate as its output. It REFUSES on an unknown `--resolver` rather than authoring a dangling edge, since the guard is satisfied by the edge's PRESENCE and would read as triaged while resolving nothing (issue109). (b) `keel contentions`, computing contradictory judgments (one verification with passing and failing results from DIFFERENT actors) and rival proposals (two still-`proposed` Decisions resolving the same Issue). VERIFIED END TO END: `record issue` produced issue113, validate 313 clean and all 29 guards exit 0 in one call, then reverted; an unknown resolver and an invalid severity each refuse with exit 2; a synthesized contradiction appears as `contradictoryJudgment probeV passedBy claudeOpus5 failedBy claudeSonnet46`; a synthesized second proposed Decision on issue111 appears as `rivalProposals`; and the SAME actor re-judging its own work does NOT appear, because that is ordinary re-verification and counting it would flood the view. clippy clean; 134 lib tests."; }
        part storyContentionDoDR1 : TestResult { :>> id = "0d8001df-0814-61df-9b3e-0000003001df"; :>> outcome = VerdictKind::pass; :>> judgedAgainst = "c400309"; :>> judgedAt = "2026-08-15"; :>> judgedBy = "claudeOpus5"; }
    }

    verification caRefineGate : Test { :>> id = "0d8001e0-0814-61e0-9b3e-0000003001e0"; :>> title = "Sprint 291 refine gate (DoR)"; :>> createdAt = "2026-08-15"; :>> createdBy = "claudeOpus5"; :>> method = VerificationMethod::inspect; :>> procedureText = "DoR. CONSUMER CHECK (dorConsumer, D0144): the consumer of a newly recorded Issue is the `issues` guard, which fails on an untriaged one — so `--resolver` is REQUIRED rather than optional, and the check of whether it exists happens before the write rather than after. The consumer of the contention view is a human adjudicator, which is why each row names the SUBJECT and the contending actors rather than just a count. One dimension of the item is not computable — see the implement gate. estimatedPoints=5. DoR met."; }
    part caRefineGateR1 : TestResult { :>> id = "0d8001e1-0814-61e1-9b3e-0000003001e1"; :>> outcome = VerdictKind::pass; :>> judgedAgainst = "c400309"; :>> judgedAt = "2026-08-15"; :>> judgedBy = "claudeOpus5"; }

    verification caStandupGate : Test { :>> id = "0d8001e2-0814-61e2-9b3e-0000003001e2"; :>> title = "Sprint 291 standup gate"; :>> createdAt = "2026-08-15"; :>> createdBy = "claudeOpus5"; :>> method = VerificationMethod::inspect; :>> procedureText = "Approach: synthesize each contention dimension against the REAL tree and then remove the probe, rather than unit-testing the predicate alone — a view that finds nothing is indistinguishable from a view that cannot find anything, and only a positive case separates them. Also test the NEGATIVE case explicitly (same actor, different outcomes), because a contention view that fires on ordinary re-verification would be abandoned within a day. No blockers."; }
    part caStandupGateR1 : TestResult { :>> id = "0d8001e3-0814-61e3-9b3e-0000003001e3"; :>> outcome = VerdictKind::pass; :>> judgedAgainst = "c400309"; :>> judgedAt = "2026-08-15"; :>> judgedBy = "claudeOpus5"; }

    verification caImplementGate : Test { :>> id = "0d8001e4-0814-61e4-9b3e-0000003001e4"; :>> title = "Sprint 291 implement gate"; :>> createdAt = "2026-08-15"; :>> createdBy = "claudeOpus5"; :>> method = VerificationMethod::test; :>> procedureText = "The item names THREE contention dimensions and only two are computable. The third — two live CLAIMS on one item — has no `Claim` type to read, and D0147 proposing one is itself awaiting human sign-off. It is reported in a `notComputed` block WITH the reason rather than omitted, because a view listing two of three dimensions and saying nothing about the third reads as 'no claim contentions exist'. That is the D0138 lesson and the same reason `orient` emits an empty `pendingAcceptances` rather than dropping the key. Also: I wrote `.map_or(None, |_| None)` for two optional fields — it type-checked, built clean, and would have silently DISCARDED `--related-task` and `--marker` whenever a caller passed them. Caught by reading what I had written rather than by any check, which is the honest account: nothing in the toolchain would have flagged it."; }
    part caImplementGateR1 : TestResult { :>> id = "0d8001e5-0814-61e5-9b3e-0000003001e5"; :>> outcome = VerdictKind::pass; :>> judgedAgainst = "c400309"; :>> judgedAt = "2026-08-15"; :>> judgedBy = "claudeOpus5"; }

    verification caReviewGate : Test { :>> id = "0d8001e6-0814-61e6-9b3e-0000003001e6"; :>> title = "Sprint 291 review gate"; :>> createdAt = "2026-08-15"; :>> createdBy = "claudeOpus5"; :>> method = VerificationMethod::inspect; :>> procedureText = "Reviewed. The issue NUMBERING is max+1 rather than count+1, and the unit test says why: counting collides the moment an issue is removed or numbered out of order, and a duplicate id is its own corruption class (issue074). The same test asserts that `issue900` mentioned inside a description string does NOT drive the counter — the self-referential-corpus trap that inflated the marker census in issue099, now guarded against at the point where a new one would be minted. Doc-sync caught in passing: `.tracking/issues.sysml`'s own header still told the reader to surface issues with `python .engine/tools/query.py issues`, retired at D0074."; }
    part caReviewGateR1 : TestResult { :>> id = "0d8001e7-0814-61e7-9b3e-0000003001e7"; :>> outcome = VerdictKind::pass; :>> judgedAgainst = "c400309"; :>> judgedAt = "2026-08-15"; :>> judgedBy = "claudeOpus5"; }

    verification caCloseOutGate : Test { :>> id = "0d8001e8-0814-61e8-9b3e-0000003001e8"; :>> title = "Sprint 291 closeOut gate (autonomous, D0049)"; :>> createdAt = "2026-08-15"; :>> createdBy = "claudeOpus5"; :>> method = VerificationMethod::inspect; :>> procedureText = "Autonomous closeOut (D0049). dcContentionAdjudication carries a passing DoD TestResult. Both computable dimensions demonstrated with synthesized positives and a negative; the third reported as not-computed with its reason. clippy clean; 134 lib tests; validate 313 clean; check-engine clean; 29 guards green. No gate bypassed, and every probe was reverted — the repo carries no synthetic contention."; }
    part caCloseOutGateR1 : TestResult { :>> id = "0d8001e9-0814-61e9-9b3e-0000003001e9"; :>> outcome = VerdictKind::pass; :>> judgedAgainst = "c400309"; :>> judgedAt = "2026-08-15"; :>> judgedBy = "claudeOpus5"; }

    verification caRetroGate : Test { :>> id = "0d8001ea-0814-61ea-9b3e-0000003001ea"; :>> title = "Sprint 291 retro gate (autonomous, D0049)"; :>> createdAt = "2026-08-15"; :>> createdBy = "claudeOpus5"; :>> method = VerificationMethod::analyze; :>> procedureText = "Autonomous retro (D0049) under D0131's retroTrack. WELL: (1) the NEGATIVE case was tested as deliberately as the positives — same actor, different outcomes must not register, because a contention view that fires on ordinary re-verification is abandoned within a day and then the mandate has an implementation nobody runs, which is barely better than none; (2) the uncomputable third dimension is reported as uncomputable rather than omitted, so the view cannot be misread as a clean bill; (3) `--resolver` is required and checked BEFORE the write, so the command cannot produce the untriaged Issue its own guard rejects. AVOIDABLE-ISSUE 1: I wrote `.map_or(None, |_| None)` for two optional fields. It compiled, passed clippy, and would have silently dropped `--related-task` and `--marker`. NOTHING IN THE TOOLCHAIN WOULD HAVE CAUGHT IT — no test exercised those flags, and the types were satisfied — so the honest account is that I found it by re-reading my own expression, not by any control. NO NEW ITEM, reason stated: the general defect is 'an optional argument silently discarded', and the only real control is a test per flag; recording a backlog item to test every optional flag on every command would be process theatre. What is actionable and done: the two flags now bind to locals, and the pattern is named here so the next reviewer of a `NewX` struct literal knows to check that every field is actually threaded. Estimate 5 pts, delivered."; }
    part caRetroGateR1 : TestResult { :>> id = "0d8001eb-0814-61eb-9b3e-0000003001eb"; :>> outcome = VerdictKind::pass; :>> judgedAgainst = "c400309"; :>> judgedAt = "2026-08-15"; :>> judgedBy = "claudeOpus5"; }
}
