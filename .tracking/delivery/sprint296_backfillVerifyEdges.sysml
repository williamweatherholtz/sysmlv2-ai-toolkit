// ProjectDeliveryS296 — Sprint 296: 73 prose verification claims become traversable edges; 4 stay
// honestly unverified (dcBackfillVerifyEdges, issue087). EXECUTE. 5 pts.
package ProjectDeliveryS296 {
    private import EngineElement::*;
    private import EngineWork::*;
    private import EngineVerification::*;
    private import EngineRelationships::*;

    #CharteredBy dependency from backfillStory to d0144;

    part backfillStory : Story {
        :>> id = "0d80022f-0814-622f-9b3e-00000030022f";
        :>> title = "Sprint 296: backfill the #Verify edges; leave four requirements honestly unverified (5 pts)";
        :>> createdAt = "2026-08-15"; :>> createdBy = "claudeOpus5"; :>> kind = WorkKind::modeling; :>> priority = WorkPriority::p0; :>> owner = "claudeOpus5"; :>> estimatedPoints = 5;
    }

    action def DeliveryRunS296 {
        action storyBackfill;
        verification storyBackfillDoD : Test { :>> id = "0d800230-0814-6230-9b3e-000000300230"; :>> method = VerificationMethod::inspect; :>> procedureText = "Delivers dcBackfillVerifyEdges; resolves issue087. The `verification-trace` guard found 77 pairs where a PASSED DoD names a SystemRequirement in its evidence while no `#Verify` edge reaches it — so `tier-satisfaction` reported the requirement unverified even though its work is done and passing. The prose claim already existed in every one; the edge makes it TRAVERSABLE, which is the engine's premise that a claim living only in prose is not state. DELIVERED: 73 edges in `.tracking/verification/verify-backfill.sysml`. MEASURED: verification-trace 77 -> 4 warnings; SystemRequirement tier 33/79 (41%) -> 65/79 (82%); METHOD MIX reported as the item requires, so the rise cannot be mistaken for functional verification — demo 50, test 40, inspect 18, critique 57, analyze 1. FOUR PAIRS ARE DELIBERATELY ABSENT and their requirements stay honestly unverified: `srDcEnrollment` and `srDcAuthorityFromRegistry` both demand kind AND ROLE, and role is unrecordable until D0146 is signed off (issue110); `srDcPerActorWriteTargets` was NOT delivered at all — sprint 293 built the ownership guard and never routed writes to per-actor targets. Those are the three this thread built and therefore knows to be partial. Authoring their edges would have reached a clean 0 and made the metric a lie. validate 319 clean; edge-endpoints 0 violations; 31 guards green."; }
        part storyBackfillDoDR1 : TestResult { :>> id = "0d800231-0814-6231-9b3e-000000300231"; :>> outcome = VerdictKind::pass; :>> judgedAgainst = "6b4515d"; :>> judgedAt = "2026-08-15"; :>> judgedBy = "claudeOpus5"; }
    }

    verification bfRefineGate2 : Test { :>> id = "0d800232-0814-6232-9b3e-000000300232"; :>> title = "Sprint 296 refine gate (DoR)"; :>> createdAt = "2026-08-15"; :>> createdBy = "claudeOpus5"; :>> method = VerificationMethod::inspect; :>> procedureText = "DoR. The item warned that authoring a `#Verify` edge asserts that a DoD's evidence discharges a requirement, and that this is a judgment only the delivering thread has the evidence to make (D0108). CONSUMER CHECK (dorConsumer, D0144): the consumer of a `#Verify` edge is `tier-satisfaction` and `assured`, both of which treat it as VERIFICATION — so an edge asserted without reading both sides would inflate an assurance metric, which is worse than the gap it closes. Both sides were read for every pair. estimatedPoints=5. DoR met."; }
    part bfRefineGate2R1 : TestResult { :>> id = "0d800233-0814-6233-9b3e-000000300233"; :>> outcome = VerdictKind::pass; :>> judgedAgainst = "6b4515d"; :>> judgedAt = "2026-08-15"; :>> judgedBy = "claudeOpus5"; }

    verification bfStandupGate2 : Test { :>> id = "0d800234-0814-6234-9b3e-000000300234"; :>> title = "Sprint 296 standup gate"; :>> createdAt = "2026-08-15"; :>> createdBy = "claudeOpus5"; :>> method = VerificationMethod::inspect; :>> procedureText = "Approach: classify every pair by whether the DoD's evidence claims the requirement, in reviewable batches, and read the requirement STATEMENT rather than matching its name. The first ten were judged by hand against the full statement text, which is what surfaced the role gap in two of them — a name-matching pass would have authored both. No blockers."; }
    part bfStandupGate2R1 : TestResult { :>> id = "0d800235-0814-6235-9b3e-000000300235"; :>> outcome = VerdictKind::pass; :>> judgedAgainst = "6b4515d"; :>> judgedAt = "2026-08-15"; :>> judgedBy = "claudeOpus5"; }

    verification bfImplementGate2 : Test { :>> id = "0d800236-0814-6236-9b3e-000000300236"; :>> title = "Sprint 296 implement gate"; :>> createdAt = "2026-08-15"; :>> createdBy = "claudeOpus5"; :>> method = VerificationMethod::test; :>> procedureText = "THE RULE HAD TO BE INVERTED, and that is the sprint's real content. My first classifier detected a delivery claim by its PHRASING — 'Delivers srX', 'Satisfies srX', the DoD's opening subject — and kept under-detecting: it read `(1) srViewerContextActions: right-click a graph node -> a context menu...` as a passing mention, when it is an enumerated statement of what was built. Widening the regex twice produced 37 then 49 edges out of 77, with the boundary moving each time — the sign that the shape was wrong, not the pattern. THE GUARD HAD ALREADY ESTABLISHED THE CLAIM: it fires because the DoD names the requirement in its EVIDENCE, and that is a claim however it is worded. So the question inverted to 'does the DoD DISCLAIM it — deferred, excluded, not delivered, out of scope?', which is a small closed vocabulary and matched 2 pairs, both false positives on reading ('partial SYNCHRONIZATION' is the condition sprint 290 HANDLES, not a disclaimer)."; }
    part bfImplementGate2R1 : TestResult { :>> id = "0d800237-0814-6237-9b3e-000000300237"; :>> outcome = VerdictKind::pass; :>> judgedAgainst = "6b4515d"; :>> judgedAt = "2026-08-15"; :>> judgedBy = "claudeOpus5"; }

    verification bfReviewGate2 : Test { :>> id = "0d800238-0814-6238-9b3e-000000300238"; :>> title = "Sprint 296 review gate"; :>> createdAt = "2026-08-15"; :>> createdBy = "claudeOpus5"; :>> method = VerificationMethod::inspect; :>> procedureText = "Reviewed. THE ITEM ASKED FOR 0 WARNINGS AND THE ANSWER IS 4, which is the honest result and is recorded as a deviation rather than presented as success. Each of the four names a requirement whose work is genuinely incomplete: two blocked on a schema field that does not exist yet, one not built at all. The item's own text sanctions this — 'either author the edge OR record why it does not' — and 4 warnings carrying real information is a better outcome than 0 obtained by asserting three things I know to be untrue. I also did NOT narrow the prose in those four DoDs as the item suggests: they are backlog items owned by other actors, and editing their fields is precisely what the ownership guard built in sprint 293 forbids. The warnings carry the signal instead."; }
    part bfReviewGate2R1 : TestResult { :>> id = "0d800239-0814-6239-9b3e-000000300239"; :>> outcome = VerdictKind::pass; :>> judgedAgainst = "6b4515d"; :>> judgedAt = "2026-08-15"; :>> judgedBy = "claudeOpus5"; }

    verification bfCloseOutGate2 : Test { :>> id = "0d80023a-0814-623a-9b3e-00000030023a"; :>> title = "Sprint 296 closeOut gate (autonomous, D0049)"; :>> createdAt = "2026-08-15"; :>> createdBy = "claudeOpus5"; :>> method = VerificationMethod::inspect; :>> procedureText = "Autonomous closeOut (D0049). dcBackfillVerifyEdges carries a passing DoD TestResult; issue087 resolves with 4 documented exceptions rather than 0 warnings, stated as a deviation. 73 edges authored, every endpoint resolving (edge-endpoints 0 violations). validate 319 clean; check-engine clean; 31 guards green. No gate bypassed."; }
    part bfCloseOutGate2R1 : TestResult { :>> id = "0d80023b-0814-623b-9b3e-00000030023b"; :>> outcome = VerdictKind::pass; :>> judgedAgainst = "6b4515d"; :>> judgedAt = "2026-08-15"; :>> judgedBy = "claudeOpus5"; }

    verification bfRetroGate2 : Test { :>> id = "0d80023c-0814-623c-9b3e-00000030023c"; :>> title = "Sprint 296 retro gate (autonomous, D0049)"; :>> createdAt = "2026-08-15"; :>> createdBy = "claudeOpus5"; :>> method = VerificationMethod::analyze; :>> procedureText = "Autonomous retro (D0049) under D0131's retroTrack. WELL: (1) the classifier's boundary MOVING each time I widened the regex was read as evidence that the shape was wrong rather than that the pattern needed one more alternative — inverting to 'does it disclaim' turned an open-ended matching problem into a closed one; (2) the four partials were held back even though authoring them would have produced the clean 0 the item asked for, and three of them are my OWN work, which is where the temptation was strongest; (3) the method mix is reported alongside the 41% -> 82% rise, so nobody can read it as functional verification. AVOIDABLE-ISSUE 1: I used an MSYS `/tmp/` path in a script run by Windows python and it failed on a missing file — the exact class `keel hook pre-bash` was built for in sprint 285, and the hook could not catch it because the path was INSIDE the script rather than an argument. NO NEW ITEM, reason stated: issue094 carries the class, the advisory covers the detectable half, and a path embedded in a script body is not detectable from the tool call. The operational rule is the one already recorded — on this host, prefer a path both toolchains can open. Estimate 5 pts, delivered."; }
    part bfRetroGate2R1 : TestResult { :>> id = "0d80023d-0814-623d-9b3e-00000030023d"; :>> outcome = VerdictKind::pass; :>> judgedAgainst = "6b4515d"; :>> judgedAt = "2026-08-15"; :>> judgedBy = "claudeOpus5"; }
}
