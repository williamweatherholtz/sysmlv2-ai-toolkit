// ProjectDeliveryS556 — Sprint 556: every Claude hook resolves the pinned binary before PATH - one resolution order for both surfaces, held equal by test. EXECUTE. 3 pts.
package ProjectDeliveryS556 {
    private import EngineElement::*;
    private import EngineWork::*;
    private import EngineVerification::*;
    private import EngineRelationships::*;

    #CharteredBy dependency from pinFirstHooksStory to d0316;

    part pinFirstHooksStory : Story {
        :>> id = "d266e699-6126-4220-8a67-072b904d565e";
        :>> title = "Sprint 556: every Claude hook resolves the pinned binary before PATH - one resolution order for both surfaces, held equal by test (3 pts)";
        :>> createdAt = "2026-09-05"; :>> createdBy = "claudeOpus5"; :>> kind = WorkKind::code; :>> priority = WorkPriority::p0; :>> owner = "claudeOpus5"; :>> estimatedPoints = 3;
    }

    action def DeliveryRunS556 {
        action storyPinFirstHooks;
        verification storyPinFirstHooksDoD : Test { :>> id = "4a23d9d0-3444-4e2a-a94f-ca285721e283"; :>> method = VerificationMethod::test; :>> procedureText = "DELIVERED BACKLOG ITEMS: dcHooksResolveThePinFirst (D0316; resolves issue348 / GH#43). DONE: RESOLUTION_ORDER (KEEL_BIN, .keel/bin/keel(.exe) under CLAUDE_PROJECT_DIR or cwd, PATH) with one pin_first_probe feeding the advisory, gating and protected-path resolvers; the scaffolded pre-commit hook moved into the library; a unit test holds every generated hook command (seven) and the git hook to that order by sequential probe and refuses a PATH-first script; .claude/settings.json and the plugin hooks.json regenerated by sync-claude; CLAUDE.md §5 says so."; }
        // RAN: same suite receipt: 501/0 exit 0
        part storyPinFirstHooksDoDR1 : TestResult { :>> id = "cdf64e6c-945a-4902-b7ea-f96de019d4c7"; :>> outcome = VerdictKind::pass; :>> judgedAgainst = "d697ae2927bde09c42b5a05d469da06e52e4cc29"; :>> judgedAt = "2026-09-05"; :>> judgedBy = "claudeOpus5"; }
    }

    verification pinFirstHooksRefineGate : Test { :>> id = "f1c369f7-2468-4d5d-a9db-20f3887f2b6c"; :>> title = "Sprint 556 refine gate (DoR)"; :>> createdAt = "2026-09-05"; :>> createdBy = "claudeOpus5"; :>> method = VerificationMethod::inspect; :>> procedureText = "READY: D0230 defined the pin and the git hook already honoured it; the Claude hooks were three copies of an older resolver string. The design question was how to keep two surfaces in one order for good: generate all three resolvers from one probe and compare the git hook against the same list in a test."; }
    verification pinFirstHooksStandupGate : Test { :>> id = "04c6eef7-e253-43d5-9aac-b0a2732b5170"; :>> title = "Sprint 556 standup gate"; :>> createdAt = "2026-09-05"; :>> createdBy = "claudeOpus5"; :>> method = VerificationMethod::inspect; :>> procedureText = "ONE FALSE START, FIXED IN THE TEST: a first-occurrence check read the git hook's COMMENT naming .keel/bin/keel as the probe and failed; the check now finds each step after the previous, which is the order the shell actually runs. The self-build's own .githooks/pre-commit probes target/release first by design and is outside this order."; }
    verification pinFirstHooksImplementGate : Test { :>> id = "3ea48431-7165-42ad-b8e4-45f5b1daf9e0"; :>> title = "Sprint 556 implement gate"; :>> createdAt = "2026-09-05"; :>> createdBy = "claudeOpus5"; :>> method = VerificationMethod::test; :>> procedureText = "RAN: cargo test --lib claude_surface 8 passed (order per hook command, git hook agreement, PATH-first refused; the six-event and fail-loud tests unchanged); clippy -D warnings clean; keel sync-claude regenerated both hook files with the pin probe (7 occurrences each); keel validate . clean; check-engine clean; the full suite in the background to completion (receipt on the DoD result)."; }
    verification pinFirstHooksReviewGate : Test { :>> id = "fe500c28-dd34-40bf-baa8-41087f51fa19"; :>> title = "Sprint 556 review gate — three passes per D0172"; :>> createdAt = "2026-09-05"; :>> createdBy = "claudeOpus5"; :>> method = VerificationMethod::inspect; :>> procedureText = "THREE PASSES. (1) DOES THE PROBE FAIL LOUD AS BEFORE: yes - the missing-binary branches are untouched and the existing tests still assert them. (2) DOES CLAUDE_PROJECT_DIR ALWAYS RESOLVE: it falls back to cwd, which the hooks already assumed. (3) IS THE GIT HOOK COMPARISON REAL: it is the same PRECOMMIT_HOOK string keel init writes, now in the library, compared by the same sequential probe."; }
    verification pinFirstHooksCloseOutGate : Test { :>> id = "ea47aba8-4b49-4f10-bf76-8e1baf5dbf85"; :>> title = "Sprint 556 closeOut gate (autonomous, D0049)"; :>> createdAt = "2026-09-05"; :>> createdBy = "claudeOpus5"; :>> method = VerificationMethod::inspect; :>> procedureText = "CLOSED. D0316 accepted under standing consent; issue348 resolved by computation."; }
    verification pinFirstHooksRetroGate : Test { :>> id = "b092f790-ed89-4692-8409-5f08e3dc0924"; :>> title = "Sprint 556 retro gate (autonomous, D0049)"; :>> createdAt = "2026-09-05"; :>> createdBy = "claudeOpus5"; :>> method = VerificationMethod::analyze; :>> procedureText = "no new item - already tracked: dcSurfaceStampNamesTheBuild is the sibling finding (a surface stamped with a version that does not say which build) and is on the frontier. The lesson: two renderings of one fact drift unless a test reads both from the same list."; }
}
