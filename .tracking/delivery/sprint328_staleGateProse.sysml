// ProjectDeliveryS328 — Sprint 328: a comment lied about a gate and I believed it over the record.
// Six comments fixed, the false claim corrected, guard 35 added. EXECUTE. 5 pts.
package ProjectDeliveryS328 {
    private import EngineElement::*;
    private import EngineWork::*;
    private import EngineVerification::*;
    private import EngineRelationships::*;

    #CharteredBy dependency from staleProseStory to d0047;

    part staleProseStory : Story {
        :>> id = "0d800430-0814-6430-9b3e-000000300430";
        :>> title = "Sprint 328: stale gate prose — six comments, one false critique claim, guard 35 (5 pts)";
        :>> createdAt = "2026-08-17"; :>> createdBy = "claudeOpus5"; :>> kind = WorkKind::code; :>> priority = WorkPriority::p0; :>> owner = "claudeOpus5"; :>> estimatedPoints = 5;
    }

    action def DeliveryRunS328 {
        action storyStaleProse;
        verification storyStaleProseDoD : Test { :>> id = "0d800431-0814-6431-9b3e-000000300431"; :>> method = VerificationMethod::test; :>> procedureText = "Resolves issue140 via dcStaleGateProse. I PUBLISHED A FALSE CLAIM AND THIS IS THE REPAIR. Selecting critique targets, I read a comment reading 'Business gate 5: PENDING human acceptance of N-18 — NOT yet accepted', concluded N-18 was unaccepted, and recorded that inside a landed critique in sprint 326. It is false: keelViewerNeedsAccept5R1 sits on the line DIRECTLY BELOW that comment, outcome pass, judgedBy wweatherholtz, judgedAt 2026-07-15, notes 'N-18 approved'. A second comment immediately AFTER the result asserted 'no TestResult yet'. Six such comments existed in that one file across Business gates 2, 3 and 5 — all three signed, none of the comments revised when they were. DELIVERED: (1) all six rewritten to state what IS, no tombstones; (2) the false clause corrected in place with the correction LEFT VISIBLE, since the error is more instructive than a clean text; (3) guard `stale-gate-prose`, the 35th and hard-blocking, fails on a PENDING-style claim within three lines of a PASSING acceptance result — VERIFIED BOTH DIRECTIONS: 148 acceptance results scanned clean, and re-injecting the exact stale comment fails with its file and line; (4) doc-sync — guards.md 34->35 and 25->26 hard-blocking with the catalogue row, CLAUDE.md's count. clippy clean; validate 356 clean; 35 guards ALL PASS."; }
        part storyStaleProseDoDR1 : TestResult { :>> id = "0d800432-0814-6432-9b3e-000000300432"; :>> outcome = VerdictKind::pass; :>> judgedAgainst = "6e16e18"; :>> judgedAt = "2026-08-17"; :>> judgedBy = "claudeOpus5"; }
    }

    verification spRefineGate : Test { :>> id = "0d800433-0814-6433-9b3e-000000300433"; :>> title = "Sprint 328 refine gate (DoR)"; :>> createdAt = "2026-08-17"; :>> createdBy = "claudeOpus5"; :>> method = VerificationMethod::inspect; :>> procedureText = "DoR. THIS SPRINT PREEMPTED THE PLANNED ONE, and the swap was right: I opened pass 5 of the critique backfill on five encoding SystemRequirements, noticed all five derive from N-18, and went to check whether architecture had been derived from an unaccepted Need — a process violation worth an Issue. It had not. What I found instead was that MY OWN understanding came from a stale comment, and that I had already published it. Fixing a false claim I authored outranks adding fifteen more critiques, because the corpus's value is entirely its truthfulness. The encoding SRs move to the next pass. estimatedPoints=5."; }
    part spRefineGateR1 : TestResult { :>> id = "0d800434-0814-6434-9b3e-000000300434"; :>> outcome = VerdictKind::pass; :>> judgedAgainst = "6e16e18"; :>> judgedAt = "2026-08-17"; :>> judgedBy = "claudeOpus5"; }

    verification spStandupGate : Test { :>> id = "0d800435-0814-6435-9b3e-000000300435"; :>> title = "Sprint 328 standup gate"; :>> createdAt = "2026-08-17"; :>> createdBy = "claudeOpus5"; :>> method = VerificationMethod::inspect; :>> procedureText = "Approach: state what IS rather than annotating the stale text (doc removal leaves no tombstones); correct the critique IN PLACE and leave the correction visible rather than silently rewriting it, because a reader who inherits the corpus needs to know a claim was wrong and why; make the guard PRECISE enough that an honest PENDING note beside a genuinely unsigned gate is untouched, since a guard that fires on correct work-in-progress would be turned off. No blockers."; }
    part spStandupGateR1 : TestResult { :>> id = "0d800436-0814-6436-9b3e-000000300436"; :>> outcome = VerdictKind::pass; :>> judgedAgainst = "6e16e18"; :>> judgedAt = "2026-08-17"; :>> judgedBy = "claudeOpus5"; }

    verification spImplementGate : Test { :>> id = "0d800437-0814-6437-9b3e-000000300437"; :>> title = "Sprint 328 implement gate"; :>> createdAt = "2026-08-17"; :>> createdBy = "claudeOpus5"; :>> method = VerificationMethod::test; :>> procedureText = "THE GUARD KEYS ON ADJACENCY BECAUSE ADJACENCY IS WHAT MADE THE COMMENT CREDIBLE: a stale note in a doc is a nuisance, but a note sitting three lines from the record it denies is authoritative to any reader, and it defeated me specifically. So the rule is a comment claiming PENDING, NOT yet accepted, or proposed/unaccepted within three lines of a TestResult that is both PASSING and an Accept — narrow on purpose, since the same words beside an UNSIGNED gate are correct and common. TWO ENCODING TRAPS HIT WHILE FIXING IT, both this host's cp1252 console: printing a matched line containing an em dash or a box-drawing character raised UnicodeEncodeError BEFORE the file was written, so the first attempt looked like a failed match while actually having lost its edits — the fix is sys.stdout.reconfigure, now in both helper scripts. THE INJECTION WAS REMOVED BY INVERSE EDIT, NOT BY GIT CHECKOUT, with an assert that the injected text is present before removing it — sprint 319's lesson applied, where a git checkout to undo a test injection discarded the uncommitted work in the same file."; }
    part spImplementGateR1 : TestResult { :>> id = "0d800438-0814-6438-9b3e-000000300438"; :>> outcome = VerdictKind::pass; :>> judgedAgainst = "6e16e18"; :>> judgedAt = "2026-08-17"; :>> judgedBy = "claudeOpus5"; }

    verification spReviewGate : Test { :>> id = "0d800439-0814-6439-9b3e-000000300439"; :>> title = "Sprint 328 review gate"; :>> createdAt = "2026-08-17"; :>> createdBy = "claudeOpus5"; :>> method = VerificationMethod::inspect; :>> procedureText = "Reviewed. WHY THE CORRECTION IS VISIBLE RATHER THAN CLEAN: I own the critique (createdBy claudeOpus5) and could have silently replaced the false sentence, and the record would read better. It would also destroy the only evidence that the corpus can contain a confident false claim, which is the single most important thing a reader of a 90-critique corpus needs to know about it. The correction states what I claimed, where I got it, why it was wrong, and what now prevents it. THE HONEST SCOPE OF THE DAMAGE, since a reader will ask: one subordinate clause in one lens. The testability finding it accompanied stands unchanged on its own ground ('semantically enough to auto-generate' has no criterion), and no other critique in the corpus depends on the acceptance status of N-18. What DID change materially is the consequence — N-18 being accepted means its untestable clause is already inherited by five derived SystemRequirements, which is worse than the 'cheap to fix now' I originally wrote."; }
    part spReviewGateR1 : TestResult { :>> id = "0d80043a-0814-643a-9b3e-00000030043a"; :>> outcome = VerdictKind::pass; :>> judgedAgainst = "6e16e18"; :>> judgedAt = "2026-08-17"; :>> judgedBy = "claudeOpus5"; }

    verification spCloseOutGate : Test { :>> id = "0d80043b-0814-643b-9b3e-00000030043b"; :>> title = "Sprint 328 closeOut gate (autonomous, D0049)"; :>> createdAt = "2026-08-17"; :>> createdBy = "claudeOpus5"; :>> method = VerificationMethod::inspect; :>> procedureText = "Autonomous closeOut (D0049). issue140 resolved; guard count 34 -> 35, hard-blocking 25 -> 26, both doc-synced in the same commit. The five encoding SystemRequirements deferred to the next pass, unstarted, which is stated rather than implied. clippy clean; 229 tests; validate 356 clean; check-engine clean; 35 guards ALL PASS."; }
    part spCloseOutGateR1 : TestResult { :>> id = "0d80043c-0814-643c-9b3e-00000030043c"; :>> outcome = VerdictKind::pass; :>> judgedAgainst = "6e16e18"; :>> judgedAt = "2026-08-17"; :>> judgedBy = "claudeOpus5"; }

    verification spRetroGate : Test { :>> id = "0d80043d-0814-643d-9b3e-00000030043d"; :>> title = "Sprint 328 retro gate (autonomous, D0049)"; :>> createdAt = "2026-08-17"; :>> createdBy = "claudeOpus5"; :>> method = VerificationMethod::analyze; :>> procedureText = "Autonomous retro (D0049) under D0131's retroTrack. THE AVOIDABLE-ISSUE IS THE SPRINT: I asserted, in a permanent record, a fact I had read in a comment and never checked against the model — and the model contradicted it three lines away. That is precisely the failure D0151 exists to name, committed one sprint after I wrote a retro congratulating myself for checking two other claims. The uncomfortable detail is that this claim FELT like context rather than a claim, which is exactly how the class survives: I verified the two facts I noticed I was asserting and missed the one I thought I was merely reporting. THE CONTROL IS NOT VIGILANCE, per D0047: guard stale-gate-prose now makes this specific contradiction impossible to leave in the tree, and it is hard-blocking because a reader cannot be expected to distrust adjacent prose. WELL: the correction is visible rather than tidied; the injection was undone by inverse edit with an assert rather than by git checkout; the doc-sync rode the same commit. Estimate 5 pts, delivered."; }
    part spRetroGateR1 : TestResult { :>> id = "0d80043e-0814-643e-9b3e-00000030043e"; :>> outcome = VerdictKind::pass; :>> judgedAgainst = "6e16e18"; :>> judgedAt = "2026-08-17"; :>> judgedBy = "claudeOpus5"; }
}
