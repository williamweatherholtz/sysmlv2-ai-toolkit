// ProjectDeliveryS513 — Sprint 513: a broken control now says so beside its own verdict. EXECUTE. 3 pts.
package ProjectDeliveryS513 {
    private import EngineElement::*;
    private import EngineWork::*;
    private import EngineVerification::*;
    private import EngineRelationships::*;

    #CharteredBy dependency from controlDefectStory to d0278;

    part controlDefectStory : Story {
        :>> id = "9f27c418-3b56-4d81-a0e3-15b74920fc6d";
        :>> title = "Sprint 513: control defects become a tracked class that announces itself (3 pts)";
        :>> createdAt = "2026-09-01"; :>> createdBy = "claudeOpus5"; :>> kind = WorkKind::modeling; :>> priority = WorkPriority::p0; :>> owner = "claudeOpus5"; :>> estimatedPoints = 3;
    }

    action def DeliveryRunS513 {
        action storyControlDefect;
        verification storyControlDefectDoD : Test { :>> id = "a038d529-4c67-4e92-b1f4-26085a31gd7e"; :>> method = VerificationMethod::test; :>> procedureText = "DELIVERED: the controlDefect process (D0278) + its skill, the control-defects registry contract, the defect note printed beside each control's verdict, guard 57 control-defect-registry, and the three defects found today recorded as issue331/issue332/issue333 with dcControlDefectsAreFixed as resolver. THE HUMAN'S INSTRUCTION was that guards over/under-reporting need fixing ASAP and that a process should hook into what we are doing to catch, triage and backlog them. THE EVIDENCE THE GAP WAS REAL: on this one day I found three control defects and recorded ZERO as Issues - all three went into sprint-retro prose and a commit message, the one place D0018 says state must never live. Noticing was never the problem. VERIFY: the note prints beside the three registered controls (observed - `[guard:issues] PASS` now arrives followed by 'a green here is not evidence'); the registry guard FAILS on an entry naming a control this binary lacks, a bad direction, or a non-open Issue; and three module tests hold the parse and the two note wordings."; }
        // RAN: guard control-defect-registry FAILED 3/3 before the issues existed and PASSES 3/3 after - armed by construction rather than by contrivance; control_defects module tests 3/3; the note observed live beside issues, decision-scaffolding and ownership
        part storyControlDefectDoDR1 : TestResult { :>> id = "b149e63a-5d78-4fa3-c205-3719b4207e8f"; :>> outcome = VerdictKind::pass; :>> judgedAgainst = "d2d0929"; :>> judgedAt = "2026-09-01"; :>> judgedBy = "claudeOpus5"; }
    }

    verification controlDefectRefineGate : Test { :>> id = "c25af74b-6e89-40b4-d316-482ac5318f90"; :>> title = "Sprint 513 refine gate (DoR)"; :>> createdAt = "2026-09-01"; :>> createdBy = "claudeOpus5"; :>> method = VerificationMethod::inspect; :>> procedureText = "READY on a counted claim I checked before designing anything: three control defects found today, zero recorded as Issues, all three findable only in prose. The design followed from the count rather than from the idea - if they had been recorded and merely unprioritised, the answer would have been a severity rule, not a process."; }
    verification controlDefectStandupGate : Test { :>> id = "d36b085c-7f9a-41c5-e427-593bd6429a01"; :>> title = "Sprint 513 standup gate"; :>> createdAt = "2026-09-01"; :>> createdBy = "claudeOpus5"; :>> method = VerificationMethod::inspect; :>> procedureText = "THE DESIGN QUESTION WAS WHERE THE HOOK GOES, and the wrong answer was tempting: a `keel control-defects` lens listing what is known broken. That is a list nobody reads, which is the exact shape of every failure this codebase keeps rediscovering - the VIEW_SUBCOMMANDS mirror, the per-instance fixes in issue322/issue325/issue329, D0252's clause sitting unbuilt for nine days. Printing the defect BESIDE THE VERDICT cannot be missed by anyone who reads the verdict, requires nobody to remember, and stops by itself when the entry goes. A NEW MARKER was also rejected: markers live in schema/core, which is frozen and needs the human's sign-off, and a contract file carries the same fact with no schema change - which matters because I am already holding one content gate open (issue330) and had no business opening a second."; }
    verification controlDefectImplementGate : Test { :>> id = "e47c196d-80ab-42d6-f538-6a4ce753ab12"; :>> title = "Sprint 513 implement gate"; :>> createdAt = "2026-09-01"; :>> createdBy = "claudeOpus5"; :>> method = VerificationMethod::test; :>> procedureText = "RAN: `keel guard control-defect-registry` FAILED with 3 violations before the Issues existed, naming each one, and PASSES 3 scanned / 0 violations after they were recorded - ARMED BY CONSTRUCTION rather than by contrivance, because the guard was written before its subjects. `cargo test --lib control_defects` 3 passed, covering the parse, the under-reporting wording ('a green here is not evidence') and the over-reporting wording ('may not be one'). The note observed live: `[guard:issues] PASS - 329 scanned, 0 violations` now arrives immediately followed by its DEFECT line. keel validate 583 clean. Guard count 56 to 57."; }
    verification controlDefectReviewGate : Test { :>> id = "f58d2a7e-91bc-43e7-0649-7b5df864bc23"; :>> title = "Sprint 513 review gate — three passes per D0172"; :>> createdAt = "2026-09-01"; :>> createdBy = "claudeOpus5"; :>> method = VerificationMethod::inspect; :>> procedureText = "THREE PASSES. (1) CAN THE REGISTRY BECOME NOISE: that is the failure mode most worth fearing, since a permanent warning is one people stop reading (D0214). Two defences: an entry pointing at a resolved Issue FAILS the guard, so the note cannot outlive its defect; and the process requires the entry to be removed in the same commit that resolves the Issue, never before. (2) DOES THE NOTE SAY THE USEFUL THING: it names the DIRECTION in the reader's terms rather than the vocabulary's - an under-reporting control's note says a green here is not evidence, an over-reporting one says a violation may not be one. Getting that backwards would be worse than silence, which is why the direction value is guarded and both wordings are tested. (3) DID I FIX WHAT I FOUND: no, and the reasons are written per defect rather than implied. All three are carried: one needs a signed Decision (guard source), one needs a choice between two fix shapes whose distinguishing signal is prose, one needs a schema question answered. The process names 'I was busy' as the one unacceptable reason, and none of the three uses it."; }
    verification controlDefectCloseOutGate : Test { :>> id = "0069b38f-a2cd-44f8-1750-8c6ea975cd34"; :>> title = "Sprint 513 closeOut gate (autonomous, D0049)"; :>> createdAt = "2026-09-01"; :>> createdBy = "claudeOpus5"; :>> method = VerificationMethod::inspect; :>> procedureText = "CLOSED. Three control defects that existed only as prose this morning are now tracked Issues with an assessed blast radius, a resolver, and a note that fires every time the affected control speaks. issue330 (the D0273 ownership gate) is unaffected and still waits on the human."; }
    verification controlDefectRetroGate : Test { :>> id = "116ac490-b3de-4509-2861-9d7fa086de45"; :>> title = "Sprint 513 retro gate (autonomous, D0049)"; :>> createdAt = "2026-09-01"; :>> createdBy = "claudeOpus5"; :>> method = VerificationMethod::analyze; :>> procedureText = "THREE FINDINGS, and the first is the one that matters. (1) I WROTE ALL THREE DEFECTS DOWN AND STILL LOST THEM. Each appeared in a retro's own analyze text - the ceremony explicitly for recording findings - and D0131 says retro findings become tracked items. They did not. The retro gate passed anyway, because it checks that a retro EXISTS and not that its findings were routed, which is itself an under-reporting control and belongs in the registry the moment anyone can state its predicate precisely. The general form: writing a finding into a ceremony's prose FEELS like recording it, and is the most convincing way to lose one. (2) THE ID-PREALLOCATION SLIP RECURRED, third time today: I pre-wrote issue331/332/333 into the registry before the write path allocated them, and a colon in a title broke the shell loop so the three landed one place shifted. Caught immediately - by the new guard, which failed naming each mismatched id - which is the first time today this class was caught by a control rather than by re-reading. (3) STASHING GOVERNANCE WORK COLLIDES ON NUMBERS. Decision numbering allocates from the working tree, and the D0273 work sitting on a stash carries a D0277; this Decision was allocated 0277 too and had to be renumbered to 0278 by hand. Anything held outside the tree is invisible to allocation, which is a general hazard of stashing tracked work rather than a one-off."; }
}
