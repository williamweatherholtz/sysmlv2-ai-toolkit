// ProjectDeliveryS542 — Sprint 542: the reference copy is out of the downstream model - proven by recording first. EXECUTE. 1 pt.
package ProjectDeliveryS542 {
    private import EngineElement::*;
    private import EngineWork::*;
    private import EngineVerification::*;
    private import EngineRelationships::*;

    #CharteredBy dependency from referenceScopeStory to d0093;

    part referenceScopeStory : Story {
        :>> id = "855a7d31-8990-436a-90ab-7fab63691676";
        :>> title = "Sprint 542: a record-then-assert test over a fresh init - no foreign attestation, every SHA resolves, the rules' edges still hold - the finding that the property already held, and the launcher flake caught in the act and fixed at its root (2 pts)";
        :>> createdAt = "2026-09-04"; :>> createdBy = "claudeOpus5"; :>> kind = WorkKind::code; :>> priority = WorkPriority::p0; :>> owner = "claudeOpus5"; :>> estimatedPoints = 2;
    }

    action def DeliveryRunS542 {
        action storyReferenceScope;
        verification storyReferenceScopeDoD : Test { :>> id = "1c26e443-4426-4586-be59-04ed195d9b52"; :>> method = VerificationMethod::test; :>> procedureText = "DELIVERED BACKLOG ITEMS: scopeReferenceCopyOutOfTheInstanceModel (resolves issue292); dcLauncherFinishTestIsDeterministic (resolves issue369 - the flake fired AGAIN during this sprint's full run, --no-fail-fast captured got [.keel/sessions/]: the session binding issue337 writes when the test process inherits CLAUDE_CODE_SESSION_ID, present under an agent session and never under CI; launcher::finish now excludes machine-local .keel/ from a run's diff, the test forces the variable so the cause is exercised, twenty consecutive runs green). FOUND FIRST: the property already holds - view::model_dirs has excluded .engine/reference since 0bd61be (2026-08-14, D0093) and edge-endpoints resolves the rules' JustifiedBy edges through declared_elsewhere; issue292's diagnosis (collect_sysml at lib.rs:75 has no exclusions, so the copy was always parsed) named a function the Model does not use. The gap issue292 named CORRECTLY was that every gate over init asserted init-then-validate and never recorded a fact. DONE: tests/reference_copy_is_out_of_the_model.rs - scaffold, commit, record a task and a passing result, then assert the attestation census holds exactly the probe's one result and no wweatherholtz row, orient's invalidEvidence is empty, check-engine is clean and edge-endpoints has 0 violations, with the 236 reference files asserted present so the test cannot pass vacuously. VERIFY: 1/1; mutation (reference copy added to model_dirs) fails the test at the leak assertion; restored passes."; }
        // RAN: live probe in C:/t/kfx (a short path - the scratchpad path was too long for Windows git): attestation one row unregistered 1, grep wweatherholtz 0, orient invalidEvidence [], check-engine clean; cargo test --test reference_copy_is_out_of_the_model 1/1; mutated model_dirs -> FAILED at line 84; restored -> ok; git diff on mod.rs empty
        part storyReferenceScopeDoDR1 : TestResult { :>> id = "dbd798ec-0830-4202-a7f9-55b2c6597a5a"; :>> outcome = VerdictKind::pass; :>> judgedAgainst = "93169c6"; :>> judgedAt = "2026-09-04"; :>> judgedBy = "claudeOpus5"; }
    }

    verification referenceScopeRefineGate : Test { :>> id = "ba09a9f7-4c30-4e4e-b8ff-1f2fd2cbb9a3"; :>> title = "Sprint 542 refine gate (DoR)"; :>> createdAt = "2026-09-04"; :>> createdBy = "claudeOpus5"; :>> method = VerificationMethod::inspect; :>> procedureText = "READY once the claim was measured rather than believed: a grep over the fixture's FILES showed 301 wweatherholtz results, which is the number issue292 was built on - and the MODEL showed zero. Two different questions; the issue conflated them, and so did my first read."; }
    verification referenceScopeStandupGate : Test { :>> id = "300064fd-03a5-4f38-819f-35d53d1cf0f3"; :>> title = "Sprint 542 standup gate"; :>> createdAt = "2026-09-04"; :>> createdBy = "claudeOpus5"; :>> method = VerificationMethod::inspect; :>> procedureText = "ONE CHOICE: build the test the DoD asked for even though the property already held, because the DoD's real finding was the missing record-then-assert gate, not the scope defect - and a property nothing measures is one refactor from false. The mutation probe is what makes the test a control rather than a ceremony."; }
    verification referenceScopeImplementGate : Test { :>> id = "f37dfcd6-83f8-4324-8d9d-6d214da222b9"; :>> title = "Sprint 542 implement gate"; :>> createdAt = "2026-09-04"; :>> createdBy = "claudeOpus5"; :>> method = VerificationMethod::test; :>> procedureText = "RAN: the first fixture failed on Windows path length (git refused the reference decisions' long file names under the deep scratchpad path) and the scaffold has no backlog to record into - both are in the test as a short path and a written backlog. The test asserts the 236 reference files are PRESENT before asserting they are out of the model."; }
    verification referenceScopeReviewGate : Test { :>> id = "a4186452-a2fa-4ba6-9cd5-f2fd6a03a99c"; :>> title = "Sprint 542 review gate — three passes per D0172"; :>> createdAt = "2026-09-04"; :>> createdBy = "claudeOpus5"; :>> method = VerificationMethod::inspect; :>> procedureText = "THREE PASSES. (1) IS THE ISSUE RESOLVED OR DISMISSED: resolved - its DoD's four assertions hold and are now held by a test; its mechanism claim was wrong and the DoD result says so with the commit that made it wrong. (2) WHAT STILL READS THE REFERENCE COPY: six syntactic guards scan all of .engine (marker vocabulary, identity, scaffold placeholders, attribute vocabulary) - form checks a reference copy should pass, and does. (3) IS THE TEST BRITTLE: it parses the census by row prefix; a renamed judge label breaks it loudly, which is the right failure."; }
    verification referenceScopeCloseOutGate : Test { :>> id = "a8fc3766-44d8-446a-9d05-a1f8cbb1fdbd"; :>> title = "Sprint 542 closeOut gate (autonomous, D0049)"; :>> createdAt = "2026-09-04"; :>> createdBy = "claudeOpus5"; :>> method = VerificationMethod::inspect; :>> procedureText = "CLOSED. issue292 resolves; the record-then-assert gate exists."; }
    verification referenceScopeRetroGate : Test { :>> id = "e00fffae-a729-4319-87dc-55cd5d343a27"; :>> title = "Sprint 542 retro gate (autonomous, D0049)"; :>> createdAt = "2026-09-04"; :>> createdBy = "claudeOpus5"; :>> method = VerificationMethod::analyze; :>> procedureText = "no new item - already tracked: issue369 closed here because its payload was finally captured - a flake is a defect with a name once its output is kept, and the fix was one filter and a forced condition, which is the argument for --no-fail-fast to a file on every full run; an Issue whose mechanism was misdiagnosed is the d0151 class (a suspicion stated in a conclusion's grammar), and d0151 is the standing control on what I say; the init-gates-never-record gap is closed by this test rather than opened as an item. The reusable lesson is one sentence: a count over files and a count over the model are different questions, and the issue was written from the first while claiming the second."; }
}
