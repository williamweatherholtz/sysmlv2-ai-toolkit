// ProjectDeliveryS584 — Sprint 584: the full suite becomes a control, not a discipline - keel suite writes the receipt, keel land demands it. EXECUTE. 3 pts.
package ProjectDeliveryS584 {
    private import EngineElement::*;
    private import EngineWork::*;
    private import EngineVerification::*;
    private import EngineRelationships::*;

    #CharteredBy dependency from suiteReceiptStory to d0353;

    part suiteReceiptStory : Story {
        :>> id = "019156f7-836f-48c7-aca9-f5a1314e0247";
        :>> title = "Sprint 584: the full suite becomes a control, not a discipline - keel suite writes the receipt, keel land demands it (3 pts)";
        :>> createdAt = "2026-09-06"; :>> createdBy = "claudeOpus5"; :>> kind = WorkKind::code; :>> priority = WorkPriority::p0; :>> owner = "claudeOpus5"; :>> estimatedPoints = 3;
    }

    action def DeliveryRunS584 {
        action storySuiteReceipt;
        verification storySuiteReceiptDoD : Test { :>> id = "acdd4684-0900-44da-b6c0-eed0a09e4a76"; :>> method = VerificationMethod::test; :>> procedureText = "DELIVERED BACKLOG ITEMS: dcLandRequiresASuiteReceipt (D0353 proposed, safety-change - waits for the human under D0337). DONE: keel suite runs cargo test --release --no-fail-fast for the self-build, logs under .keel/metrics/, writes .keel/metrics/suite-receipt.toml with the deliverable fingerprint (SHA-256 over on-disk content of keel-cli/, .engine/, keelw, Cargo.toml, Cargo.lock), head, time, counts, outcome; keel land, after the workspace gate and before the first push, refuses a self-build tree with no receipt, a red receipt, or a fingerprint that is not the deliverable's now, naming which and printing keel suite; KEEL_LAND_UNTESTED=1 pushes and records a land-untested obligation; non-self-build projects are untouched; the suite CLI fact in both homes. VERIFIED: land_requires_a_suite_receipt 2/2 (no receipt refused naming keel suite; green receipt lands; docs-only commit lands; source commit refused as CHANGED; red receipt refused as RED; override lands with exactly one obligation); suite unit tests 2/2 (result counting, receipt parse); cli-surface-declared PASS 106; this sprint itself landed through the new gate on the receipt keel suite wrote (suite585)."; }
        // RAN: DoD passes recorded on keel suite 562/0 (receipt af357bb03f1a); the implement section names each run
        part storySuiteReceiptDoDR1 : TestResult { :>> id = "eb9ac45e-bebf-4cd9-8dbc-aedbd3344433"; :>> outcome = VerdictKind::pass; :>> judgedAgainst = "a66324cffb59b843c32591c1a2e5f19ee1639036"; :>> judgedAt = "2026-09-06"; :>> judgedBy = "claudeOpus5"; }
    }

    verification suiteReceiptRefineGate : Test { :>> id = "8bbd5b59-bd12-437a-85b9-3aa51ae8f948"; :>> title = "Sprint 584 refine gate (DoR)"; :>> createdAt = "2026-09-06"; :>> createdBy = "claudeOpus5"; :>> method = VerificationMethod::inspect; :>> procedureText = "READY: the DoD named the mechanism; the two design points were what to fingerprint (the deliverable on disk, so a docs-only change needs no rerun and an uncommitted source edit does) and where to check (after the gate - the override's obligation is an untriaged Issue, and before the gate it refused the push it authorised; the first test run showed exactly that)."; }
    verification suiteReceiptStandupGate : Test { :>> id = "8a26bb1e-fbc2-415c-a958-3335f2bbc262"; :>> title = "Sprint 584 standup gate"; :>> createdAt = "2026-09-06"; :>> createdBy = "claudeOpus5"; :>> method = VerificationMethod::inspect; :>> procedureText = "TWENTY-ONE SPRINTS OF SUITE-BY-HAND: every sprint today ran the suite from a background shell and wrote the count into the receipt by hand - the same discipline whose one lapse (sprint 521) chartered this item, and which CI caught twice more today on Linux-only defects. From here the receipt is written by the run and read by the push."; }
    verification suiteReceiptImplementGate : Test { :>> id = "652679bb-60be-4215-9cf4-f0b96fe3db52"; :>> title = "Sprint 584 implement gate"; :>> createdAt = "2026-09-06"; :>> createdBy = "claudeOpus5"; :>> method = VerificationMethod::test; :>> procedureText = "RAN: cargo test --test land_requires_a_suite_receipt 2/2 (first run red twice: init on a non-empty dir, then the obligation-before-gate ordering - both fixed at the root); --lib suite 2/2; clippy -D warnings clean after extracting cmd_status and cmd_suite from main; keel audit-adherence . PASS; keel suite . on this tree (suite585.txt) wrote the receipt land then read."; }
    verification suiteReceiptReviewGate : Test { :>> id = "5a7ed0bc-bd87-416e-aa48-ae004a482a4a"; :>> title = "Sprint 584 review gate — three passes per D0172"; :>> createdAt = "2026-09-06"; :>> createdBy = "claudeOpus5"; :>> method = VerificationMethod::inspect; :>> procedureText = "THREE PASSES. (1) CAN A SOURCE EDIT SLIP PAST: the fingerprint reads disk content of every tracked or addable deliverable file, so an uncommitted edit changes it. (2) CAN THE RECEIPT BE FORGED: yes, by hand - it is machine-local evidence and says so; CI reruns the suite and is the independent check. (3) IS A DOWNSTREAM PROJECT AFFECTED: no - is_self_build is the guard on the whole check."; }
    verification suiteReceiptCloseOutGate : Test { :>> id = "d06c318e-78da-4643-a183-a649e9723f4f"; :>> title = "Sprint 584 closeOut gate (autonomous, D0049)"; :>> createdAt = "2026-09-06"; :>> createdBy = "claudeOpus5"; :>> method = VerificationMethod::inspect; :>> procedureText = "CLOSED. D0353 joins the human's queue; from this sprint on the suite runs through keel suite."; }
    verification suiteReceiptRetroGate : Test { :>> id = "112579d2-98cb-49f8-933e-a7c164ddcc58"; :>> title = "Sprint 584 retro gate (autonomous, D0049)"; :>> createdAt = "2026-09-06"; :>> createdBy = "claudeOpus5"; :>> method = VerificationMethod::analyze; :>> procedureText = "no new item - already tracked: issue380's release-gap note applies here too - a downstream keel land is unaffected because it has no suite, and CI stays its check. The lesson: a discipline performed twenty-one times in a day is a control waiting to be written, and the day's two CI reds were the cost of waiting."; }
}
