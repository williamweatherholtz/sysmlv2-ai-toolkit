// ProjectDeliveryS547 — Sprint 547: the write API never reports success over a file validate rejects. EXECUTE. 1 pts.
package ProjectDeliveryS547 {
    private import EngineElement::*;
    private import EngineWork::*;
    private import EngineVerification::*;
    private import EngineRelationships::*;

    #CharteredBy dependency from sanitizeBackslashStory to d0305;

    part sanitizeBackslashStory : Story {
        :>> id = "74e699a7-0008-428b-bc71-6e3c70f1c924";
        :>> title = "Sprint 547: the write API never reports success over a file validate rejects (1 pts)";
        :>> createdAt = "2026-09-04"; :>> createdBy = "claudeOpus5"; :>> kind = WorkKind::code; :>> priority = WorkPriority::p0; :>> owner = "claudeOpus5"; :>> estimatedPoints = 1;
    }

    action def DeliveryRunS547 {
        action storySanitizeBackslash;
        verification storySanitizeBackslashDoD : Test { :>> id = "be39aafa-63b8-456e-b280-cd15c663e8ff"; :>> method = VerificationMethod::test; :>> procedureText = "DELIVERED BACKLOG ITEMS: dcSanitizeMakesBackslashesSafe (resolves issue366). DONE: sanitize_field turns a backslash into a forward slash; write_atomic tokenises and parses every .sysml result before it lands and REFUSES with InvalidData naming the file and the parse error, nothing on disk changed, no temp file left; non-.sysml targets untouched. VERIFY: unit test both directions (path and regex sanitised; an unparsable .sysml write refused and the original intact; a valid write still lands; a .json write unparsed); the exact 2026-09-03 shape - record decision --from with a Windows path in its context - now records a slash-form path and validates clean; 482 tests; clippy clean."; }
        // RAN: write::tests 19/19 incl. the new both-direction test; fixture reproduction clean; first full run 480/2 (launcher's second sanitiser and an atomicity test, both fixed), rerun total in the implement gate; clippy 0. This line first claimed 482/0 before the suite finished and was corrected by its author | (rerun after the two fixes, launcher's one sanitiser and the atomicity test's parseable content): cargo test --release --no-fail-fast 482 passed, 0 failed; clippy 0
        part storySanitizeBackslashDoDR1 : TestResult { :>> id = "8f2f6739-ff2e-429d-a890-64fa2880038c"; :>> outcome = VerdictKind::pass; :>> judgedAgainst = "936dabc"; :>> judgedAt = "2026-09-04"; :>> judgedBy = "claudeOpus5"; }
    }

    verification sanitizeBackslashRefineGate : Test { :>> id = "10d125d2-0108-42b7-a783-c59c7169f045"; :>> title = "Sprint 547 refine gate (DoR)"; :>> createdAt = "2026-09-04"; :>> createdBy = "claudeOpus5"; :>> method = VerificationMethod::inspect; :>> procedureText = "READY from issue366's own record: three commands, one path, one missing sanitisation and no parse-before-write; the DoD named both halves."; }
    verification sanitizeBackslashStandupGate : Test { :>> id = "87c506d5-3ed1-4712-b578-74b58cd27d68"; :>> title = "Sprint 547 standup gate"; :>> createdAt = "2026-09-04"; :>> createdBy = "claudeOpus5"; :>> method = VerificationMethod::inspect; :>> procedureText = "ONE CHOICE: the parse check lives in write_atomic, the choke point every API writer of model text already passes for issue185's atomicity - not in the fourteen sanitising call sites, where one forgotten site is the next issue366. Second: a slash, not an escape, because the two parsers (issue097) disagree on escape vocabulary and a slash is a character everywhere."; }
    verification sanitizeBackslashImplementGate : Test { :>> id = "e22db6b6-159f-4c66-b8f6-f2a56944148c"; :>> title = "Sprint 547 implement gate"; :>> createdAt = "2026-09-04"; :>> createdBy = "claudeOpus5"; :>> method = VerificationMethod::test; :>> procedureText = "RAN: unit test first (a duplicated #[test] attribute caught by clippy); the live reproduction in the fixture - record decision --from with C:/Program Files in the context - records and validates clean; the write path's own 19 tests pass. THEN the full suite: 480 passed, 2 FAILED - the new refusal caught launcher::finish writing a run summary that did not parse (its own escaper handled quotes and newlines, not the Windows path a gate problem carried - replaced by the one sanitiser) and an atomicity test writing prose into a .sysml (given parseable content). I had recorded 482/0 in two receipts before that run finished; both corrected in place, and this gate says so. Rerun total after the fixes: see the RAN line above this gate's DoD result."; }
    verification sanitizeBackslashReviewGate : Test { :>> id = "2cb3af8a-b768-4798-9646-f72f4b7042e6"; :>> title = "Sprint 547 review gate — three passes per D0172"; :>> createdAt = "2026-09-04"; :>> createdBy = "claudeOpus5"; :>> method = VerificationMethod::inspect; :>> procedureText = "THREE PASSES. (1) CAN A REFUSAL LOSE WORDS: no - refusal happens before the temp write, the original stays, and the error carries the parse message so the author sees what to change. (2) IS ANY LEGITIMATE BACKSLASH LOST: a regex in prose becomes slashed - stated in D0305 as the trade; a field that needs a literal backslash is code and belongs in a file, not a record. (3) WHAT ELSE THIS CATCHES: any future write-path bug that produces unparsable text is a refusal at the writer, not a red gate later - the D0295 misplacement would have been one."; }
    verification sanitizeBackslashCloseOutGate : Test { :>> id = "61c95f97-0571-4331-a19f-c28ea1ab1829"; :>> title = "Sprint 547 closeOut gate (autonomous, D0049)"; :>> createdAt = "2026-09-04"; :>> createdBy = "claudeOpus5"; :>> method = VerificationMethod::inspect; :>> procedureText = "CLOSED. issue366 resolves; write_atomic's doc carries the contract."; }
    verification sanitizeBackslashRetroGate : Test { :>> id = "9da8e6b9-2022-4f36-ac98-28c2d497376c"; :>> title = "Sprint 547 retro gate (autonomous, D0049)"; :>> createdAt = "2026-09-04"; :>> createdBy = "claudeOpus5"; :>> method = VerificationMethod::analyze; :>> procedureText = "no new item - already tracked: the three records broken on 2026-09-03 were repaired that day and stand; the class is closed at the choke point, which is where d0295's retro said the other block-locating code should also go when touched - and now a mistake there is refused rather than landed."; }
}
