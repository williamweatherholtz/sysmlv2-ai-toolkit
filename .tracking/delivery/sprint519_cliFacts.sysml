// ProjectDeliveryS519 — Sprint 519: the CLI facts are authored, the help renders from them, a guard holds all three equal. EXECUTE. 3 pts.
package ProjectDeliveryS519 {
    private import EngineElement::*;
    private import EngineWork::*;
    private import EngineVerification::*;
    private import EngineRelationships::*;

    #CharteredBy dependency from cliFactsStory to d0283;

    part cliFactsStory : Story {
        :>> id = "9a7b3c1d-2e4f-4a56-b7c8-d9e0f1a2b3c4";
        :>> title = "Sprint 519: 100 CLI facts authored, keel --help rendered from them, guard 58 holds facts, help and dispatch equal both ways (3 pts)";
        :>> createdAt = "2026-09-02"; :>> createdBy = "claudeOpus5"; :>> kind = WorkKind::code; :>> priority = WorkPriority::p0; :>> owner = "claudeOpus5"; :>> estimatedPoints = 3;
    }

    action def DeliveryRunS519 {
        action storyCliFacts;
        verification storyCliFactsDoD : Test { :>> id = "ab8c4d2e-3f50-4b67-c8d9-e0f1a2b3c4d5"; :>> method = VerificationMethod::test; :>> procedureText = "DELIVERED BACKLOG ITEMS: dcCliCommandFactsAuthored (resolves issue344); dcUnknownMarkerRefused (resolves issue346, found while recording this sprint's own Decision: an unknown marker value was dropped silently and the locked-file edit was refused for want of it). DONE: .engine/cli/commands.sysml with 65 command and 35 lens CliCommand facts in ten families; cli_facts.rs mirrors them and renders keel --help grouped by family, replacing the hand-written CATALOGUE that had listed three show lenses as verbs since D0273; guard 58 cli-surface-declared holds facts, mirror and dispatch equal both ways, field by field; .engine/cli/ joins the check-engine instance set; the hardening help-coverage lens reads the rendered facts instead of main.rs source; six guards gained their missing guards.md rows and a test keeps the catalogue complete; CLAUDE.md invariant 8 says what is true and carries no count. VERIFY: the guard armed live both ways before landing; the live facts, mirror and dispatch agree (unit test); keel version reports 58 guards."; }
        // RAN: cargo test -p keel-cli --lib guards::cli_surface_declared_tests 4/4; hardening every_dispatched_subcommand_is_documented 1/1 over rendered facts; guard_catalogue_tests 1/1; keel guard cli-surface-declared . 100 scanned 0 violations; ARMED: status effect flipped -> 1 violation; orient fact deleted -> 2 violations; restored -> PASS; keel --help 100 rows
        part storyCliFactsDoDR1 : TestResult { :>> id = "bc9d5e3f-4a61-4c78-d9e0-f1a2b3c4d5e6"; :>> outcome = VerdictKind::pass; :>> judgedAgainst = "52424e3"; :>> judgedAt = "2026-09-02"; :>> judgedBy = "claudeOpus5"; }
    }

    verification cliFactsRefineGate : Test { :>> id = "cda0e640-5b72-4d89-e0f1-a2b3c4d5e6f7"; :>> title = "Sprint 519 refine gate (DoR)"; :>> createdAt = "2026-09-02"; :>> createdBy = "claudeOpus5"; :>> method = VerificationMethod::inspect; :>> procedureText = "READY because D0271 had already designed the schema and named the deferral condition, D0273 had discharged it, and cli_surface.rs held the exact inventory (65 + 35) to author against - the facts were a transcription of dispatch plus a judgment per command about effect. The one open question at refine was where the help's home is when the binary must work without a tree; answered by the mirror-held-equal pattern COMMAND_NAMES already uses."; }
    verification cliFactsStandupGate : Test { :>> id = "deb1f751-6c83-4e9a-f102-b3c4d5e6f708"; :>> title = "Sprint 519 standup gate"; :>> createdAt = "2026-09-02"; :>> createdBy = "claudeOpus5"; :>> method = VerificationMethod::inspect; :>> procedureText = "TWO CHOICES. (1) The effect values are judgments and were made explicit: ten commands are both (read to decide, then write), advance is reads because the cursor is computed and --to refuses rather than stamps, four are tooling. A status command that writes is now a guard violation - the property D0270 built status to hold and nothing had tested. (2) The facts were generated from one table into both files ONCE, and the generator is not committed: after landing, the .sysml is the home and the guard is what keeps the mirror honest - a committed generator would have been a third home."; }
    verification cliFactsImplementGate : Test { :>> id = "efc20862-7d94-4fab-0213-c4d5e6f70819"; :>> title = "Sprint 519 implement gate"; :>> createdAt = "2026-09-02"; :>> createdBy = "claudeOpus5"; :>> method = VerificationMethod::test; :>> procedureText = "RAN: the cross-check of facts against COMMAND_NAMES and LENS_NAMES before any Rust was written - zero in either direction; the hardening test then found the one name the facts did not carry, --version, and the fact for version now names it. Guard armed live: status effect flipped to writes -> one violation naming status and both sides; orient fact deleted -> two violations, mirror-without-fact and dispatched-without-fact; restored -> PASS with 100 scanned. Six guards had no guards.md row - five of them older than this sprint - and now do, with a test that fails the build on the next omission."; }
    verification cliFactsReviewGate : Test { :>> id = "f0d31973-8ea5-4abc-1324-d5e6f708192a"; :>> title = "Sprint 519 review gate — three passes per D0172"; :>> createdAt = "2026-09-02"; :>> createdBy = "claudeOpus5"; :>> method = VerificationMethod::inspect; :>> procedureText = "THREE PASSES. (1) IS THE MIRROR A SECOND HOME: no - it is checked field by field against the .sysml on every gate, and a mirror held equal by a control is the same shape as COMMAND_NAMES versus the dispatch. (2) DID THE HELP LOSE ANYTHING: the old block's decision citations and parentheticals are gone on purpose (D0270: a synopsis is what a user needs to run it); every dispatched arm is still named, checked by the same test that found --version. (3) IS THE DOC SURFACE TRUE: invariant 8 no longer claims a count or an unauthored fact; the guards.md catalogue is complete and tested; the D0271 decision file still says NOT YET AUTHORED in its own text and stays so - an accepted Decision's text is history, and D0283 records what changed."; }
    verification cliFactsCloseOutGate : Test { :>> id = "01e42a84-9fb6-4bcd-2435-e6f708192a3b"; :>> title = "Sprint 519 closeOut gate (autonomous, D0049)"; :>> createdAt = "2026-09-02"; :>> createdBy = "claudeOpus5"; :>> method = VerificationMethod::inspect; :>> procedureText = "CLOSED. issue344 resolved. The computed control structure (dcControlStructureIsComputed, next on the frontier) has its source for the agent's write actions and read feedback: effect on 100 facts."; }
    verification cliFactsRetroGate : Test { :>> id = "12f53b95-a0c7-4cde-3546-f708192a3b4c"; :>> title = "Sprint 519 retro gate (autonomous, D0049)"; :>> createdAt = "2026-09-02"; :>> createdBy = "claudeOpus5"; :>> method = VerificationMethod::analyze; :>> procedureText = "ADDED THIS COMMIT: issue346 (the silent marker drop, fixed in the same commit with its test). Otherwise already tracked: the two other findings of this sprint are the stale help (the D0273 residue the facts replace, recorded in D0283) and the five undocumented guards (fixed here with a permanent test, no Issue needed because the control now exists and nothing recurs without it). The pattern worth naming is the same as issue344 itself: a Decision that defers work until a condition is met has no mechanism that fires when the condition is met - D0271 waited on D0273 and nobody was reminded. decision-follow-through already reports accepted Decisions with no downstream item, and D0271 was one of its rows; the lens was right and unread."; }
}
