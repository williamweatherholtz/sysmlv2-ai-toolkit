// ProjectDeliveryS177 — Sprint 177: businessArchitectureSkill (D0105 / issue054-F1 root).
// The Business + Architecture workflows were INERT (defined, no deploying skill, contra D0059) — the real
// root of issue054 F1, and why a keel-blind brainstorming skill filled the vacuum. FIX (Part 1): author
// the keel-native business-architecture skill that DEPLOYS both workflows (needs-before-architecture,
// point-of-decision recording, output=authored facts not prose). Part 2 (workflow-coverage ENFORCEMENT)
// folds into guardsToRulesMigration as a declared EdgeRule (D0105), not bespoke Rust. EXECUTE. 1 pt. AUTONOMOUS (D0049).
package ProjectDeliveryS177 {
    private import EngineElement::*;
    private import EngineWork::*;
    private import EngineVerification::*;
    private import EngineRelationships::*;

    #CharteredBy dependency from businessArchStory to d0105;

    part businessArchStory : Story {
        :>> id = "63940516-2c7d-4e8f-c177-51627384c001";
        :>> title = "Sprint 177: businessArchitectureSkill (1 pt) - deploy the inert Business/Architecture workflows via a keel-native design skill (issue054-F1 root)";
        :>> createdAt = "2026-07-02"; :>> createdBy = "wweatherholtz"; :>> kind = WorkKind::documentation; :>> priority = WorkPriority::p2; :>> owner = "claudeOpus"; :>> estimatedPoints = 1;
    }

    action def DeliveryRunS177 {
        action storyBusinessArch;
        verification storyBusinessArchDoD : Test { :>> id = "63940516-2c7d-4e8f-c177-51627384c002"; :>> method = VerificationMethod::inspect; :>> procedureText = "Root fix of issue054 F1 (Part 1). Authored .engine/skills/business-architecture/SKILL.md — the keel-native design skill that DEPLOYS the Business workflow (.engine/workflows/business.sysml: Brief->Personas->Needs->UseCases) then the Architecture workflow (.engine/workflows/architecture.sysml): the non-negotiable ordering rule (Needs upstream of architecture; may explore early, may not RECORD architecture before accepted Needs); record every decision AT THE POINT OF DECISION as a Decision (proposed until its gate); output = AUTHORED FACTS (Brief/Needs/Decisions/SystemRequirements + typed edges), NEVER a prose design doc; one-source-of-truth (D0105/issue058); parse-first + explicit human sign-off gates (D0106). Registered in skills-registry (businessArchitectureSkill), naming the two workflows it deploys. Replaces the keel-blind brainstorming skill for keel projects. SCOPE: Part 2 (workflow-coverage enforcement) is a declared EdgeRule in guardsToRulesMigration (D0105), not bespoke Rust. VERIFY: skill file + registry entry exist; kernel validate_instances PASS (registry); keel validate + guard all green; doc-sync."; }
        part storyBusinessArchDoDR1 : TestResult { :>> id = "63940516-2c7d-4e8f-c177-51627384c003"; :>> outcome = VerdictKind::pass; :>> judgedAgainst = "e96b36f"; :>> judgedAt = "2026-07-02"; :>> judgedBy = "claudeOpus"; }
    }

    verification businessArchRefineGate : Test { :>> id = "63940516-2c7d-4e8f-c177-51627384c004"; :>> title = "Sprint 177 refine gate (DoR)"; :>> createdAt = "2026-07-02"; :>> createdBy = "claudeOpus"; :>> method = VerificationMethod::inspect; :>> procedureText = "DoR: issue054 F1 root (inert Business/Architecture workflows). Author their deploying skill; route the coverage enforcement to the D0105 migration. estimatedPoints=1. #CharteredBy d0105. DoR met."; }
    part businessArchRefineGateR1 : TestResult { :>> id = "63940516-2c7d-4e8f-c177-51627384c005"; :>> outcome = VerdictKind::pass; :>> judgedAgainst = "e96b36f"; :>> judgedAt = "2026-07-02"; :>> judgedBy = "claudeOpus"; }
    verification businessArchStandupGate : Test { :>> id = "63940516-2c7d-4e8f-c177-51627384c006"; :>> title = "Sprint 177 standup gate"; :>> createdAt = "2026-07-02"; :>> createdBy = "claudeOpus"; :>> method = VerificationMethod::inspect; :>> procedureText = "Approach: author the business-architecture SKILL.md (deploys both workflows; needs-before-architecture; point-of-decision recording; authored-facts-not-prose; D0105/D0106 bound); register it; scope Part 2 to the migration. No blockers (doc + registry; kernel-validate the registry)."; }
    part businessArchStandupGateR1 : TestResult { :>> id = "63940516-2c7d-4e8f-c177-51627384c007"; :>> outcome = VerdictKind::pass; :>> judgedAgainst = "e96b36f"; :>> judgedAt = "2026-07-02"; :>> judgedBy = "claudeOpus"; }
    verification businessArchImplementGate : Test { :>> id = "63940516-2c7d-4e8f-c177-51627384c008"; :>> title = "Sprint 177 implement gate"; :>> createdAt = "2026-07-02"; :>> createdBy = "claudeOpus"; :>> method = VerificationMethod::inspect; :>> procedureText = "business-architecture SKILL.md authored + registered (businessArchitectureSkill names both workflows). kernel validate_instances PASS; keel validate + guard all green. Part 2 routed to guardsToRulesMigration."; }
    part businessArchImplementGateR1 : TestResult { :>> id = "63940516-2c7d-4e8f-c177-51627384c009"; :>> outcome = VerdictKind::pass; :>> judgedAgainst = "e96b36f"; :>> judgedAt = "2026-07-02"; :>> judgedBy = "claudeOpus"; }
    verification businessArchReviewGate : Test { :>> id = "63940516-2c7d-4e8f-c177-51627384c00a"; :>> title = "Sprint 177 review gate"; :>> createdAt = "2026-07-02"; :>> createdBy = "claudeOpus"; :>> method = VerificationMethod::inspect; :>> procedureText = "Reviewed. The skill fills the exact vacuum that caused issue054 F1 (an inert workflow with no deployer) and encodes the hard-won lessons of this session — needs-before-architecture, point-of-decision recording, authored-facts-not-prose, one-source-of-truth, parse-first. It supersedes the keel-blind brainstorming skill in intent. Enforcement correctly deferred to a declared EdgeRule (D0105), avoiding throwaway bespoke Rust. Clean."; }
    part businessArchReviewGateR1 : TestResult { :>> id = "63940516-2c7d-4e8f-c177-51627384c00b"; :>> outcome = VerdictKind::pass; :>> judgedAgainst = "e96b36f"; :>> judgedAt = "2026-07-02"; :>> judgedBy = "claudeOpus"; }
    verification businessArchCloseOutGate : Test { :>> id = "63940516-2c7d-4e8f-c177-51627384c00c"; :>> title = "Sprint 177 closeOut gate (autonomous, D0049)"; :>> createdAt = "2026-07-02"; :>> createdBy = "claudeOpus"; :>> method = VerificationMethod::inspect; :>> procedureText = "Autonomous closeOut (D0049): DoD pass; the Business/Architecture workflows now have a deploying skill (no longer inert). keel validate + guard all green; kernel registry PASS. Self-evidencing (D0051)."; }
    part businessArchCloseOutGateR1 : TestResult { :>> id = "63940516-2c7d-4e8f-c177-51627384c00d"; :>> outcome = VerdictKind::pass; :>> judgedAgainst = "e96b36f"; :>> judgedAt = "2026-07-02"; :>> judgedBy = "claudeOpus"; }
    verification businessArchRetroGate : Test { :>> id = "63940516-2c7d-4e8f-c177-51627384c00e"; :>> title = "Sprint 177 retro gate (autonomous, D0049)"; :>> createdAt = "2026-07-02"; :>> createdBy = "claudeOpus"; :>> method = VerificationMethod::analyze; :>> procedureText = "Autonomous retro (D0049). WELL: the deepest root of the whole ignite episode (an inert workflow with no keel-native deployer) is now closed with a skill that encodes the session's lessons, so future design happens by deploying the workflows, not chatting. AVOIDABLE-ISSUE SCAN: the avoidable root was a declared-but-undeployed workflow slipping past the process-skill guard (it scans only .engine/processes/, not workflows) — the workflow-coverage EdgeRule (guardsToRulesMigration) will make that class un-recurring; LESSON: a DEFINITION without a DEPLOYER is inert (D0059) and must be guarded at the workflow level too. Estimate 1 pt held. Remaining unblocked: serveBusinessNeedsView; the big frozen-core migration (declarativeControlsEvaluator, guardsToRulesMigration) is now sign-off-unblocked."; }
    part businessArchRetroGateR1 : TestResult { :>> id = "63940516-2c7d-4e8f-c177-51627384c00f"; :>> outcome = VerdictKind::pass; :>> judgedAgainst = "e96b36f"; :>> judgedAt = "2026-07-02"; :>> judgedBy = "claudeOpus"; }
}
