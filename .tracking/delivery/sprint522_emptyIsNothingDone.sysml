// ProjectDeliveryS522 — Sprint 522: an empty population is nothing done, never a clean sweep. CHANGE. 2 pts.
package ProjectDeliveryS522 {
    private import EngineElement::*;
    private import EngineWork::*;
    private import EngineVerification::*;
    private import EngineRelationships::*;

    #CharteredBy dependency from emptyIsNothingDoneStory to d0286;

    part emptyIsNothingDoneStory : Story {
        :>> id = "e090a95b-0a6e-4453-8752-2189da2651da";
        :>> title = "Sprint 522: 0/0 reads 0 percent and NOTHING TO ASSURE everywhere keel computes a ratio or a readiness verdict, with a scan that refuses the next vacuous 100 (2 pts)";
        :>> createdAt = "2026-09-03"; :>> createdBy = "claudeOpus5"; :>> kind = WorkKind::code; :>> priority = WorkPriority::p0; :>> owner = "claudeOpus5"; :>> estimatedPoints = 2;
    }

    action def DeliveryRunS522 {
        action storyEmptyIsNothingDone;
        verification storyEmptyIsNothingDoneDoD : Test { :>> id = "150212a5-a33a-4fb9-a5b0-9d55abd1b3dd"; :>> method = VerificationMethod::test; :>> procedureText = "DELIVERED BACKLOG ITEMS: dcEmptyIsNothingDone. The human (st071): inheriting projects get a clean sweep of 100 percent when 0/0 should read 0 percent - nothing is done yet. MEASURED on a fresh scaffold: three 100 percent cards and READY in report assurance, pct 100 per empty tier, assured ready true. DONE: every pct helper returns 0 on an empty denominator (reports.rs, verification.rs); a missing tier is 0; readiness carries the governed count and is false over nothing, with a three-valued verdict - NOTHING TO ASSURE / READY / NOT READY - emitted by assured and both report sites; an empty tone on ratio cards, rendered neutral in the console and report CSS; the pinned 'vacuously complete' test inverted; a source-scan test refusing any division whose fallback is 100. VERIFY: scaffold sweep of 16 lenses and reports finds no 100, READY or PASS-over-nothing; this repository's verdicts unchanged (NOT READY, 379 governed); the scan armed against a planted map_or(100 in pm.rs and caught it by file and line."; }
        // RAN: keel report assurance / show tier-satisfaction / assured on a fresh scaffold, before and after; sweep loop over audit, hardening, 8 show lenses, 5 reports, status -> no hits; cargo test --lib empty_population_tests 3/3; planted map_or(100 -> no_division_in_the_crate FAILED naming src/pm.rs:126, reverted -> ok; full suite 445/0; clippy clean
        part storyEmptyIsNothingDoneDoDR1 : TestResult { :>> id = "1c0252fe-1e7a-44cc-bcba-ff3d820d2f5f"; :>> outcome = VerdictKind::pass; :>> judgedAgainst = "4674965"; :>> judgedAt = "2026-09-03"; :>> judgedBy = "claudeOpus5"; }
    }

    verification emptyIsNothingDoneRefineGate : Test { :>> id = "90334f09-b59f-4ec4-b89d-b692b7b29b5d"; :>> title = "Sprint 522 refine gate (DoR)"; :>> createdAt = "2026-09-03"; :>> createdBy = "claudeOpus5"; :>> method = VerificationMethod::inspect; :>> procedureText = "READY because the defect reproduced in one command on a scaffold and the crate already held the correct convention in one place (hardening.rs: an empty population has no percentage), so the question was not what right looks like but how many places were wrong. A grep for ratio sites found 51; reading them found four that chose full for empty, and a scan test found a fifth the reading missed."; }
    verification emptyIsNothingDoneStandupGate : Test { :>> id = "f01c7fec-9fa6-4f1e-90ed-6073bc3b897d"; :>> title = "Sprint 522 standup gate"; :>> createdAt = "2026-09-03"; :>> createdBy = "claudeOpus5"; :>> method = VerificationMethod::inspect; :>> procedureText = "TWO CHOICES. (1) 0, not null: the human asked for 0 to say nothing is done; the pct JSON contract is an integer the console renders, and a null would break consumers for a distinction the new empty tone carries instead; hardening's None-with-reason stays where the statement is 'nothing found', which differs from 'nothing done'. (2) A THIRD verdict rather than flipping READY to NOT READY: a fresh project has not failed anything, and naming the empty case is what lets a reader tell a project that has done nothing from one that has done things badly. The fix reached for by instinct would have been NOT READY, which is the same conflation in the other direction."; }
    verification emptyIsNothingDoneImplementGate : Test { :>> id = "c405c127-e3c6-4eeb-affc-b7025ade8d57"; :>> title = "Sprint 522 implement gate"; :>> createdAt = "2026-09-03"; :>> createdBy = "claudeOpus5"; :>> method = VerificationMethod::test; :>> procedureText = "RAN: scaffold before and after on three surfaces; a sweep loop over every lens and report on the scaffold - zero hits; the scan test written, then armed by planting checked_div(0).map_or(100 in pm.rs - it failed naming src/pm.rs:126, and passed again after the revert. The scan also refused the first draft of its own file (its pattern line) and a second arm in verification.rs I had read past; both were real. Two heredoc backslash traps hit (a \\u escape in a Rust string) and worked around through the Write tool, as the recorded memory says."; }
    verification emptyIsNothingDoneReviewGate : Test { :>> id = "494b046c-7a03-40cb-abba-6b52bb0c48ab"; :>> title = "Sprint 522 review gate — three passes per D0172"; :>> createdAt = "2026-09-03"; :>> createdBy = "claudeOpus5"; :>> method = VerificationMethod::inspect; :>> procedureText = "THREE PASSES. (1) DID ANY NON-EMPTY RESULT CHANGE: no - this repository reads NOT READY with 379 governed before and after, and pct over a non-zero denominator is the same arithmetic. (2) IS THE CONTROL REAL OR DECORATIVE: armed against a planted defect and it fired by file and line; it also excludes comments and its own pattern line, so it cannot be satisfied by rewording. (3) WHERE THIS CAME FROM: the human observed it across projects, not here - the engine's own repo is never empty, which is exactly why the vacuous case survived four authors."; }
    verification emptyIsNothingDoneCloseOutGate : Test { :>> id = "5fadf32c-ed56-4686-83d7-a6085eb6ef99"; :>> title = "Sprint 522 closeOut gate (autonomous, D0049)"; :>> createdAt = "2026-09-03"; :>> createdBy = "claudeOpus5"; :>> method = VerificationMethod::inspect; :>> procedureText = "CLOSED. Downstream projects receive the change with the next engine vintage; their earlier 100 percent readings were never facts, so nothing migrates."; }
    verification emptyIsNothingDoneRetroGate : Test { :>> id = "b7107b9d-bcd8-4dad-958d-15abd95a51ef"; :>> title = "Sprint 522 retro gate (autonomous, D0049)"; :>> createdAt = "2026-09-03"; :>> createdBy = "claudeOpus5"; :>> method = VerificationMethod::analyze; :>> procedureText = "no new item - already tracked: the finding is structural and the Decision records it - the engine repository is never empty, so the empty case is only ever observed downstream, and the realistic-fixture tests (D0275) are where such cases belong. The scaffold sweep loop used here is the shape of a test that should run there; it is folded into this sprint's evidence rather than opened as an item because the scan test now catches the defect class at its source, before any surface renders it."; }
}
