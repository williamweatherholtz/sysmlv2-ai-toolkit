// ProjectDeliveryS483 — Sprint 483: author the twelve Needs the code has and the model never stated. EXECUTE. 8 pts.
package ProjectDeliveryS483 {
    private import EngineElement::*;
    private import EngineWork::*;
    private import EngineVerification::*;
    private import EngineRelationships::*;

    #CharteredBy dependency from needSetRederivationStory to d0246;

    part needSetRederivationStory : Story {
        :>> id = "f6396f5d-e1d9-4575-a69a-f300057b9c1e";
        :>> title = "Sprint 483: the Need set is re-derived from the code (8 pts)";
        :>> createdAt = "2026-08-28"; :>> createdBy = "claudeOpus5"; :>> kind = WorkKind::modeling; :>> priority = WorkPriority::p0; :>> owner = "claudeOpus5"; :>> estimatedPoints = 8;
    }

    action def DeliveryRunS483 {
        action storyNeedSetRederivation;
        verification storyNeedSetRederivationDoD : Test { :>> id = "bba6057b-5fb9-45e5-b19e-8c6e4f666510"; :>> method = VerificationMethod::test; :>> procedureText = "DELIVERED: D0246 (keel's subject is AI work management; the twelve Needs; no backfill) and .tracking/business/engine-needs.sysml carrying twelve Needs, each with a #DerivedFrom edge to us029. DONE MEANS: the twelve capabilities the bottom-up pass found unstated now have a stated direction, and NOTHING ELSE MOVED. VERIFY: keel validate clean; check-engine clean; keel guard all-pass; the twelve Needs appear in `keel business`; each of the twelve resolves a #DerivedFrom edge to us029 (edge-endpoints guard green); tier-satisfaction's Need tier FALLS from 100 percent to 82 (58/70) reporting exactly the twelve new Needs as gaps, and rootedness's need_rooted count is UNCHANGED at 53 - both are the pass working, per D0246 clause C, and a run where the gap count did not rise would mean requirements were authored that do not exist. decision_ungrounded goes 415 -> 416: this sprint's OWN story is chartered by D0246, which reaches no Need, so the ungrounded count rises by exactly the one story this sprint added. need_rooted, not decision_ungrounded, is the count that must not move - a rise there would mean existing stories were re-parented onto the new Needs, which clause C forbids."; }
        // RAN: / RAN at the time (2026-08-28, landed in 1a6d660..e2f03a5): keel validate 541 clean; check-engine clean; guard ALL PASS; keel business showed all twelve; tier-satisfaction fell 100->82 with exactly the twelve as gaps; need_rooted unchanged at 53. STAMPED LATE: the DoD result was never appended when the sprint closed - found by the priority-assessment pass seeing the story on the ready frontier
        part storyNeedSetRederivationDoDR1 : TestResult { :>> id = "7f61e5ed-74c5-46d7-8f81-3cbe511e96a8"; :>> outcome = VerdictKind::pass; :>> judgedAgainst = "32149b5"; :>> judgedAt = "2026-08-29"; :>> judgedBy = "claudeOpus5"; }
    }

    verification needSetRederivationRefineGate : Test { :>> id = "79e130e3-e7b8-4b1f-af7a-03c75fed2ab4"; :>> title = "Sprint 483 refine gate (DoR)"; :>> createdAt = "2026-08-28"; :>> createdBy = "claudeOpus5"; :>> method = VerificationMethod::inspect; :>> procedureText = "READY: the charter D0246 exists and names the twelve; the human's instruction is a recorded utterance (st023) with a translation (us029) the Needs can cite, so no Need rests on my judgment alone; the twelve are enumerated from a completed derivation rather than brainstormed, each traceable to a named artifact (schema package, write path, command, process, guard or contract). SCOPE IS BOUNDED BY WHAT IT EXCLUDES: no SystemRequirement, no story re-parenting, no nViewer Need moved, no STPA verdict."; }
    verification needSetRederivationStandupGate : Test { :>> id = "3f23b3a8-0a8b-4691-81e6-cbab6e991e70"; :>> title = "Sprint 483 standup gate"; :>> createdAt = "2026-08-28"; :>> createdBy = "claudeOpus5"; :>> method = VerificationMethod::inspect; :>> procedureText = "No blocker. The one dependency was issue300 - the write path accepted 12 of the schema's 15 ImplicationKind members, so the triage that routes this work could not be recorded honestly. Fixed and landed at 1a6d660 before this sprint opened, which is why us036 (designChange) and us038/us042 (verifiedRequirement) exist to be cited here."; }
    verification needSetRederivationImplementGate : Test { :>> id = "c90ad7d9-3d31-4d70-a8ce-8732f17b54b4"; :>> title = "Sprint 483 implement gate"; :>> createdAt = "2026-08-28"; :>> createdBy = "claudeOpus5"; :>> method = VerificationMethod::test; :>> procedureText = "RAN: keel validate . (541 files clean); keel check-engine .; keel guard; keel business . (the twelve present); keel tier-satisfaction . and keel rootedness . read back AFTER the write. THE ASSERTION THAT COULD FAIL: the Need tier must FALL and report twelve gaps. Observed 100 percent -> 82 (58/70), gap set exactly the twelve. A gate that demanded it stay at 100 percent would be satisfied only by authoring requirements for work nobody has done - the issue088 error inverted, where a metric points a contributor at wrong work. THE NO-BACKFILL ASSERTION is need_rooted, observed unchanged at 53: a RISE there would mean existing stories were re-parented onto the new Needs, which D0246 clause C forbids. decision_ungrounded moved 415 -> 416 and that is correct, not a violation - this sprint's own story is chartered by D0246 and D0246 reaches no Need, so the count rises by exactly the one story added. I asserted 'unchanged at 415' when authoring this gate and the read-back disproved it; the number recorded here is the observed one."; }
    verification needSetRederivationReviewGate : Test { :>> id = "8e3f6c1f-377d-40f8-820c-5a9d129444b3"; :>> title = "Sprint 483 review gate — three passes per D0172"; :>> createdAt = "2026-08-28"; :>> createdBy = "claudeOpus5"; :>> method = VerificationMethod::inspect; :>> procedureText = "THREE ADVERSARIAL PASSES OVER THE TWELVE. (1) WIDER-THAN-ASKED, the D0157 lens: each statement is read against what the code actually does, and any clause reaching past the observed capability is cut - a Need written wider than the evidence is how N-8 came to overstate its scope. (2) DUPLICATION: each of the twelve is checked against the 58 live Needs for restatement under another name, since a duplicate Need splits satisfaction across two parents and hides a gap in both. (3) COMPUTED-STATE LEAKAGE: no statement may assert a status, readiness or coverage claim, which would put authored prose where a view belongs. The human's read-back is a SEPARATE gate and is not this one: per D0157 they are asked what is WIDER than they meant, never whether the set is good."; }
    verification needSetRederivationCloseOutGate : Test { :>> id = "12a7b893-4bd4-4d0f-a089-f6b4c4c832c2"; :>> title = "Sprint 483 closeOut gate (autonomous, D0049)"; :>> createdAt = "2026-08-28"; :>> createdBy = "claudeOpus5"; :>> method = VerificationMethod::inspect; :>> procedureText = "CLOSED WITH ITS DEBT NAMED, not hidden: the twelve Needs have no SystemRequirements and no verification, deliberately, so twelve Need-tier gaps and twelve uncovered Needs are the recorded outcome of this sprint rather than a defect in it. Two portability defects found while committing wave 0 - machine-absolute path keys under the decision-channel unit in installed-units.toml, and unit version bumps with no content change - are NOT recorded as Issues here: record issue requires an existing resolver, and the honest resolver is a story that does not exist yet. They are named in this gate so they survive the sprint boundary and are filed against the portability work when it is chartered."; }
    verification needSetRederivationRetroGate : Test { :>> id = "c929d1cd-62a8-4f03-8b55-b77e6fb7e432"; :>> title = "Sprint 483 retro gate (autonomous, D0049)"; :>> createdAt = "2026-08-28"; :>> createdBy = "claudeOpus5"; :>> method = VerificationMethod::analyze; :>> procedureText = "FINDING 1, the one worth keeping: the Need set was inverted relative to the code for a long time and NO VIEW SAID SO. tier-satisfaction reported 100 percent because it only ever measures requirements hanging off Needs, never whether the Needs describe the system; rootedness held the honest number - 415 of 482 ungrounded - and nothing ranked it or raised it. A metric that can only be read by someone who already suspects the answer is not a control. BECOMES TRACKED WORK: the latent-need derivation process, with rootedness's ungrounded ratio as its computed trigger rather than a periodic reminder (D0047: manual vigilance is not a control). FINDING 2: the vocabulary defect (issue300) was found only because a real triage was refused - the schema declared 15 members and the binary accepted 12 for as long as both existed. It was the FOURTH constant of its kind after issue119/issue120 built schema.rs precisely to end the class, which says the earlier fix removed three instances without removing the ability to add a fourth. BECOMES TRACKED WORK: a check that no binary constant restates a schema enum, so the fifth is a red gate rather than a discovery."; }
}
