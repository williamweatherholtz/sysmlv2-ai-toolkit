// ProjectDeliveryS678 — Sprint 678: The rendering family folds into one verb. Under D0449 (d0399 option A, the human's word 2026-09-11) `keel diagram`, `keel report` and `keel decision-card` leave the top-level dispatch and become `keel render model`, `keel render report <kind>` and `keel render decision-card`, in the sprint 512 shape (D0273): a committed transform rewrites every call site in the same commit, no alias window, and the pre-fold binary is held byte-equal to the post-fold binary on every moved verb. Delivers the first of the five folds dcRemainingCliFamilies names; the dispatch count hardening reads drops 72 to 69. CHANGE.. EXECUTE. 2 pts.
package ProjectDeliveryS678 {
    private import EngineElement::*;
    private import EngineWork::*;
    private import EngineVerification::*;
    private import EngineRelationships::*;

    #CharteredBy dependency from renderFamilyFoldStory to d0449;

    part renderFamilyFoldStory : Story {
        :>> id = "dda18134-38e5-434d-a7dc-f6e213c8c751";
        :>> title = "Sprint 678: The rendering family folds into one verb. Under D0449 (d0399 option A, the human's word 2026-09-11) `keel diagram`, `keel report` and `keel decision-card` leave the top-level dispatch and become `keel render model`, `keel render report <kind>` and `keel render decision-card`, in the sprint 512 shape (D0273): a committed transform rewrites every call site in the same commit, no alias window, and the pre-fold binary is held byte-equal to the post-fold binary on every moved verb. Delivers the first of the five folds dcRemainingCliFamilies names; the dispatch count hardening reads drops 72 to 69. CHANGE. (2 pts)";
        :>> createdAt = "2026-09-11"; :>> createdBy = "claudeOpus5"; :>> kind = WorkKind::code; :>> priority = WorkPriority::p0; :>> owner = "claudeOpus5"; :>> estimatedPoints = 2;
    }

    action def DeliveryRunS678 {
        action storyRenderFamilyFold;
        verification storyRenderFamilyFoldDoD : Test { :>> id = "548d1b68-d989-4af7-b7ad-c390bbb5bf84"; :>> method = VerificationMethod::test; :>> procedureText = "DELIVERED: `keel render` resolves `model`|`all`|`whole`, `report <kind>`, `decision-card [NAME]` before any declared view, in an order held by cli_surface::RENDER_RESERVED and a test that reads .engine/views for a shadowed name; the three top-level arms are gone from main.rs, COMMAND_NAMES (71 to 68), CLI_FACTS (111 to 108) and .engine/cli/commands.sysml; every call site under .engine, CLAUDE.md, README.md, docs, scripts and keel-cli/assets is rewritten by .engine/tools/migrations/2026-09-11-render-family-fold.py (dry-run default, per-file conservation, re-plan 0); .claude regenerated by keel sync-claude; the pre-fold binary (build 10b6912) and the post-fold binary agree byte for byte on 12 report cases and 3 decision-card cases, and on sorted lines for the whole-model graph whose run-to-run order is issue495; hardening reads dispatched 69/69; validate, check-engine, guard, the touched suite and the D0449 reserved-word tests pass. Decisions and .tracking are not rewritten; the stpa fixture is not rewritten."; }
        // RAN: keel render model . / keel render report assurance . / keel render decision-card d0449 . on keel-serve.exe: all three answer; keel diagram / keel report / keel decision-card: unknown command; keel show hardening .: 69 of 69 dispatched; compare678.txt 17/18 EQUAL; keel suite --touched pass 776/0
        part storyRenderFamilyFoldDoDR1 : TestResult { :>> id = "e6e960ca-8a73-4d53-adbe-e6c5a807c3e5"; :>> outcome = VerdictKind::pass; :>> judgedAgainst = "5fcd953"; :>> judgedAt = "2026-09-11"; :>> judgedBy = "claudeOpus5"; }
    }

    verification renderFamilyFoldRefineGate : Test { :>> id = "ad1f04fd-d185-4674-bc59-67041b357a37"; :>> title = "Sprint 678 refine gate (DoR)"; :>> createdAt = "2026-09-11"; :>> createdBy = "claudeOpus5"; :>> method = VerificationMethod::inspect; :>> procedureText = "Chartered by D0449, plan-covered under D0396 by d0399 option A, accepted by the human 2026-09-11 on the brief copy-out. Two points: three dispatch arms move under one verb, one Python transform, two constant arrays, one SysML surface file, thirteen prose files. Same shape as sprint 512, whose transform is the template. NOT A PROCESS CHANGE beyond what D0449 states - the fold is the Decision's own text. NOT A FORK - the fork was d0399 and is decided."; }
    // RAN: keel show authority-queue . before the sprint: d0399 option A accepted 2026-09-11 (brief copy-out); keel show item dcRemainingCliFamilies: ready
    part renderFamilyFoldRefineGateR1 : TestResult { :>> id = "ab5a97f5-5b83-4421-b093-806144ef865a"; :>> outcome = VerdictKind::proposed; :>> judgedAgainst = "5fcd953"; :>> judgedAt = "2026-09-11"; :>> judgedBy = "claudeOpus5"; }
    verification renderFamilyFoldStandupGate : Test { :>> id = "07d19760-7994-442c-a662-59ed98c6ac4b"; :>> title = "Sprint 678 standup gate"; :>> createdAt = "2026-09-11"; :>> createdBy = "claudeOpus5"; :>> method = VerificationMethod::inspect; :>> procedureText = "Order: build and preserve the pre-fold binary as keel-prefold.exe; move the arms in main.rs and drop cmd_diagram (render model already drew the same graph); shrink COMMAND_NAMES and CLI_FACTS and commands.sysml together so cli-surface-declared stays equal; add RENDER_RESERVED with its shadowing test; write the transform, dry-run, apply, sync-claude; rebuild; compare old against new back to back on the same tree; read hardening; record. Blocker met: the graph is not deterministic run to run, so raw byte equality could not hold on it - held on sorted lines and tracked as issue495 with dcRenderModelIsDeterministic as resolver, rather than sorted silently."; }
    // RAN: cp target/release/keel.exe target/release/keel-prefold.exe (build 10b6912); keel-prefold.exe version printed 10b6912
    part renderFamilyFoldStandupGateR1 : TestResult { :>> id = "cdc803c9-5e1f-420d-88c5-6bf38b6b1f38"; :>> outcome = VerdictKind::proposed; :>> judgedAgainst = "5fcd953"; :>> judgedAt = "2026-09-11"; :>> judgedBy = "claudeOpus5"; }
    verification renderFamilyFoldImplementGate : Test { :>> id = "458af752-14fe-4162-9987-7813bb89630b"; :>> title = "Sprint 678 implement gate"; :>> createdAt = "2026-09-11"; :>> createdBy = "claudeOpus5"; :>> method = VerificationMethod::test; :>> procedureText = "keel-cli/src/main.rs: cmd_render routes report and decision-card to the unchanged cmd_report / cmd_decision_card with args[1..]; cmd_diagram deleted; three dispatch arms removed; usage lines name the three shapes. cli_surface.rs: COMMAND_NAMES 68, RENDER_RESERVED [all, control-structure, decision-card, model, report, whole], is_render_reserved, two tests. cli_facts.rs 108 facts, one render fact carrying the folded invocation. .engine/cli/commands.sysml: cliDiagram, cliReport, cliDecisionCard removed, cliRender invocation and synopsis equal to the fact. serve.rs NOT_A_COMPUTED_VIEW 7. Tests flow_cycle_time_from_git and supersession_is_said_once call the new spelling; guards.rs classify_renderer tests, reports.rs title and generator metas, flow.rs, deck.rs, write.rs doc comments updated. Transform applied: 23 call sites across 13 files, re-plan 0. guards.md carried no call site, nothing to rewrite there."; }
    // RAN: python .engine/tools/migrations/2026-09-11-render-family-fold.py --dry-run then --apply: 23 call site(s) across 13 file(s), re-plan finds 0 remaining; cargo build --release ok; cargo test -p keel-cli --release cli_surface: 10 passed; cargo test --test capability_refusal_bites: 5 passed; cargo clippy --release --all-targets -- -D warnings: exit 0 (after fix_clippy678); keel suite --touched: pass - 776 passed, 0 failed in 458s, receipt .keel/metrics/touched-receipt.toml at=1789164892 head=f33af01 stems cli_facts cli_surface deck flow guards reports serve write
    part renderFamilyFoldImplementGateR1 : TestResult { :>> id = "4feaae97-090c-4180-82b6-aaae68d7c8c2"; :>> outcome = VerdictKind::pass; :>> judgedAgainst = "5fcd953"; :>> judgedAt = "2026-09-11"; :>> judgedBy = "claudeOpus5"; }
    verification renderFamilyFoldReviewGate : Test { :>> id = "7d988c07-072d-4c44-8ba4-0ae4cf227a4f"; :>> title = "Sprint 678 review gate — three passes per D0172"; :>> createdAt = "2026-09-11"; :>> createdBy = "claudeOpus5"; :>> method = VerificationMethod::inspect; :>> procedureText = "Delivered and measured 2026-09-11: compare678.txt - 17 of 18 cases EQUAL between keel-prefold.exe (build 10b6912) and keel-serve.exe on the same tree back to back; the one DIFF is report assurance, where the OLD binary counts 9 invariant blockers to the new binary's 2 and the seven extra are the old binary's own cli-surface-declared guard failing against the post-fold commands.sysml (read from `assured .` blockers on both binaries) - a self-consistency check of the retired surface, not a change in the moved arm; every other field byte-equal. Graph: 277780 sorted lines both sides, +5 bytes from the generator string. hardening dispatched 69 of 69. Residual: the graph's order wanders (issue495); the fixture keel-cli/tests/fixtures/stpa/control-structure.json still names the old verbs as a frozen input, by design."; }
    // RAN: compare678.txt: 17 of 18 cases EQUAL between keel-prefold.exe and keel-serve.exe on one tree back to back; DIFF only in report assurance (old binary cli-surface-declared self-check, 9 vs 2 blockers); keel show hardening .: dispatched 69 of 69
    part renderFamilyFoldReviewGateR1 : TestResult { :>> id = "3c3ac0fc-dd7f-4a87-a974-6996a4afd4b6"; :>> outcome = VerdictKind::proposed; :>> judgedAgainst = "5fcd953"; :>> judgedAt = "2026-09-11"; :>> judgedBy = "claudeOpus5"; }
    verification renderFamilyFoldCloseOutGate : Test { :>> id = "22d0ca9c-1c36-4e87-ac1b-bb29915653f0"; :>> title = "Sprint 678 closeOut gate (autonomous, D0049)"; :>> createdAt = "2026-09-11"; :>> createdBy = "claudeOpus5"; :>> method = VerificationMethod::inspect; :>> procedureText = "Sprint 678 closes on the byte comparison, the hardening read-back, validate, check-engine, guard, sync-claude --check, the touched suite and the D0449 tests. D0449 is staged with this sprint (keystone lock, D0209 cl.2). dcRemainingCliFamilies stays open: four folds remain, D0450 and D0451 next, D0452 and D0453 on the human's word."; }
    // RAN: keel validate .: 776 tracking file(s) validated clean; keel check-engine .: clean; keel guard --no-receipt .: ALL PASS; keel sync-claude --check .: keel-owned subset matches (46 registry skills); keel show open-issues .: issue495 and issue496 present with resolvers
    part renderFamilyFoldCloseOutGateR1 : TestResult { :>> id = "63cce2ee-2731-4837-8a34-f80a2d492802"; :>> outcome = VerdictKind::proposed; :>> judgedAgainst = "5fcd953"; :>> judgedAt = "2026-09-11"; :>> judgedBy = "claudeOpus5"; }
    verification renderFamilyFoldRetroGate : Test { :>> id = "f933ac7f-f191-40eb-86b4-c2805ba5ef69"; :>> title = "Sprint 678 retro gate (autonomous, D0049)"; :>> createdAt = "2026-09-11"; :>> createdBy = "claudeOpus5"; :>> method = VerificationMethod::analyze; :>> procedureText = "AVOIDABLE-ISSUE SCAN: issue495 recorded - the whole-model graph is not deterministic, found because the fold's criterion is byte equality and the graph could not meet it raw. FINDING: the first comparison baseline was taken from an older tree and produced false diffs; the fix was to keep the pre-fold BINARY and run both on one tree back to back, which is what the next four folds should do from the start. FINDING: the compare harness's normaliser first rewrote the new spelling everywhere in the output, corrupting D0449's own text inside the decision-card JSON; narrowed to the two generator strings. Why no control (D0131): both findings are properties of a scratch harness that exists for five folds and ends with them; a committed comparison tool would be a control over nothing once d0399 is delivered. The one durable defect the harness exposed is issue495, which is tracked."; }
    // RAN: keel show open-issues .: issue495 (render model nondeterministic, resolver dcRenderModelIsDeterministic) and issue496 (verifier subagent committed 5fcd953, resolver dcSubagentCannotCommit) both listed; guard --no-receipt: issues guard green
    part renderFamilyFoldRetroGateR1 : TestResult { :>> id = "bc236048-5799-42e1-ba66-6f84ccdc35cd"; :>> outcome = VerdictKind::proposed; :>> judgedAgainst = "5fcd953"; :>> judgedAt = "2026-09-11"; :>> judgedBy = "claudeOpus5"; }
}
