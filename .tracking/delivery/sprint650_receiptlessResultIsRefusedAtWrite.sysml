// ProjectDeliveryS650 — Sprint 650: Deliver dcReceiptlessResultIsRefusedAtWrite (issue448, obligationf76e7aba): a receiptless AI-judged method=test result is refused at the WRITE, not caught at the turn boundary. append-result and append-gate-result refuse when the target verification declares method=test, the judge is an AI-kind or unregistered actor, and --evidence is absent or blank; the file is untouched and the refusal is a `refused` ledger line naming `append-result:ran-receipt` / `append-gate-result:ran-receipt` and the actor kind (D0424). Chartered by D0232 (a pass is a receipt, not a testimony): the receipt the guard reads at the turn boundary is owed where the line is written.. EXECUTE. 2 pts.
package ProjectDeliveryS650 {
    private import EngineElement::*;
    private import EngineWork::*;
    private import EngineVerification::*;
    private import EngineRelationships::*;

    #CharteredBy dependency from receiptlessResultIsRefusedAtWriteStory to d0232;

    part receiptlessResultIsRefusedAtWriteStory : Story {
        :>> id = "065e5661-d070-4d2d-81e3-247782edf90a";
        :>> title = "Sprint 650: Deliver dcReceiptlessResultIsRefusedAtWrite (issue448, obligationf76e7aba): a receiptless AI-judged method=test result is refused at the WRITE, not caught at the turn boundary. append-result and append-gate-result refuse when the target verification declares method=test, the judge is an AI-kind or unregistered actor, and --evidence is absent or blank; the file is untouched and the refusal is a `refused` ledger line naming `append-result:ran-receipt` / `append-gate-result:ran-receipt` and the actor kind (D0424). Chartered by D0232 (a pass is a receipt, not a testimony): the receipt the guard reads at the turn boundary is owed where the line is written. (2 pts)";
        :>> createdAt = "2026-09-10"; :>> createdBy = "claudeOpus5"; :>> kind = WorkKind::code; :>> priority = WorkPriority::p0; :>> owner = "claudeOpus5"; :>> estimatedPoints = 2;
    }

    action def DeliveryRunS650 {
        action storyReceiptlessResultIsRefusedAtWrite;
        verification storyReceiptlessResultIsRefusedAtWriteDoD : Test { :>> id = "641caaae-a93c-47c2-9614-66bde44bfa4d"; :>> method = VerificationMethod::test; :>> procedureText = "The dcReceiptlessResultIsRefusedAtWriteDoD text at HEAD. VERIFY (probe pair): the unit test receiptless_ai_test_results_are_refused_at_the_write in keel-cli/src/write.rs runs the four cases for each write path (AI + method=test + no evidence refused with the file byte-for-byte; the same call with evidence lands with its RAN line; a human with no evidence lands; a method=inspect verification with an AI judge and no evidence lands; blank evidence is no evidence); the live CLI probe against sprint649's Implement gate is refused with exit 1, the file unchanged, and one `refused` ledger line with control append-gate-result:ran-receipt and actorKind ai; CLAUDE.md sec 4 names the refusal at the write; clippy clean."; }
        // RAN: cd keel-cli && cargo test --release --lib write:: - test result: ok. 26 passed; cd keel-cli && cargo test --release --lib census - test result: ok. 9 passed; cd keel-cli && cargo test --release --lib view:: - test result: ok. 108 passed; cd keel-cli && cargo test --release --test write_bdd - 10 scenarios (10 passed), 35 steps (35 passed); cargo clippy --release --all-targets - 0 warnings/errors; ./target/release/keel.exe guard --no-receipt . - ALL PASS; ./target/release/keel.exe validate . - 739 tracking file(s) validated clean; ./target/release/keel.exe check-engine . - .engine instance files validated clean; live probe (append-gate-result on sprint649 gate without --evidence) - exit 1, UNCHANGED, ledger +1, control append-gate-result:ran-receipt, actorKind ai
        part storyReceiptlessResultIsRefusedAtWriteDoDR1 : TestResult { :>> id = "dba501c6-3b54-4928-b55c-d79c09b0bbb7"; :>> outcome = VerdictKind::pass; :>> judgedAgainst = "989c277"; :>> judgedAt = "2026-09-10"; :>> judgedBy = "claudeOpus5"; }
    }

    verification receiptlessResultIsRefusedAtWriteRefineGate : Test { :>> id = "8a67fa79-1639-4a25-b168-30d3282d4e61"; :>> title = "Sprint 650 refine gate (DoR)"; :>> createdAt = "2026-09-10"; :>> createdBy = "claudeOpus5"; :>> method = VerificationMethod::inspect; :>> procedureText = "Scope: write.rs (verification_declares_method generalising the confirmation lookup to any verification and any method member; refuse_receiptless_ai_test mirroring refuse_ai_judgment's registry rule - a registered human owes no receipt, outside a model tree or without actors.sysml the guard owns it; WriteError::ReceiptOwed with a Display that names the flag to pass; the check in both append_result_locked and append_gate_result_locked before any line is built), main.rs (the two dispatch sites ledger the refusal through ledger_refused so the census reads it as a fact), census.rs (append-gate-result:ran-receipt is its own write-path row - the ledger control name differs from append-result's), the existing K6 test updated to carry a receipt on its AI method=test case, the new probe-pair test, CLAUDE.md sec 4 doc-sync. 2 points (a write-path check with tests and a ledger line)."; }
    part receiptlessResultIsRefusedAtWriteRefineGateR1 : TestResult { :>> id = "36cd4670-629c-4412-b3d6-52b3961da336"; :>> outcome = VerdictKind::pass; :>> judgedAgainst = "989c277"; :>> judgedAt = "2026-09-10"; :>> judgedBy = "claudeOpus5"; }
    verification receiptlessResultIsRefusedAtWriteStandupGate : Test { :>> id = "150176ea-d235-44c4-9637-79761d70304d"; :>> title = "Sprint 650 standup gate"; :>> createdAt = "2026-09-10"; :>> createdBy = "claudeOpus5"; :>> method = VerificationMethod::inspect; :>> procedureText = "Blockers: none. The first live probe passed `--sha` where the gate name goes (gate not found: --sha) - a CLI-argument order slip, caught by the refusal itself, no code change. The census row count test in view/census.rs was checked for a hard-coded count before adding the row: none."; }
    part receiptlessResultIsRefusedAtWriteStandupGateR1 : TestResult { :>> id = "f8bf1514-d542-4af7-8585-c0d7cc62f0cf"; :>> outcome = VerdictKind::pass; :>> judgedAgainst = "989c277"; :>> judgedAt = "2026-09-10"; :>> judgedBy = "claudeOpus5"; }
    verification receiptlessResultIsRefusedAtWriteImplementGate : Test { :>> id = "8eea86a9-1984-4f50-bf42-c44fc422219c"; :>> title = "Sprint 650 implement gate"; :>> createdAt = "2026-09-10"; :>> createdBy = "claudeOpus5"; :>> method = VerificationMethod::test; :>> procedureText = "keel-cli/src/write.rs (verification_declares_method, dod_method_is_confirmation as its wrapper, refuse_receiptless_ai_test, WriteError::ReceiptOwed + Display, the two call sites, the updated K6 test, receiptless_ai_test_results_are_refused_at_the_write), keel-cli/src/main.rs (ReceiptOwed arms at the append-result and append-gate-result dispatches calling ledger_refused), keel-cli/src/view/census.rs (append-gate-result:ran-receipt row; the append-result row's rule names the write-time refusal), CLAUDE.md sec 4."; }
    // RAN: cd keel-cli && cargo test --release --lib write:: - test result: ok. 26 passed; cd keel-cli && cargo test --release --lib census - test result: ok. 9 passed; cd keel-cli && cargo test --release --lib view:: - test result: ok. 108 passed; cd keel-cli && cargo test --release --test write_bdd - 10 scenarios (10 passed), 35 steps (35 passed); cargo clippy --release --all-targets - 0 warnings/errors; ./target/release/keel.exe guard --no-receipt . - ALL PASS; ./target/release/keel.exe validate . - 739 tracking file(s) validated clean; ./target/release/keel.exe check-engine . - .engine instance files validated clean; live probe (append-gate-result on sprint649 gate without --evidence) - exit 1, UNCHANGED, ledger +1, control append-gate-result:ran-receipt, actorKind ai
    part receiptlessResultIsRefusedAtWriteImplementGateR1 : TestResult { :>> id = "82a66d9d-fea3-4cec-917a-65614af789cd"; :>> outcome = VerdictKind::pass; :>> judgedAgainst = "989c277"; :>> judgedAt = "2026-09-10"; :>> judgedBy = "claudeOpus5"; }
    verification receiptlessResultIsRefusedAtWriteReviewGate : Test { :>> id = "e568c966-fed0-4878-a87c-4d8a563cedc6"; :>> title = "Sprint 650 review gate — three passes per D0172"; :>> createdAt = "2026-09-10"; :>> createdBy = "claudeOpus5"; :>> method = VerificationMethod::inspect; :>> procedureText = "Three passes (D0172). Correctness: the check sits under the file lock before the line is built, so a refused write cannot leave a partial record; the unit probe asserts byte-for-byte equality after refusal for both paths. Scope: a human judge owes no receipt (their word is the evidence, D0232) - serve.rs's console gate write with no evidence is a human judge and is untouched; write_bdd's fixtures have no actors.sysml and fall to the guard as before. Evidence: the live probe wrote the ledger line the census reads (`append-gate-result:ran-receipt`, actorKind ai) - the census row went from a label to a fact in the same change."; }
    part receiptlessResultIsRefusedAtWriteReviewGateR1 : TestResult { :>> id = "eb37070d-5027-4822-bb84-4750219709b3"; :>> outcome = VerdictKind::pass; :>> judgedAgainst = "989c277"; :>> judgedAt = "2026-09-10"; :>> judgedBy = "claudeOpus5"; }
    verification receiptlessResultIsRefusedAtWriteCloseOutGate : Test { :>> id = "f4dd69b8-66ec-40d1-8c23-a96ed84c07d1"; :>> title = "Sprint 650 closeOut gate (autonomous, D0049)"; :>> createdAt = "2026-09-10"; :>> createdBy = "claudeOpus5"; :>> method = VerificationMethod::inspect; :>> procedureText = "Recorded by the RECORDER subagent from the verifier's receipt (D0425); the primary wrote no ceremony result."; }
    part receiptlessResultIsRefusedAtWriteCloseOutGateR1 : TestResult { :>> id = "9b1acd2f-12ca-4ace-a7a0-2a45d5416038"; :>> outcome = VerdictKind::pass; :>> judgedAgainst = "989c277"; :>> judgedAt = "2026-09-10"; :>> judgedBy = "claudeOpus5"; }
    verification receiptlessResultIsRefusedAtWriteRetroGate : Test { :>> id = "02953ec8-4e47-42bf-b06f-225af8f9a94b"; :>> title = "Sprint 650 retro gate (autonomous, D0049)"; :>> createdAt = "2026-09-10"; :>> createdBy = "claudeOpus5"; :>> method = VerificationMethod::analyze; :>> procedureText = "Avoidable-issue scan: issue448 was found by the D0425 split itself - a recorder following the API with no memory of the RAN convention did what CLAUDE.md said was impossible, which is the evidence class the census exists to collect (an ai-kind refusal, now recorded as such). The census row `append-result:ran-receipt` had been declared active since D0426 while the write path did not refuse - a control declared in a table before it bound in code; the row was true for the guard and false for the verb, and nothing checked that a write-path row has a refusal behind it. That is the same gap control_structure's test closes for HUMAN_ONLY_WRITE_COMMANDS; a census test holding every `active` write-path row to a WriteError variant or a refusal site is the control this retro asks for - recorded as issue449 (in-field) with resolver dcWritePathCensusRowsHaveARefusalBehindThem. Second finding, met at the commit: the verifier's receipt and the primary's own guard run both read ALL PASS while the pre-commit gate refused on retro-backlog, because that guard scans only `git diff --cached` and an unstaged run scans nothing (probed: unstaged 0 scanned PASS, staged 1 scanned FAIL) - the in-loop tiers were blind to the D0131 finding class; recorded as issue450 (in-field) with resolver dcRetroBacklogReadsTheWorkingTree."; }
    part receiptlessResultIsRefusedAtWriteRetroGateR1 : TestResult { :>> id = "0e3e58bc-9198-4e66-b750-e57d7ffd2773"; :>> outcome = VerdictKind::pass; :>> judgedAgainst = "989c277"; :>> judgedAt = "2026-09-10"; :>> judgedBy = "claudeOpus5"; }
}
