// ProjectDeliveryS674 — Sprint 674: A control's PROOF state is computed by the binary beside DECLARED and ARMED (D0360): PROVEN when a test body names the guard and asserts a failure, UNPROVEN when it is named only around passing assertions, UNDETERMINED when no test body names it. Until this sprint the number lived in a Python census someone had to remember to run; now `keel show controls` carries it on every run, with the unproven and undetermined LISTS as the actionable output and the share as context, never a bare percentage. An indicator, not a gate (D0088).. EXECUTE. 3 pts.
package ProjectDeliveryS674 {
    private import EngineElement::*;
    private import EngineWork::*;
    private import EngineVerification::*;
    private import EngineRelationships::*;

    #CharteredBy dependency from controlProofStateIsComputedStory to d0360;

    part controlProofStateIsComputedStory : Story {
        :>> id = "8936f24b-e85e-43ca-8c96-4e10c1137554";
        :>> title = "Sprint 674: A control's PROOF state is computed by the binary beside DECLARED and ARMED (D0360): PROVEN when a test body names the guard and asserts a failure, UNPROVEN when it is named only around passing assertions, UNDETERMINED when no test body names it. Until this sprint the number lived in a Python census someone had to remember to run; now `keel show controls` carries it on every run, with the unproven and undetermined LISTS as the actionable output and the share as context, never a bare percentage. An indicator, not a gate (D0088). (3 pts)";
        :>> createdAt = "2026-09-11"; :>> createdBy = "claudeOpus5"; :>> kind = WorkKind::code; :>> priority = WorkPriority::p0; :>> owner = "claudeOpus5"; :>> estimatedPoints = 3;
    }

    action def DeliveryRunS674 {
        action storyControlProofStateIsComputed;
        verification storyControlProofStateIsComputedDoD : Test { :>> id = "a5532865-8338-402f-bfcd-f4ec2e44c7b3"; :>> method = VerificationMethod::test; :>> procedureText = "keel-cli/src/control_proof.rs computes ProofState per guard from the test corpus under the root (the D0360 heuristic: a `#[test]` body naming the guard with a failure-asserting form is PROVEN; naming it only around passing assertions is UNPROVEN; named in no test body is UNDETERMINED); `keel show controls` (view/reports.rs, view/mod.rs) reports `controlProof` with the three counts and the two lists; the cliShowControls synopsis in cli_facts.rs and commands.sysml names the three states; usage.md's controls row explains them. Integration test control_proof_state_is_computed: the D0388 pair (a fixture guard named in a failure-asserting test is PROVEN and one named only in passing tests is UNPROVEN, before any real tree is read); the binary agrees with the census script on this tree and shows all three states; a malformed id is a violation the guard names. The census script stays as the independent cross-check the test compares against."; }
        // RAN: verifier receipt batch3 head=40190c5: keel suite --touched -> 710 passed 0 failed 700 s (touched-1789134894.log); keel show controls . -> controlProof 72 guards 30 proven 22 unproven 20 undetermined; control_proof_state_is_computed in the touched set
        part storyControlProofStateIsComputedDoDR1 : TestResult { :>> id = "43b3b42d-5f76-4272-8378-7674c0992fb7"; :>> outcome = VerdictKind::pass; :>> judgedAgainst = "40190c5"; :>> judgedAt = "2026-09-11"; :>> judgedBy = "claudeOpus5"; }
    }

    verification controlProofStateIsComputedRefineGate : Test { :>> id = "db29c766-790a-47a5-bf05-1502eac2e997"; :>> title = "Sprint 674 refine gate (DoR)"; :>> createdAt = "2026-09-11"; :>> createdBy = "claudeOpus5"; :>> method = VerificationMethod::inspect; :>> procedureText = "Chartered by D0360 (accepted). Built by a parallel implementer in a worktree (2026-09-11, the agentic-flow experiment) and integrated by the manager. 3 points: one new module of 472 lines, two view files, the CLI fact pair, four integration tests. NOT A FORK."; }
    // RAN: verifier receipt batch3 head=40190c5: keel suite --touched -> 710 passed 0 failed 700 s (touched-1789134894.log); validate exit 0; check-engine exit 0; guard ALL PASS exit 0; chartered by d0360; 3 points; task dcControlProofStateIsComputed
    part controlProofStateIsComputedRefineGateR1 : TestResult { :>> id = "0c6af4e6-4ad8-4663-a5ec-bd0d71a0b78f"; :>> outcome = VerdictKind::proposed; :>> judgedAgainst = "40190c5"; :>> judgedAt = "2026-09-11"; :>> judgedBy = "claudeOpus5"; }
    verification controlProofStateIsComputedStandupGate : Test { :>> id = "2f296f42-4432-4a2e-9d5b-5d870f1d3121"; :>> title = "Sprint 674 standup gate"; :>> createdAt = "2026-09-11"; :>> createdBy = "claudeOpus5"; :>> method = VerificationMethod::inspect; :>> procedureText = "Order: control_proof.rs (states, heuristic, corpus walk) then reports.rs/mod.rs (controlProof in the JSON and text) then the cli_facts/commands.sysml synopsis then usage.md then the test. Blockers met in integration, not in the build: (1) the SubagentStop hook ran the main tree's stale binary against the patched facts and reported cli-surface-declared red - a false red cleared by rebuilding (issue487); (2) the usage.md row named the census script by path, which exists on this tree but is dev-only and never scaffolded (migrate.rs:289), so tool-reference went red inside every scaffolded project and four integration tests failed fifteen minutes into the touched run (issue489); the row was reworded to name no dev-only path."; }
    // RAN: verifier receipt batch3 head=40190c5: keel suite --touched -> 710 passed 0 failed 700 s (touched-1789134894.log); validate exit 0; check-engine exit 0; guard ALL PASS exit 0; blockers issue487 (stale binary) and issue489 (dev-only path on shipped doc) recorded with resolvers
    part controlProofStateIsComputedStandupGateR1 : TestResult { :>> id = "2dce3cbd-c3d6-40ca-8af3-2aedb2df99d2"; :>> outcome = VerdictKind::proposed; :>> judgedAgainst = "40190c5"; :>> judgedAt = "2026-09-11"; :>> judgedBy = "claudeOpus5"; }
    verification controlProofStateIsComputedImplementGate : Test { :>> id = "7a4f2f30-100f-48c3-a08a-7ca24027d00d"; :>> title = "Sprint 674 implement gate"; :>> createdAt = "2026-09-11"; :>> createdBy = "claudeOpus5"; :>> method = VerificationMethod::test; :>> procedureText = "keel-cli/src/control_proof.rs (new): ProofState, the corpus walk over keel-cli/tests and src, the failure-asserting heuristic, the per-guard result and the census. keel-cli/src/view/reports.rs and view/mod.rs: controlProof block (proven/unproven/undetermined counts, unprovenList, undeterminedList) beside controlArming. keel-cli/src/lib.rs: the module. keel-cli/src/cli_facts.rs:102 and .engine/cli/commands.sysml:103: the synopsis names DECLARED, ARMED and PROOF. .engine/docs/usage.md:108: the controls row. .engine/tools/guard_proof_census.py: the independent reference, unchanged in method. .tracking/architecture/engine-instruments.sysml: the census Sensor's comment says where it is published. keel-cli/tests/control_proof_state_is_computed.rs: four tests."; }
    // RAN: verifier receipt batch3 head=40190c5: keel suite --touched -> 710 passed 0 failed 700 s (touched-1789134894.log); validate exit 0; check-engine exit 0; guard ALL PASS exit 0; control_proof_state_is_computed 4 tests in the touched set; keel show controls . controlProof present
    part controlProofStateIsComputedImplementGateR1 : TestResult { :>> id = "7fb9a75f-08d6-4a54-b427-a17b0a249c26"; :>> outcome = VerdictKind::pass; :>> judgedAgainst = "40190c5"; :>> judgedAt = "2026-09-11"; :>> judgedBy = "claudeOpus5"; }
    verification controlProofStateIsComputedReviewGate : Test { :>> id = "d2227d03-9019-4297-ae88-f7307f58fab2"; :>> title = "Sprint 674 review gate — three passes per D0172"; :>> createdAt = "2026-09-11"; :>> createdBy = "claudeOpus5"; :>> method = VerificationMethod::inspect; :>> procedureText = "Delivered: on this tree at the receipt the binary reads 72 enforced guards over 808 test functions: 30 PROVEN, 22 UNPROVEN, 20 UNDETERMINED (the eol guard of sprint 675 is the 72nd, proven by its own pair), and the integration test holds the binary and the census to agreement, and the lists name which guards have never been shown catching anything - the census's first finding (2026-09-06: 16 proven of 64) is now a number the binary keeps honest on every run. Residual: the heuristic is textual (a fixture that exercises a guard without naming it lands UNDETERMINED, by design), and nothing binds an Indicator to the three counts yet; that is one declaration in indicators.sysml when someone wants the direction watched."; }
    // RAN: verifier receipt batch3 head=40190c5: keel suite --touched -> 710 passed 0 failed 700 s (touched-1789134894.log); validate exit 0; check-engine exit 0; guard ALL PASS exit 0; keel show controls . -> 72 guards 808 test functions 30/22/20; census script agrees per the integration test
    part controlProofStateIsComputedReviewGateR1 : TestResult { :>> id = "c495b805-471c-4262-9931-997ad92721ff"; :>> outcome = VerdictKind::proposed; :>> judgedAgainst = "40190c5"; :>> judgedAt = "2026-09-11"; :>> judgedBy = "claudeOpus5"; }
    verification controlProofStateIsComputedCloseOutGate : Test { :>> id = "655317b5-4093-41a2-aa7e-4511530db090"; :>> title = "Sprint 674 closeOut gate (autonomous, D0049)"; :>> createdAt = "2026-09-11"; :>> createdBy = "claudeOpus5"; :>> method = VerificationMethod::inspect; :>> procedureText = "Sprint 674 closes on the verifier's receipt only (D0425). dcControlProofStateIsComputed gets its DoD result. The census script remains a Sensor on the engine tree."; }
    // RAN: verifier receipt batch3 head=40190c5: keel suite --touched -> 710 passed 0 failed 700 s (touched-1789134894.log); validate exit 0; check-engine exit 0; guard ALL PASS exit 0; dcControlProofStateIsComputedDoDR1 recorded at 40190c5; DISCREPANCIES none in receipt
    part controlProofStateIsComputedCloseOutGateR1 : TestResult { :>> id = "5e490a7f-59eb-43b8-ace5-6d0e717e917e"; :>> outcome = VerdictKind::proposed; :>> judgedAgainst = "40190c5"; :>> judgedAt = "2026-09-11"; :>> judgedBy = "claudeOpus5"; }
    verification controlProofStateIsComputedRetroGate : Test { :>> id = "14c1cbb2-a1f3-4199-a003-927878f31664"; :>> title = "Sprint 674 retro gate (autonomous, D0049)"; :>> createdAt = "2026-09-11"; :>> createdBy = "claudeOpus5"; :>> method = VerificationMethod::analyze; :>> procedureText = "AVOIDABLE-ISSUE SCAN: two items, both recorded this commit with resolvers - issue487 (dcCliSurfaceGuardNamesAStaleBinary: the guard must say STALE BINARY, not drift) and issue489 (dcToolReferenceKnowsWhatShips: the guard must give on the engine tree the verdict the scaffold gives). Already tracked, not new: issue488 (a verifier obeyed its stop hook and recorded a Decision in the human's name; this sprint's batch-1 verifier also made two commits on main, 7fdf11a and 40190c5, which stay as history under D0129). FINDING: the implementer's own worktree run was green and the defects were all at the seam - a stale binary, a dev-only path, a hook picking the wrong tree; the parallel flow finds integration defects the serial flow never had, and each one is now a control."; }
    // RAN: verifier receipt batch3 head=40190c5: keel suite --touched -> 710 passed 0 failed 700 s (touched-1789134894.log); validate exit 0; check-engine exit 0; guard ALL PASS exit 0; retro names issue487 and issue489 (new, resolvers recorded) and issue488 (already tracked)
    part controlProofStateIsComputedRetroGateR1 : TestResult { :>> id = "2624c885-0042-44c1-9c2b-fc558e1de3af"; :>> outcome = VerdictKind::proposed; :>> judgedAgainst = "40190c5"; :>> judgedAt = "2026-09-11"; :>> judgedBy = "claudeOpus5"; }
}
