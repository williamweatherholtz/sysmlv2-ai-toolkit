// ProjectDeliveryS656 — Sprint 656: Close dcSkillsRouteBehaviourally on exercised evidence: the routing rig (sprint 609, D0382) run against a named case under the whole-turn scorer (dcRoutingVerdictReadsTheWholeTurn), its per-sample verdicts, agree/disagree finding and measured spend read from its own output, and the case that disagreed with itself recorded as issue456 with the prompt that missed it and a resolver in the backlog - the DoD's VERIFY clause, word for word.. EXECUTE. 1 pts.
package ProjectDeliveryS656 {
    private import EngineElement::*;
    private import EngineWork::*;
    private import EngineVerification::*;
    private import EngineRelationships::*;

    #CharteredBy dependency from skillsRouteBehaviourallyStory to d0382;

    part skillsRouteBehaviourallyStory : Story {
        :>> id = "b81b0fdb-81ce-4362-83ca-fcd562ea3968";
        :>> title = "Sprint 656: Close dcSkillsRouteBehaviourally on exercised evidence: the routing rig (sprint 609, D0382) run against a named case under the whole-turn scorer (dcRoutingVerdictReadsTheWholeTurn), its per-sample verdicts, agree/disagree finding and measured spend read from its own output, and the case that disagreed with itself recorded as issue456 with the prompt that missed it and a resolver in the backlog - the DoD's VERIFY clause, word for word. (1 pts)";
        :>> createdAt = "2026-09-10"; :>> createdBy = "claudeOpus5"; :>> kind = WorkKind::code; :>> priority = WorkPriority::p0; :>> owner = "claudeOpus5"; :>> estimatedPoints = 1;
    }

    action def DeliveryRunS656 {
        action storySkillsRouteBehaviourally;
        verification storySkillsRouteBehaviourallyDoD : Test { :>> id = "8ce55968-3fab-41bf-98d0-6f8032715352"; :>> method = VerificationMethod::test; :>> procedureText = "The DoD of dcSkillsRouteBehaviourally is satisfied by a run whose receipt this sprint carries: --probe holds on the scorer's seven known cases before any model is paid for (D0388); --investigate release --samples 3 reports three per-sample verdicts, a DISAGREES finding and the spend; the disagreement is recorded as an Issue naming the prompt and the check's own cause, triaged to the EXISTING resolver dcPrefixLeavesRoomForTheRoute (issue432 is the same class, one day earlier); no rate and no coverage number is published anywhere (D0378 C). VERIFY: the rig's log names 1 routed / 2 none with $3.78 over 3 runs; issue456 exists with a #Resolves edge from dcPrefixLeavesRoomForTheRoute; keel validate and keel guard green; dcSkillsRouteBehaviourally leaves whats-next."; }
        // RAN: python .engine/tools/routing_probe.py --investigate release --samples 3: 1 ROUTED / 2 none, $3.78, 39s; --probe 7/7 hold; issue456 -> dcPrefixLeavesRoomForTheRoute; keel validate . clean; keel guard --no-receipt . ALL PASS
        part storySkillsRouteBehaviourallyDoDR1 : TestResult { :>> id = "2c9f9f77-1bdf-4728-ad11-421c90609c59"; :>> outcome = VerdictKind::pass; :>> judgedAgainst = "d316dd8766acf72faaa689e39f4e5bc516f03e11"; :>> judgedAt = "2026-09-10T15:47:45Z"; :>> judgedBy = "claudeOpus5"; }
    }

    verification skillsRouteBehaviourallyRefineGate : Test { :>> id = "7e95613b-9f95-428c-ab1e-d399ed6ccfa6"; :>> title = "Sprint 656 refine gate (DoR)"; :>> createdAt = "2026-09-10"; :>> createdBy = "claudeOpus5"; :>> method = VerificationMethod::inspect; :>> procedureText = "One point: a rig run, an Issue, a result. Ready: the resolver of issue415 is done, so the check's first defect is out of the way and the second run is the natural before/after. PROBED FIRST: python .engine/tools/routing_probe.py --probe - all 7 cases hold; --dry-run estimated ~$3.71 from the 2026-09-09 measurement."; }
    // RAN: python .engine/tools/routing_probe.py --probe: all 7 cases hold; keel validate .: 747 files clean; DoR read from the record
    part skillsRouteBehaviourallyRefineGateR1 : TestResult { :>> id = "d45ca796-1633-4d56-9f14-9ac42df3acb4"; :>> outcome = VerdictKind::pass; :>> judgedAgainst = "d316dd8766acf72faaa689e39f4e5bc516f03e11"; :>> judgedAt = "2026-09-10T15:47:45Z"; :>> judgedBy = "claudeOpus5"; }
    verification skillsRouteBehaviourallyStandupGate : Test { :>> id = "814f027e-1da7-4912-b85c-839ae21a498e"; :>> title = "Sprint 656 standup gate"; :>> createdAt = "2026-09-10"; :>> createdBy = "claudeOpus5"; :>> method = VerificationMethod::inspect; :>> procedureText = "No blocker. The run was made while sprint 655's land was pushing: the probe session disallows Write, Edit, NotebookEdit and Bash and runs headless, so it cannot touch the tree, and the rig writes only .keel/metrics/routing-investigation.json."; }
    // RAN: keel advance 656 .: cursor at Refine after refine pass; no blocker; probe session disallows Write/Edit/NotebookEdit/Bash
    part skillsRouteBehaviourallyStandupGateR1 : TestResult { :>> id = "96385281-9197-463f-aa95-6fad1c87345b"; :>> outcome = VerdictKind::pass; :>> judgedAgainst = "d316dd8766acf72faaa689e39f4e5bc516f03e11"; :>> judgedAt = "2026-09-10T15:47:45Z"; :>> judgedBy = "claudeOpus5"; }
    verification skillsRouteBehaviourallyImplementGate : Test { :>> id = "d1551266-a50e-4eb3-b901-1fef13674a41"; :>> title = "Sprint 656 implement gate"; :>> createdAt = "2026-09-10"; :>> createdBy = "claudeOpus5"; :>> method = VerificationMethod::test; :>> procedureText = "python .engine/tools/routing_probe.py --investigate release --samples 3: #1 ROUTED (Skill intake, Skill release, ToolSearch) 36.9s $1.273; #2 none (Skill intake, ToolSearch, ToolSearch) 37.0s $1.253; #3 none (Skill intake, ToolSearch, ToolSearch) 38.8s $1.254; DISAGREES release 1 routed 2 none; spend $3.78 over 3 runs, 39s wall. The JSON's tool sequences are the finding: both none samples spent every turn of --max-turns 3 after intake on ToolSearch - the rig disallows Bash, intake's deployed procedure says run keel record statement, so the agent hunted for its instrument and the budget ran out before the intended skill; the scorer returns none for 'never reached' and 'cut off' alike. Recorded as issue456 (Medium, code-read from the rig's own JSON) with the prompt verbatim, resolved by dcPrefixLeavesRoomForTheRoute - the item issue432 already carries for this class - after a duplicate resolver added first in this sprint was removed before commit."; }
    // RAN: python .engine/tools/routing_probe.py --investigate release --samples 3: 1 ROUTED / 2 none, $3.78 over 3 runs, 39s wall (.keel/metrics/routing-investigation.json); issue456 recorded with #Resolves from dcPrefixLeavesRoomForTheRoute; keel validate .: clean
    part skillsRouteBehaviourallyImplementGateR1 : TestResult { :>> id = "d6710fa1-3a2b-4798-8acd-94af310f3262"; :>> outcome = VerdictKind::pass; :>> judgedAgainst = "d316dd8766acf72faaa689e39f4e5bc516f03e11"; :>> judgedAt = "2026-09-10T15:47:45Z"; :>> judgedBy = "claudeOpus5"; }
    verification skillsRouteBehaviourallyReviewGate : Test { :>> id = "9a155488-98da-454e-bf13-ba86edf363c0"; :>> title = "Sprint 656 review gate — three passes per D0172"; :>> createdAt = "2026-09-10"; :>> createdBy = "claudeOpus5"; :>> method = VerificationMethod::inspect; :>> procedureText = "The DoD's VERIFY clause is met on its own terms: a named case investigated, three per-sample verdicts with tool sequences, an agree/disagree finding, the spend measured from the model's own result events, and the disagreeing case recorded as an Issue with the prompt (issue415 was the first; issue456 is the second). Stated plainly: the rig has now disagreed with itself twice for two different causes, both in the check - first the scorer's first-call criterion, now its budget and sandbox - so it is not yet a check whose 'none' can be believed, and issue456's resolver is where that lives. No rate is published; the two runs are not averaged."; }
    // RAN: keel guard --no-receipt .: ALL PASS, 65 warnings not blocking; keel check-engine .: clean; grep issues-claudeOpus5.sysml: issue456 -> dcPrefixLeavesRoomForTheRoute, issue457 -> dcRecordIssueNamesOpenIssuesOnTheSameInstrument
    part skillsRouteBehaviourallyReviewGateR1 : TestResult { :>> id = "e5e31819-ca52-4e06-9799-2435a426c8f6"; :>> outcome = VerdictKind::pass; :>> judgedAgainst = "d316dd8766acf72faaa689e39f4e5bc516f03e11"; :>> judgedAt = "2026-09-10T15:47:45Z"; :>> judgedBy = "claudeOpus5"; }
    verification skillsRouteBehaviourallyCloseOutGate : Test { :>> id = "767721c5-a7c2-47dc-967c-123fce766b5c"; :>> title = "Sprint 656 closeOut gate (autonomous, D0049)"; :>> createdAt = "2026-09-10"; :>> createdBy = "claudeOpus5"; :>> method = VerificationMethod::inspect; :>> procedureText = "Delivered: the run, issue456 triaged to dcPrefixLeavesRoomForTheRoute, and dcSkillsRouteBehaviourally's result on the rig's receipt. Not delivered by design: no standing coverage number, no sweep, no TestResult from the rig itself (D0382) - the result written is the backlog item's DoD verdict, whose evidence is the rig's output."; }
    // RAN: keel validate .: 747 clean; keel guard --no-receipt .: ALL PASS; git status: backlog.sysml, issues-claudeOpus5.sysml, sprint656 file staged
    part skillsRouteBehaviourallyCloseOutGateR1 : TestResult { :>> id = "0ce9ce51-4244-4081-aeed-969cef146df1"; :>> outcome = VerdictKind::pass; :>> judgedAgainst = "d316dd8766acf72faaa689e39f4e5bc516f03e11"; :>> judgedAt = "2026-09-10T15:47:45Z"; :>> judgedBy = "claudeOpus5"; }
    verification skillsRouteBehaviourallyRetroGate : Test { :>> id = "fbf59816-7a69-4a33-b5e5-6e4bb9943583"; :>> title = "Sprint 656 retro gate (autonomous, D0049)"; :>> createdAt = "2026-09-10"; :>> createdBy = "claudeOpus5"; :>> method = VerificationMethod::analyze; :>> procedureText = "Autonomous retro (D0049). AVOIDABLE-ISSUE SCAN: one issue recorded this sprint, issue456, and the finding itself was not avoidable - the sandbox cause shows only in the JSON of a run under the fixed scorer. What WAS avoidable: the primary added a new resolver task for it before reading the check's open Issues, and issue432 (2026-09-09, the same 3/3 none at 3 turns on the same case) already had dcPrefixLeavesRoomForTheRoute as its resolver - the duplicate was found by keel show priority listing an item whose name said the same thing, removed before commit, and is the finding of issue457 with dcRecordIssueNamesOpenIssuesOnTheSameInstrument as its control: record issue prints the open Issues whose description names a path the new description names, so a duplicate is visible in the command's own output. Recurrence for the priority lens (D0311): the routing check is now the subject of three Issues (issue415, issue432, issue456), all against the check and none against a skill - one instrument, three findings, its verdict vocabulary was designed from the transcripts it had seen and not from what a turn can do; dcPrefixLeavesRoomForTheRoute is the tracked home."; }
    // RAN: keel guard --no-receipt .: ALL PASS (retro-backlog guard among them); issue457 exists with resolver dcRecordIssueNamesOpenIssuesOnTheSameInstrument at backlog.sysml line 1061
    part skillsRouteBehaviourallyRetroGateR1 : TestResult { :>> id = "396fa970-69d7-4732-bc6c-aa19022f0df5"; :>> outcome = VerdictKind::pass; :>> judgedAgainst = "d316dd8766acf72faaa689e39f4e5bc516f03e11"; :>> judgedAt = "2026-09-10T15:47:45Z"; :>> judgedBy = "claudeOpus5"; }
}
