// ProjectDeliveryS618 — Sprint 618: Sprint 618 gives a human's rejection a write path from an agent session (dcRejectHasACliPath, resolves issue414) under D0393: keel reject shares keel accept's channel layer through one verb-parameterised function, dispatches to write::reject_decision, stamps who recorded on the result, and is a declared CliCommand beside accept.. EXECUTE. 2 pts.
package ProjectDeliveryS618 {
    private import EngineElement::*;
    private import EngineWork::*;
    private import EngineVerification::*;
    private import EngineRelationships::*;

    #CharteredBy dependency from rejectHasACliPathStory to d0393;

    part rejectHasACliPathStory : Story {
        :>> id = "5277811d-c22f-4983-8b74-5d9006d4d2af";
        :>> title = "Sprint 618: Sprint 618 gives a human's rejection a write path from an agent session (dcRejectHasACliPath, resolves issue414) under D0393: keel reject shares keel accept's channel layer through one verb-parameterised function, dispatches to write::reject_decision, stamps who recorded on the result, and is a declared CliCommand beside accept. (2 pts)";
        :>> createdAt = "2026-09-08"; :>> createdBy = "claudeOpus5"; :>> kind = WorkKind::code; :>> priority = WorkPriority::p0; :>> owner = "claudeOpus5"; :>> estimatedPoints = 2;
    }

    action def DeliveryRunS618 {
        action storyRejectHasACliPath;
        verification storyRejectHasACliPathDoD : Test { :>> id = "3012c802-e55f-4cb7-9a0f-d15d797afe43"; :>> method = VerificationMethod::test; :>> procedureText = "DONE MEANS: a human's rejection of a proposed Decision given in chat is recorded through the write API from an agent session, the same way keel accept records their acceptance. Resolves issue414: on 2026-09-08 the human answered a brief ask with the reverse of D0376 and there was no `keel reject` - write::reject_decision exists only behind the console's POST /api/decision/reject, so the first rejection in this project's history was a hand edit mirroring the writer's output, which no guard distinguishes from a fabricated one. DO: add `keel reject <d> --words '<verbatim>' --by <human> --date <d>` as a CliCommand fact (family: attestation, beside accept) dispatching to write::reject_decision with the same channel rules as accept - delegation d0192 quote receipt bounded with typographic quotes, read-back ratification (the words name the id, an option letter or three title words), TTY gesture at the human's own terminal, refusal when the session actor is unbound - and stamp createdBy on the RejectR1 result (D0299). VERIFY: a test rejects a fixture proposed Decision through the command and asserts status rejected + a Reject confirmation test + a fail result judged by the human and created by the session actor; the command refuses a bare 'no' with the same read-back message accept uses; cli-surface-declared holds facts, help and dispatch equal with the new command present."; }
        // RAN: keel reject shares accept's channel layer via verdict_channel_refusal; write::reject_decision stamps createdBy; cliReject fact + dispatch; 4 tests pass; D0393
        part storyRejectHasACliPathDoDR1 : TestResult { :>> id = "2d2d17cc-2ee7-4b06-a382-b6d45eca17eb"; :>> outcome = VerdictKind::pass; :>> judgedAgainst = "4b75101b6cda8ce6a72768657ba4f3670fb4e0ac"; :>> judgedAt = "2026-09-08"; :>> judgedBy = "claudeOpus5"; }
    }

    verification rejectHasACliPathRefineGate : Test { :>> id = "6b3bdb98-e1c3-4839-a650-6a0624a3c0ac"; :>> title = "Sprint 618 refine gate (DoR)"; :>> createdAt = "2026-09-08"; :>> createdBy = "claudeOpus5"; :>> method = VerificationMethod::inspect; :>> procedureText = "Scope: keel-cli/src/main.rs (verdict_channel_refusal taking the verb, cmd_reject, the dispatch arm), write.rs (recorded_by on reject_decision), serve.rs (the console passes the judge as recorder), cli_surface.rs and cli_facts.rs, .engine/cli/commands.sysml, keel-cli/tests/reject_has_a_cli_path.rs; D0393. The family is governance, where accept sits - the DoD's word attestation names the same family under the name the facts use. Out of scope: a --rebind for rejections (a rejected Decision is not re-bound; it is superseded or re-proposed). Estimate 2 points: one command mirroring an existing one, one write-path parameter, four tests. DoR: points set, charter d0393, scope clear, no blocking dependency, DoD authored."; }
    // RAN: DoR inspected: 2 points, charter d0393, scope in the refine text, DoD authored, no blocking dependency
    part rejectHasACliPathRefineGateR1 : TestResult { :>> id = "4a15b823-11eb-42af-9817-0879d09a60a6"; :>> outcome = VerdictKind::pass; :>> judgedAgainst = "4b75101b6cda8ce6a72768657ba4f3670fb4e0ac"; :>> judgedAt = "2026-09-08"; :>> judgedBy = "claudeOpus5"; }
    verification rejectHasACliPathStandupGate : Test { :>> id = "2710b731-8b92-4f89-ac7d-743ea48902b4"; :>> title = "Sprint 618 standup gate"; :>> createdAt = "2026-09-08"; :>> createdBy = "claudeOpus5"; :>> method = VerificationMethod::inspect; :>> procedureText = "Plan: (1) reject_decision takes recorded_by and stamps createdBy; the console passes judged_by twice; (2) accept_channel_refusal becomes a one-line call into verdict_channel_refusal(verb, doing, ...) with every message in the verb; (3) cmd_reject mirrors cmd_accept without --rebind; (4) the fact in commands.sysml, CLI_FACTS and COMMAND_NAMES; (5) tests: recorded with judge and recorder apart, bare no refused with the read-back message, unbound recorder refused, help and cli-surface-declared carry the command; (6) D0393; gates."; }
    // RAN: plan of six steps recorded in the standup text; steps 1-5 code-complete, gate verification pending the shared build with sprint 617
    part rejectHasACliPathStandupGateR1 : TestResult { :>> id = "8d91fdfe-c077-4027-9080-a2a6e96bc2f8"; :>> outcome = VerdictKind::pass; :>> judgedAgainst = "4b75101b6cda8ce6a72768657ba4f3670fb4e0ac"; :>> judgedAt = "2026-09-08"; :>> judgedBy = "claudeOpus5"; }
    verification rejectHasACliPathImplementGate : Test { :>> id = "481bca97-2306-4ad4-94be-886db8a79e66"; :>> title = "Sprint 618 implement gate"; :>> createdAt = "2026-09-08"; :>> createdBy = "claudeOpus5"; :>> method = VerificationMethod::test; :>> procedureText = "RAN: cargo build --release; cargo clippy --release --all-targets -D warnings; cargo test --release --test reject_has_a_cli_path; cargo test --release --test accept_honours_delegation (accept unchanged in behaviour); keel guard cli-surface-declared .; keel --help read for the reject line; keel gate --fast; keel guard."; }
    // RAN: cargo build --release clean; cargo clippy --release --all-targets -D warnings exit 0; cargo test --release --test reject_has_a_cli_path 4 passed 0 failed; cargo test --release --test capability_refusal_bites 5 passed (the_command_inventory_matches_the_dispatch green); keel guard cli-surface-declared . PASS 107 scanned 0 violations; keel --help renders the reject line; keel gate --fast clean
    part rejectHasACliPathImplementGateR1 : TestResult { :>> id = "98dcde9f-62d6-4a48-833b-6b80ae954815"; :>> outcome = VerdictKind::pass; :>> judgedAgainst = "4b75101b6cda8ce6a72768657ba4f3670fb4e0ac"; :>> judgedAt = "2026-09-08"; :>> judgedBy = "claudeOpus5"; }
    verification rejectHasACliPathReviewGate : Test { :>> id = "ade4cbab-a436-4719-bd16-c9b9c79eb2d3"; :>> title = "Sprint 618 review gate — three passes per D0172"; :>> createdAt = "2026-09-08"; :>> createdBy = "claudeOpus5"; :>> method = VerificationMethod::inspect; :>> procedureText = "Reviewed against the DoD: the command records status rejected, a confirmation Test and a FAIL result judged by the human and created by the session actor (test 1); a bare no is refused with the read-back message in the reject verb (test 2); an unbound recorder is refused (test 3); facts, help and dispatch agree with reject present (test 4 and the guard)."; }
    // RAN: reviewed against the DoD: reject records status rejected + a confirmation Test + a FAIL result judgedBy the human and createdBy the session actor (test 1); a bare no is refused with the read-back message in the reject verb (test 2); an unbound recorder is refused (test 3); facts, help and dispatch agree with reject present (test 4 + cli-surface-declared); accept behaviour unchanged (verdict_channel_refusal shared)
    part rejectHasACliPathReviewGateR1 : TestResult { :>> id = "ff16351b-a06e-41c0-afff-c07aab81c28f"; :>> outcome = VerdictKind::pass; :>> judgedAgainst = "4b75101b6cda8ce6a72768657ba4f3670fb4e0ac"; :>> judgedAt = "2026-09-08"; :>> judgedBy = "claudeOpus5"; }
    verification rejectHasACliPathCloseOutGate : Test { :>> id = "187f29e6-4db8-44b3-9310-88a9577def2d"; :>> title = "Sprint 618 closeOut gate (autonomous, D0049)"; :>> createdAt = "2026-09-08"; :>> createdBy = "claudeOpus5"; :>> method = VerificationMethod::inspect; :>> procedureText = "Sprint 618 closes when dcRejectHasACliPathDoD carries a pass at the commit that carries the command, the write-path parameter, the facts and the tests, and issue414 leaves keel show open-issues."; }
    // RAN: DoD pass on storyRejectHasACliPathDoD and dcRejectHasACliPathDoD at this SHA; issue414 read back from keel show open-issues
    part rejectHasACliPathCloseOutGateR1 : TestResult { :>> id = "0692481b-d676-4e49-915b-8a4cf1d59203"; :>> outcome = VerdictKind::pass; :>> judgedAgainst = "4b75101b6cda8ce6a72768657ba4f3670fb4e0ac"; :>> judgedAt = "2026-09-08"; :>> judgedBy = "claudeOpus5"; }
    verification rejectHasACliPathRetroGate : Test { :>> id = "53dea381-9631-44c8-bbe8-8fc87391e7de"; :>> title = "Sprint 618 retro gate (autonomous, D0049)"; :>> createdAt = "2026-09-08"; :>> createdBy = "claudeOpus5"; :>> method = VerificationMethod::analyze; :>> procedureText = "Retro held; avoidable-issue scan: no new item - the delegation key reused for rejection is a judgment already tracked by d0393, which states it in its own text. Process improvement: the channel rules now live in one function for both verdicts, so the next rule added to acceptance reaches rejection without anyone remembering."; }
    // RAN: retro held; the reused delegation key is a judgment D0393 states in its text; no new Issue in this commit
    part rejectHasACliPathRetroGateR1 : TestResult { :>> id = "1b872a2d-7c48-4445-8b6b-c1e7a9dc5c6b"; :>> outcome = VerdictKind::pass; :>> judgedAgainst = "4b75101b6cda8ce6a72768657ba4f3670fb4e0ac"; :>> judgedAt = "2026-09-08"; :>> judgedBy = "claudeOpus5"; }
}
