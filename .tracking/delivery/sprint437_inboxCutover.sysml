// ProjectDeliveryS437 — Sprint 437: the Smartsheet inbox retires (D0206, auto-accepted from its own issue): contract deleted, deck degraded to a local read view, skills re-pointed at the GitHub board. EXECUTE. 1 pts.
package ProjectDeliveryS437 {
    private import EngineElement::*;
    private import EngineWork::*;
    private import EngineVerification::*;
    private import EngineRelationships::*;

    #CharteredBy dependency from inboxCutoverStory to d0206;

    part inboxCutoverStory : Story {
        :>> id = "4225c71c-53ad-4839-9fad-7287a5255353";
        :>> title = "Sprint 437: the old channel stands down (1 pts)";
        :>> createdAt = "2026-08-24"; :>> createdBy = "claudeFable5"; :>> kind = WorkKind::code; :>> priority = WorkPriority::p0; :>> owner = "claudeFable5"; :>> estimatedPoints = 1;
    }

    action def DeliveryRunS437 {
        action storyInboxCutover;
        verification storyInboxCutoverDoD : Test { :>> id = "b27dad41-3c55-45ed-8210-08c3b5a704af"; :>> method = VerificationMethod::test; :>> procedureText = "DELIVERED: the retireInbox cutover (D0206), whose acceptance was itself the first live auto-acceptance - recorded entirely by GitHub Actions from its own issue #2 while this machine had no part, then pulled down by keel sync. The follow-through: (1) .engine/contracts/deck-inbox.toml DELETED - D0206's designed removal path, and the deck now emits INBOX=null with its transport line honestly reading 'NONE - nothing tapped here reaches keel' outside localhost (read back from the regenerated page); the deck-inbox-toml guard exclusion and the tap-save JS remain harmless with no contract to read. (2) obligation-review SKILL.md rewritten: the board is the GitHub issues list filtered is:open label:blocks-work, the deck is a local read view only, verdicts record via GitHub comments / chat-with-provenance / localhost console - the connector-inbox transport is documented as retired, not merely unused. (3) deck decision cards now link to their GitHub issue (github_slug derived from the origin remote; no link on a non-GitHub remote - no link beats a wrong link), so the local deck points at the recorded channel rather than a dead tap. The Smartsheet sheet stays readable as history; nothing writes to it and no session sweeps it. VERIFIED: deck regenerated with INBOX=null; sync-claude 37/37; validate + check-engine + all 48 guards green; zero open issues."; }
        part storyInboxCutoverDoDR1 : TestResult { :>> id = "27a58cbd-4d93-4dc0-8e25-b5775be070d1"; :>> outcome = VerdictKind::pass; :>> judgedAgainst = "3195ad63b80f40db8070afb7ec22431b823d9555"; :>> judgedAt = "2026-08-23"; :>> judgedBy = "claudeFable5"; }
    }

    verification inboxCutoverRefineGate : Test { :>> id = "339ed276-4559-4342-b755-00177371aad2"; :>> title = "Sprint 437 refine gate (DoR)"; :>> createdAt = "2026-08-24"; :>> createdBy = "claudeFable5"; :>> method = VerificationMethod::inspect; :>> procedureText = "DoR. Chartered by D0206, which auto-accepted from its own GitHub issue - the cutover is gated on the new channel's own successful use, exactly as the decision required. 1 point."; }
    part inboxCutoverRefineGateR1 : TestResult { :>> id = "6acbfe69-395b-41a4-926e-0dbb44fe7159"; :>> outcome = VerdictKind::pass; :>> judgedAgainst = "3195ad63b80f40db8070afb7ec22431b823d9555"; :>> judgedAt = "2026-08-23"; :>> judgedBy = "claudeFable5"; }
    verification inboxCutoverStandupGate : Test { :>> id = "70c15c9b-7c19-4dbb-82b1-c9efe553c3af"; :>> title = "Sprint 437 standup gate"; :>> createdAt = "2026-08-24"; :>> createdBy = "claudeFable5"; :>> method = VerificationMethod::inspect; :>> procedureText = "Approach: use D0206's built-in removal path (delete the contract; the deck already degrades honestly on an absent contract - the pre-designed exit) rather than ripping out the tap JS, so the change is a deletion plus doc-sync, not a rewrite. No blockers."; }
    part inboxCutoverStandupGateR1 : TestResult { :>> id = "aebf1467-1c74-43dc-98fa-e5677658e368"; :>> outcome = VerdictKind::pass; :>> judgedAgainst = "3195ad63b80f40db8070afb7ec22431b823d9555"; :>> judgedAt = "2026-08-23"; :>> judgedBy = "claudeFable5"; }
    verification inboxCutoverImplementGate : Test { :>> id = "16dcdd39-aac5-4ced-8d4e-3b20cafb9983"; :>> title = "Sprint 437 implement gate"; :>> createdAt = "2026-08-24"; :>> createdBy = "claudeFable5"; :>> method = VerificationMethod::test; :>> procedureText = "Verified by running: keel deck regenerated shows INBOX=null and the transport line says NONE outside localhost; the obligation-review skill points at the issues board; the deck card GitHub link renders from the origin slug; sync-claude re-synced 37/37 skills; validate 485 + check-engine + all 48 guards green; open-issues empty."; }
    part inboxCutoverImplementGateR1 : TestResult { :>> id = "9f918b51-6310-4d78-8f21-b46a8a1c5f8e"; :>> outcome = VerdictKind::pass; :>> judgedAgainst = "3195ad63b80f40db8070afb7ec22431b823d9555"; :>> judgedAt = "2026-08-23"; :>> judgedBy = "claudeFable5"; }
    verification inboxCutoverReviewGate : Test { :>> id = "8826401d-d23f-4822-b0b1-214544586029"; :>> title = "Sprint 437 review gate — three passes per D0172"; :>> createdAt = "2026-08-24"; :>> createdBy = "claudeFable5"; :>> method = VerificationMethod::inspect; :>> procedureText = "PASS 1, CLAIMS: INBOX=null and the skill re-point are read-backs from the regenerated artifacts. PASS 2, BOUNDARY: the tap-save JS and the guard's deck-inbox exclusion still exist - dead-but-harmless with no contract, left rather than surgically removed because the honest-degradation path (absent contract = null) was the DESIGNED exit and removing live code adds risk for no behavior change; a reviewer who wants the JS gone can charter it, but it cannot fire. PASS 3, OWN DIFF: none - a deletion plus doc-sync, the cleanest kind of cutover, made possible only because D0206 designed its own off-ramp when it was written. WHAT A REVIEWER SHOULD ATTACK: the Smartsheet sheet is left readable with stale unprocessed-looking rows possible in principle; the skill states no session sweeps it, so a future tap there is inert by design, not lost silently - but a human tapping an old bookmarked deck would get NONE and the instruction to tell Claude."; }
    part inboxCutoverReviewGateR1 : TestResult { :>> id = "aa402489-4a10-47da-86b2-42a8ff316447"; :>> outcome = VerdictKind::pass; :>> judgedAgainst = "3195ad63b80f40db8070afb7ec22431b823d9555"; :>> judgedAt = "2026-08-23"; :>> judgedBy = "claudeFable5"; }
    verification inboxCutoverCloseOutGate : Test { :>> id = "c7b85c3f-e970-46cd-87e7-f70ca2e48437"; :>> title = "Sprint 437 closeOut gate (autonomous, D0049)"; :>> createdAt = "2026-08-24"; :>> createdBy = "claudeFable5"; :>> method = VerificationMethod::inspect; :>> procedureText = "Autonomous closeOut (D0049). D0206 delivered; the decision-channel is now the sole decision surface; validate + all 48 guards green; zero open issues."; }
    part inboxCutoverCloseOutGateR1 : TestResult { :>> id = "4f767971-3497-47c3-aaa7-216b8a230f6c"; :>> outcome = VerdictKind::pass; :>> judgedAgainst = "3195ad63b80f40db8070afb7ec22431b823d9555"; :>> judgedAt = "2026-08-23"; :>> judgedBy = "claudeFable5"; }
    verification inboxCutoverRetroGate : Test { :>> id = "ceebeb4f-3616-44d4-94e2-a5d63057a880"; :>> title = "Sprint 437 retro gate (autonomous, D0049)"; :>> createdAt = "2026-08-24"; :>> createdBy = "claudeFable5"; :>> method = VerificationMethod::analyze; :>> procedureText = "Autonomous retro (D0049). AVOIDABLE-ISSUE SCAN under rcRecurrence: none - the cutover was clean because the retiring decision (D0206) built its own removal path and gated itself on proof of the replacement; the lesson worth keeping is that a replace-a-channel decision should always ship its own off-ramp and self-gate, which D0206 did. WELL: the whole arc - propose, auto-accept from the issue via GitHub compute, pull down, execute the cutover - ran with the human doing nothing, which is the D0204/D0207 thesis realized end to end. Estimate 1 pt, delivered 1."; }
    part inboxCutoverRetroGateR1 : TestResult { :>> id = "bcf5c678-245b-4b00-b28d-f2795b6c7484"; :>> outcome = VerdictKind::pass; :>> judgedAgainst = "3195ad63b80f40db8070afb7ec22431b823d9555"; :>> judgedAt = "2026-08-23"; :>> judgedBy = "claudeFable5"; }
}
