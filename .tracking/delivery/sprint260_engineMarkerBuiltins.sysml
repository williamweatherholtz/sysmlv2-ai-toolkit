// ProjectDeliveryS260 — Sprint 260: engine markers become builtin to the binary, unblocking a
// downstream project blocked by the D0133 regression (issue089, D0136). v0.2.1. EXECUTE. 2 pts.
package ProjectDeliveryS260 {
    private import EngineElement::*;
    private import EngineWork::*;
    private import EngineVerification::*;
    private import EngineRelationships::*;

    #CharteredBy dependency from engineMarkerBuiltinsStory to d0136;

    part engineMarkerBuiltinsStory : Story {
        :>> id = "0d780001-0814-5801-9b3e-000000280001";
        :>> title = "Sprint 260: ENGINE_MARKERS builtin; project markers declare anywhere; v0.2.1 patch (2 pts)";
        :>> createdAt = "2026-08-14"; :>> createdBy = "claudeOpus5"; :>> kind = WorkKind::code; :>> priority = WorkPriority::p0; :>> owner = "claudeOpus5"; :>> estimatedPoints = 2;
    }

    action def DeliveryRunS260 {
        action storyEngineMarkerBuiltins;
        verification storyEngineMarkerBuiltinsDoD : Test { :>> id = "0d780002-0814-5802-9b3e-000000280002"; :>> method = VerificationMethod::test; :>> procedureText = "Delivers dcEngineMarkerBuiltins (issue089/D0136), a FIELD-REPORTED Critical regression. DEFECT: D0133's marker-vocabulary is a HARD guard in the BINARY whose passing condition was `metadata def` lines in the PROJECT's schema. include_dir! embeds .engine at BUILD time, so a v0.2.0 binary carries the nine declarations while upgrading the binary never touches an existing project's on-disk .engine/schema/. REPRODUCED by simulating the downstream state in this repo: 566 violations, keel guard exit 1, every commit blocked, including on the engine's own shipped files (.engine/rules/rules.sysml) — and the only apparent remedy was editing FROZEN schema/core, so the guard forced downstream projects into a frozen-schema sign-off purely to keep committing. FIX: (a) ENGINE_MARKERS builtin to the binary — the engine's own algebra (17 markers) is always valid with no project declaration, because it is the engine's contract and its own guards consume it; (b) project-declared markers scanned from ANY .engine or .tracking file, so a project declares its own vocabulary without touching frozen core; (c) guard STAYS HARD, since with (a)+(b) the only remaining failures are genuine typos — demoting it to a warning would have traded away D0133's entire value (a misspelled #Verify silently reports a DELIVERED requirement as unverified); (d) the violation message no longer directs the reader to edit frozen schema and now distinguishes 'fix the typo' from 'declare your own marker'. VERIFY (all measured): the reproduced downstream state goes 566 -> 0 violations; `#DerivdFrom` STILL hard-fails with exit 1 IN that same state, so the unblock costs nothing in protection; this repo stays at 0 across 996 scanned markers; unit test asserts all 17 engine markers resolve against an EMPTY project declaration set and that a misspelling does not, so the builtin set cannot silently regress. clippy clean; 156 tests; validate + all 23 guards + check-engine green at c4464de. SHIPPED v0.2.1 with three platform binaries verified attached (linux 7,814,080 / macOS 6,932,128 / windows 6,579,200 bytes)."; }
        part storyEngineMarkerBuiltinsDoDR1 : TestResult { :>> id = "0d780003-0814-5803-9b3e-000000280003"; :>> outcome = VerdictKind::pass; :>> judgedAgainst = "c4464de"; :>> judgedAt = "2026-08-14"; :>> judgedBy = "claudeOpus5"; }
    }

    verification emRefineGate : Test { :>> id = "0d780004-0814-5804-9b3e-000000280004"; :>> title = "Sprint 260 refine gate (DoR)"; :>> createdAt = "2026-08-14"; :>> createdBy = "claudeOpus5"; :>> method = VerificationMethod::inspect; :>> procedureText = "DoR: a field report from another project, taken ahead of the whole frontier because a team was BLOCKED — the one condition that outranks declaration order (D0052 ranks work, it does not rank an outage). The human asked whether it was intended and offered to backfill acceptance; the answer was that it was neither intended nor an acceptance gap, so no sign-off was recorded for it. estimatedPoints=2. DoR met."; }
    part emRefineGateR1 : TestResult { :>> id = "0d780005-0814-5805-9b3e-000000280005"; :>> outcome = VerdictKind::pass; :>> judgedAgainst = "c4464de"; :>> judgedAt = "2026-08-14"; :>> judgedBy = "claudeOpus5"; }

    verification emStandupGate : Test { :>> id = "0d780006-0814-5806-9b3e-000000280006"; :>> title = "Sprint 260 standup gate"; :>> createdAt = "2026-08-14"; :>> createdBy = "claudeOpus5"; :>> method = VerificationMethod::inspect; :>> procedureText = "Approach: REPRODUCE the downstream state locally before theorising about it — simulate a pre-D0133 schema against the current binary and read the real violation count. That turned a plausible hypothesis into a measured 566, and it also revealed the second, worse fact (the only remedy was a frozen-schema edit) which pure reasoning had not surfaced. Then fix at the coupling, not the symptom. No blockers."; }
    part emStandupGateR1 : TestResult { :>> id = "0d780007-0814-5807-9b3e-000000280007"; :>> outcome = VerdictKind::pass; :>> judgedAgainst = "c4464de"; :>> judgedAt = "2026-08-14"; :>> judgedBy = "claudeOpus5"; }

    verification emImplementGate : Test { :>> id = "0d780008-0814-5808-9b3e-000000280008"; :>> title = "Sprint 260 implement gate"; :>> createdAt = "2026-08-14"; :>> createdBy = "claudeOpus5"; :>> method = VerificationMethod::demo; :>> procedureText = "Implemented at c4464de, released as v0.2.1. Both halves were verified in the SAME simulated downstream state — unblock (566 -> 0) and retained protection (#DerivdFrom still exit 1) — because verifying them in different states would prove nothing about the combination. Release followed deploy.sysml: CI green at the exact commit before tagging, then assets confirmed attached via gh release view."; }
    part emImplementGateR1 : TestResult { :>> id = "0d780009-0814-5809-9b3e-000000280009"; :>> outcome = VerdictKind::pass; :>> judgedAgainst = "c4464de"; :>> judgedAt = "2026-08-14"; :>> judgedBy = "claudeOpus5"; }

    verification emReviewGate : Test { :>> id = "0d78000a-0814-580a-9b3e-00000028000a"; :>> title = "Sprint 260 review gate"; :>> createdAt = "2026-08-14"; :>> createdBy = "claudeOpus5"; :>> method = VerificationMethod::inspect; :>> procedureText = "Reviewed. The right call was refusing the two easy exits the human's message offered. It was NOT an acceptance backfill — signing it off would have left the downstream project blocked, since no human judgment was missing, only a defect. And it was NOT a case for demoting the guard to a warning, which would have escaped the regression by discarding the protection D0133 exists for. Fixing the COUPLING keeps both. The durable finding is broader than this guard: a control shipped in the binary must not depend on content the binary cannot guarantee is present or current — the same class as issue076, arriving through DATA instead of a runtime, and structurally invisible in this repo because code and data always move together here. That is worth carrying into every future guard."; }
    part emReviewGateR1 : TestResult { :>> id = "0d78000b-0814-580b-9b3e-00000028000b"; :>> outcome = VerdictKind::pass; :>> judgedAgainst = "c4464de"; :>> judgedAt = "2026-08-14"; :>> judgedBy = "claudeOpus5"; }

    verification emCloseOutGate : Test { :>> id = "0d78000c-0814-580c-9b3e-00000028000c"; :>> title = "Sprint 260 closeOut gate (autonomous, D0049)"; :>> createdAt = "2026-08-14"; :>> createdBy = "claudeOpus5"; :>> method = VerificationMethod::inspect; :>> procedureText = "Autonomous closeOut (D0049). dcEngineMarkerBuiltins carries a passing DoD TestResult at c4464de; issue089 RESOLVES. v0.2.1 published with three platform binaries; downstream projects are unblocked on any schema vintage with NO action required from them. validate + all 23 guards + check-engine green; clippy clean. This was also the first use of the release discipline established one sprint earlier for its actual purpose — shipping an urgent fix."; }
    part emCloseOutGateR1 : TestResult { :>> id = "0d78000d-0814-580d-9b3e-00000028000d"; :>> outcome = VerdictKind::pass; :>> judgedAgainst = "c4464de"; :>> judgedAt = "2026-08-14"; :>> judgedBy = "claudeOpus5"; }

    verification emRetroGate : Test { :>> id = "0d78000e-0814-580e-9b3e-00000028000e"; :>> title = "Sprint 260 retro gate (autonomous, D0049)"; :>> createdAt = "2026-08-14"; :>> createdBy = "claudeOpus5"; :>> method = VerificationMethod::analyze; :>> procedureText = "Autonomous retro (D0049) under D0131's retroTrack. WELL: (1) the downstream state was REPRODUCED before being theorised about, which produced the real number (566) and surfaced the worse second fact (the only remedy was a frozen-schema edit) that reasoning alone had missed; (2) both easy exits were refused — acceptance backfill would have left the team blocked, and demoting the guard would have discarded the protection; (3) unblock and retained protection were verified in the SAME state, since separate states would prove nothing about the combination. AVOIDABLE-ISSUE 1 (the substantive one): I shipped a HARD guard whose passing condition lived in data the binary does not control, and could not see it because in this repo code and data always move in one commit. This is the third distinct instance this sitting of a control coupled to something it cannot guarantee — issue076 (a gate needing a possibly-absent runtime), issue081 (a gate whose bypass disabled every other layer), and now this. TRACKED: no new item, because D0136 records the general rule and srGovSelfDetectingDiscipline already owns the ambition of computing such disagreements; but the recurrence count is now three, and the next new guard should state explicitly what it depends on and whether the binary can guarantee it. AVOIDABLE-ISSUE 2: my own violation message told the reader to edit FROZEN schema/core — the guard's advice would have pushed a downstream project into exactly the imposition that made this Critical. Fixed in the same change; no new item, it was part of this defect. Estimate 2 pts, delivered."; }
    part emRetroGateR1 : TestResult { :>> id = "0d78000f-0814-580f-9b3e-00000028000f"; :>> outcome = VerdictKind::pass; :>> judgedAgainst = "c4464de"; :>> judgedAt = "2026-08-14"; :>> judgedBy = "claudeOpus5"; }
}
