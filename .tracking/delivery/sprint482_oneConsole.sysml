// ProjectDeliveryS482 - Sprint 482: one console for many projects. keel serve attaches instead of spawning, and the selector lists projects that ASKED to be there. EXECUTE. 5 pts.
package ProjectDeliveryS482 {
    private import EngineElement::*;
    private import EngineWork::*;
    private import EngineVerification::*;
    private import EngineRelationships::*;

    #CharteredBy dependency from oneConsoleStory to d0245;

    part oneConsoleStory : Story {
        :>> id = "d31e1256-7410-4033-b9e5-e3d9e6bdeac2";
        :>> title = "Sprint 482: one console per machine - a registry of served projects, and keel serve becomes idempotent (5 pts)";
        :>> createdAt = "2026-08-28"; :>> createdBy = "claudeOpus5"; :>> kind = WorkKind::code; :>> priority = WorkPriority::p1; :>> owner = "claudeOpus5"; :>> estimatedPoints = 5;
    }

    action def DeliveryRunS482 {
        action storyOneConsole;
        verification storyOneConsoleDoD : Test { :>> id = "c456286c-d453-47b0-8d8a-45b4c233770d"; :>> method = VerificationMethod::test; :>> procedureText = "DELIVERED: oneConsoleManyProjects (D0245). A machine-local registry outside every repository records the projects a console can reach; keel serve asks whether one of OURS is already answering and, if so, registers and exits 0 rather than binding; /api/projects reads the registry instead of scanning sibling directories, so a project in another repo appears and one that was never served does not; keel serve --forget deregisters without touching the project. The human chose PRUNE DEAD, KEEP THE REST and READ ANY, WRITE ACTIVE ONLY - the second because one tab that can write into eight repositories is a materially larger authority surface than eight tabs that each write into one, and Decision acceptance through that surface is their own attestation."; }
    // RAN: cargo test --release => 14 suites 0 failures; cargo clippy --release --all-targets => 0 errors; keel validate . => 537 clean; keel guard => 0 of 52 failing | LIVE against the human's own running console: keel serve from penumbra, passext and se-templates each printed 'ALREADY RUNNING ... attached, did not start a second' and exited 0 without binding | registry at USERPROFILE/.keel/console.json holds 4 projects from 4 SEPARATE repos, canonical absolute roots plus repo and lastServed | git check-ignore reports the file is OUTSIDE the repository; git status shows 0 tracked changes for it | unit: distinct labels stay short, colliding labels qualify by repo; console_on(unbound) is false.
        part storyOneConsoleDoDR1 : TestResult { :>> id = "1b3b177e-4902-41c5-8b19-7530dfe88edd"; :>> outcome = VerdictKind::pass; :>> judgedAgainst = "2bec54d"; :>> judgedAt = "2026-08-28"; :>> judgedBy = "claudeOpus5"; }
    }

    verification oneConsoleRefineGate : Test { :>> id = "a6d15ffe-7a6f-4558-8019-755a688125b7"; :>> title = "Sprint 482 refine gate (DoR)"; :>> createdAt = "2026-08-28"; :>> createdBy = "claudeOpus5"; :>> method = VerificationMethod::inspect; :>> procedureText = "DoR: the human reported too many keel serve windows, new projects starting their own, and a selector that 'is not actually projects requesting to tap into keel serve, it seems to be based on directory structure'. Measured before designing: serve binds 7777 and HARD-ERRORS when taken, and api_projects scanned the PARENT directory for siblings - which works on this machine only because all eight projects happen to share a parent, and never for a project in another repository. The diagnosis matched the report exactly. Ten use cases were written out before any code. Resolver: oneConsoleManyProjects. estimatedPoints=5. #CharteredBy d0245."; }
    part oneConsoleRefineGateR1 : TestResult { :>> id = "956e8197-d3e2-4e38-b861-7454cbdbfdbf"; :>> outcome = VerdictKind::pass; :>> judgedAgainst = "2bec54d"; :>> judgedAt = "2026-08-28"; :>> judgedBy = "claudeOpus5"; }
    verification oneConsoleStandupGate : Test { :>> id = "d6eaf9c1-93a6-451b-b7eb-30ebf67a5b53"; :>> title = "Sprint 482 standup gate"; :>> createdAt = "2026-08-28"; :>> createdBy = "claudeOpus5"; :>> method = VerificationMethod::inspect; :>> procedureText = "Approach: two questions were put to the human because they are theirs, not mine - the write scope of a cross-repo console, and how a project leaves the list. Both recommendations were taken. THE PRINCIPLE BEND WAS STATED RATHER THAN SLIPPED PAST: api_projects carried the comment 'A config file would be a second place to keep the list true, and the filesystem already knows', and that reasoning is right for workspace discovery and WRONG here, because which projects an operator wants in their console is a preference spanning repositories, not a fact the tree holds. The registry keeps the spirit by being a RECORD OF AN ACT - an entry exists because someone ran serve there, and is pruned when the directory goes - so there is nothing to hand-maintain and no second truth to keep."; }
    part oneConsoleStandupGateR1 : TestResult { :>> id = "8f92f85e-5af2-441f-8483-95c59330cd0e"; :>> outcome = VerdictKind::pass; :>> judgedAgainst = "2bec54d"; :>> judgedAt = "2026-08-28"; :>> judgedBy = "claudeOpus5"; }
    verification oneConsoleImplementGate : Test { :>> id = "643b2e76-8d6a-440a-87e8-aa907eeba1c5"; :>> title = "Sprint 482 implement gate"; :>> createdAt = "2026-08-28"; :>> createdBy = "claudeOpus5"; :>> method = VerificationMethod::test; :>> procedureText = "Implemented and tested against the human's OWN running console rather than a fixture, which is what caught the defect worth recording: console_on matched the literal lowercase 'keel', and a real console's /api/version payload spells it only as viewerKeelApi. So detection returned false, serve fell through to binding, and hard-errored on the occupied port - the exact failure the function exists to prevent, produced by the function itself. A fixture I built would have used whatever string I had in mind. Fixed to a case-insensitive check on fields only our console serves."; }
    // RAN: cargo test --release => 14 suites 0 failures; cargo clippy --release --all-targets => 0 errors; keel validate . => 537 clean; keel guard => 0 of 52 failing | LIVE against the human's own running console: keel serve from penumbra, passext and se-templates each printed 'ALREADY RUNNING ... attached, did not start a second' and exited 0 without binding | registry at USERPROFILE/.keel/console.json holds 4 projects from 4 SEPARATE repos, canonical absolute roots plus repo and lastServed | git check-ignore reports the file is OUTSIDE the repository; git status shows 0 tracked changes for it | unit: distinct labels stay short, colliding labels qualify by repo; console_on(unbound) is false.
    part oneConsoleImplementGateR1 : TestResult { :>> id = "01cb0864-9ac3-42fd-aa5c-238fbd546d0b"; :>> outcome = VerdictKind::pass; :>> judgedAgainst = "2bec54d"; :>> judgedAt = "2026-08-28"; :>> judgedBy = "claudeOpus5"; }
    verification oneConsoleReviewGate : Test { :>> id = "385c44fd-b8e4-4369-9e1a-46c524290d90"; :>> title = "Sprint 482 review gate"; :>> createdAt = "2026-08-28"; :>> createdBy = "claudeOpus5"; :>> method = VerificationMethod::inspect; :>> procedureText = "Diff reviewed. Write scope is unchanged by design: rebind already REFUSED an invalid target rather than falling back, and read-any/write-active-only is exactly that behaviour extended to registry-listed projects, so no new write path was opened. Two residuals are named rather than assumed away. First, the human's CURRENTLY RUNNING console is an older binary, so its selector still scans siblings until it is restarted - the attach half works today, the selector half needs a restart. Second, version skew: a console started from one project's binary now serves another project whose .engine may be a different vintage; the per-project engine-version warning still fires, but whether the SERVER's version should be checked against each registered project is left open in D0245 rather than silently assumed safe."; }
    part oneConsoleReviewGateR1 : TestResult { :>> id = "9a889997-8ff4-4119-80b5-bce72d036bff"; :>> outcome = VerdictKind::pass; :>> judgedAgainst = "2bec54d"; :>> judgedAt = "2026-08-28"; :>> judgedBy = "claudeOpus5"; }
    verification oneConsoleCloseOutGate : Test { :>> id = "a32f4915-f230-46a8-956c-fa6f3b3ac6bc"; :>> title = "Sprint 482 closeOut gate (autonomous, D0049)"; :>> createdAt = "2026-08-28"; :>> createdBy = "claudeOpus5"; :>> method = VerificationMethod::inspect; :>> procedureText = "Autonomous closeOut (D0049): the DoD is recorded pass with its RAN receipt, verified live across four separate repositories. The reported problem - running serve in a second project produces a second window - no longer reproduces. Self-evidencing (D0051): no human confirmation is claimed; the two choices they made were recorded as their choices in D0245, not as attestations."; }
    part oneConsoleCloseOutGateR1 : TestResult { :>> id = "1a0b14f5-ab0a-4e25-9464-eb424017363d"; :>> outcome = VerdictKind::pass; :>> judgedAgainst = "2bec54d"; :>> judgedAt = "2026-08-28"; :>> judgedBy = "claudeOpus5"; }
    verification oneConsoleRetroGate : Test { :>> id = "982362a7-fa57-4e4b-953c-eec4b33bb664"; :>> title = "Sprint 482 retro gate (autonomous, D0049)"; :>> createdAt = "2026-08-28"; :>> createdBy = "claudeOpus5"; :>> method = VerificationMethod::analyze; :>> procedureText = "Autonomous retro (D0049). WELL: testing against the human's live console instead of a fixture found a defect a fixture could not have - my detector looked for a string I had imagined rather than the one a real console emits. That is the second time this session that using the real artefact beat using my model of it. Asking the two questions up front was also right: the write- scope answer changed what I built, and guessing it would have quietly widened an authority surface over eight repositories. FINDING: the sibling scan was defensible when written and became wrong when the human's working arrangement changed - eight repos instead of one tree. Nothing detected the drift; it took the human noticing windows piling up. A design justified by 'the filesystem already knows' is only as good as the assumption about what the filesystem is asked to know, and that assumption was never written down as an assumption. AVOIDABLE-ISSUE SCAN: the code comment asserting the config-file argument read as settled principle rather than as a scoped judgement, which is why it survived unexamined until now. Candidate forward control, stated not built: a rejected alternative recorded in a code comment should name the CONDITION under which it would become the right choice. Estimate 5 pts held."; }
    part oneConsoleRetroGateR1 : TestResult { :>> id = "a0338390-0bbf-4ecd-b363-d1bbd284ce46"; :>> outcome = VerdictKind::pass; :>> judgedAgainst = "2bec54d"; :>> judgedAt = "2026-08-28"; :>> judgedBy = "claudeOpus5"; }
}
