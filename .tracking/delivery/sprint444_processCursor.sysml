// ProjectDeliveryS444 — Sprint 444: keel advance - the process cursor: the sprint ceremony machine, promoted from a reference to an executed forward gate (D0209 clause 3). EXECUTE. 3 pts.
package ProjectDeliveryS444 {
    private import EngineElement::*;
    private import EngineWork::*;
    private import EngineVerification::*;
    private import EngineRelationships::*;

    #CharteredBy dependency from processCursorStory to d0209;

    part processCursorStory : Story {
        :>> id = "d415729c-df21-4621-bd32-576f13becc29";
        :>> title = "Sprint 444: the AI can be REFUSED in-loop for skipping a step (3 pts)";
        :>> createdAt = "2026-08-24"; :>> createdBy = "claudeFable5"; :>> kind = WorkKind::code; :>> priority = WorkPriority::p0; :>> owner = "claudeFable5"; :>> estimatedPoints = 3;
    }

    action def DeliveryRunS444 {
        action storyProcessCursor;
        verification storyProcessCursorDoD : Test { :>> id = "c3bb8964-8f2b-4c98-86fd-a78d50e2016d"; :>> method = VerificationMethod::test; :>> procedureText = "DELIVERED: dcProcessCursor (D0209 clause 3, the manager-inversion panel's third increment). keel advance promotes the sprint ceremony ProcessStep machine (Refine->Standup->Implement->Review->CloseOut->Retro) from a reference the AI reads - and the ceremony guard checks only POST-HOC at commit - into an EXECUTED, in-loop cursor. keel advance <sprint> prints the cursor: the current step is the first defined gate without a passing verify-Test; it exits 1 if the tree already holds an out-of-order pass. keel advance <sprint> --to <Gate> is the forward gate: permitted only if every DEFINED gate earlier than the target has a passing verify-Test, else REFUSED (exit 1) naming the unpassed earlier step - literally 'step N+1 is refused until step N passes' (D0098 order-gating, made executable, bounded, no topology inversion). The cursor is COMPUTED from the delivery file every call (never stored, D0018); the step order is orient::GATE_ORDER, the single source shared with orient and the ceremony guard (no third copy - orient's const was promoted to pub(crate) rather than duplicated). This is the one genuine D0098 gap the panel named: the sequence was declared and the AI self-followed it; now keel tracks the position and refuses a skip in-loop, not only at the commit boundary. VERIFIED end-to-end against real sprints: the COMPLETE sprint443 reports 'all defined gates passed, ceremony complete' (exit 0); a PARTIAL sprint (Refine+Standup passed) reports current step Implement (exit 0); --to Standup is PERMITTED (exit 0); --to CloseOut is REFUSED naming Implement, Review (exit 1). Four lib unit tests pin cursor/complete/out-of-order/defined-not-result; workspace clippy --all-targets clean. NOT in scope (bounded): the generic ProcessStep sub-steps inside a phase (refineCriteria->refineSize...) have no per-run pass state, so no cursor computes over them - the ceremony gate chain is the only machine with per-run verify-Tests, and that is exactly what makes a cursor computable."; }
        part storyProcessCursorDoDR1 : TestResult { :>> id = "bf42d7e0-f572-4711-bd6e-95e0528e4f30"; :>> outcome = VerdictKind::pass; :>> judgedAgainst = "cdd6fab87566075cee5338e2d549ccc43adc43df"; :>> judgedAt = "2026-08-23"; :>> judgedBy = "claudeFable5"; }
    }

    verification processCursorRefineGate : Test { :>> id = "49d4b291-ef40-4259-84c0-93dddbe718f8"; :>> title = "Sprint 444 refine gate (DoR)"; :>> createdAt = "2026-08-24"; :>> createdBy = "claudeFable5"; :>> method = VerificationMethod::inspect; :>> procedureText = "DoR. Delivers D0209 clause 3, the panel's one-genuine-gap increment (D0098 deferred order-gating). Scope: a keel advance command that computes the sprint's ceremony cursor and refuses a forward transition past an unpassed step, reusing the existing gate-Test machinery - no schema change, no topology inversion. 3 points."; }
    part processCursorRefineGateR1 : TestResult { :>> id = "f1b3d5f6-cfd9-4424-83da-1bff126245a9"; :>> outcome = VerdictKind::pass; :>> judgedAgainst = "cdd6fab87566075cee5338e2d549ccc43adc43df"; :>> judgedAt = "2026-08-23"; :>> judgedBy = "claudeFable5"; }
    verification processCursorStandupGate : Test { :>> id = "ff2b18f6-f8fb-4258-93ec-dd64d982925c"; :>> title = "Sprint 444 standup gate"; :>> createdAt = "2026-08-24"; :>> createdBy = "claudeFable5"; :>> method = VerificationMethod::inspect; :>> procedureText = "Approach: the sprint ceremony gate chain is the ONLY declared ProcessStep machine with per-run pass state (each gate is a verification Test with a pass/fail result), so it is the only place a cursor is computable - the generic phase sub-steps have no per-run state. Reuse orient::gate_passed and orient::GATE_ORDER (promote the const to pub(crate), do NOT copy it). New module cursor.rs; dispatch in main.rs; neither is on the enforcement surface, so no marked decision is needed and D0209 already charters it. No blockers."; }
    part processCursorStandupGateR1 : TestResult { :>> id = "f9ae68d8-aa0e-4db3-8e09-1ad7cc6e6d56"; :>> outcome = VerdictKind::pass; :>> judgedAgainst = "cdd6fab87566075cee5338e2d549ccc43adc43df"; :>> judgedAt = "2026-08-23"; :>> judgedBy = "claudeFable5"; }
    verification processCursorImplementGate : Test { :>> id = "f9dd38f5-98f8-46f2-b683-cf4c6a3f33d2"; :>> title = "Sprint 444 implement gate"; :>> createdAt = "2026-08-24"; :>> createdBy = "claudeFable5"; :>> method = VerificationMethod::test; :>> procedureText = "Verified by running the built binary end-to-end: complete sprint443 -> ceremony complete (exit 0); partial sprint -> current step Implement (exit 0); --to Standup PERMITTED (exit 0); --to CloseOut REFUSED naming Implement, Review (exit 1). cargo test --lib cursor -> 4 passed (cursor-is-first-unpassed, complete-has-no-current, out-of-order-detected, defined-needs-Test-not-Result). cargo clippy --workspace --all-targets -D warnings clean after fixing doc_markdown, must_use, similar-binding (stem vs step), panic-index, and format-append lints."; }
    part processCursorImplementGateR1 : TestResult { :>> id = "ba849f49-1006-48c6-b8a5-9f699ac7f569"; :>> outcome = VerdictKind::pass; :>> judgedAgainst = "cdd6fab87566075cee5338e2d549ccc43adc43df"; :>> judgedAt = "2026-08-23"; :>> judgedBy = "claudeFable5"; }
    verification processCursorReviewGate : Test { :>> id = "d8212175-e8a1-4f85-97e9-7376a4a2253f"; :>> title = "Sprint 444 review gate — three passes per D0172"; :>> createdAt = "2026-08-24"; :>> createdBy = "claudeFable5"; :>> method = VerificationMethod::inspect; :>> procedureText = "PASS 1, CLAIMS: the four CLI exit codes and the 4-passed test line are quoted read-backs from the built binary. PASS 2, BOUNDARY: the cursor binds to the ceremony gate chain, NOT the generic ProcessStep sub-steps (refineCriteria->refineSize) - those have no per-run pass state so no cursor computes; stated in the DoD, not hidden. advance is an in-loop HELPER, not a commit gate: it does not run in a hook or CI, so it complements (does not replace) the ceremony guard's post-hoc hard block. gate_defined keys on the string 'XGate : Test' - a gate declared with unusual whitespace would be missed, but the scaffold format is fixed so the real case is covered. PASS 3, OWN DIFF: the interpretation was genuinely ambiguous (ProcessStep chains vs ceremony gates); I chose the binding FORCED by computability - only the gate chain has per-run verify-Tests - and recorded that reasoning so a reviewer can challenge it. WHAT A REVIEWER SHOULD ATTACK: whether an in-loop advisory cursor adds enough over the existing commit-time ceremony guard to justify a new command; the answer is that it makes the position queryable and refuses a skip BEFORE the work, which is the 'executed not referenced' promotion the clause asked for."; }
    part processCursorReviewGateR1 : TestResult { :>> id = "131606b9-58d8-4c26-a41e-1676353b9ca7"; :>> outcome = VerdictKind::pass; :>> judgedAgainst = "cdd6fab87566075cee5338e2d549ccc43adc43df"; :>> judgedAt = "2026-08-23"; :>> judgedBy = "claudeFable5"; }
    verification processCursorCloseOutGate : Test { :>> id = "de3466d3-ef12-4e9a-8a30-7f859bc934cb"; :>> title = "Sprint 444 closeOut gate (autonomous, D0049)"; :>> createdAt = "2026-08-24"; :>> createdBy = "claudeFable5"; :>> method = VerificationMethod::inspect; :>> procedureText = "Autonomous closeOut (D0049). D0209 clause 3 delivered and verified end-to-end + unit-tested; validate + all 48 guards + rules --enforce green after this covering sprint; the impl landed at cdd6fab; only clause 4 (dcProactivePostEdit) remains on the frontier."; }
    part processCursorCloseOutGateR1 : TestResult { :>> id = "3b318b12-9793-4f63-87ee-dcdd33ba89cf"; :>> outcome = VerdictKind::pass; :>> judgedAgainst = "cdd6fab87566075cee5338e2d549ccc43adc43df"; :>> judgedAt = "2026-08-23"; :>> judgedBy = "claudeFable5"; }
    verification processCursorRetroGate : Test { :>> id = "c65ca384-0fce-4c65-b294-5d0ea700f2f5"; :>> title = "Sprint 444 retro gate (autonomous, D0049)"; :>> createdAt = "2026-08-24"; :>> createdBy = "claudeFable5"; :>> method = VerificationMethod::analyze; :>> procedureText = "Autonomous retro (D0049). AVOIDABLE-ISSUE SCAN under rcRecurrence: the ciClippyGreen class recurred AGAIN and heavier this time - a brand-new module drew 14 clippy errors (doc_markdown, must_use, similar-binding, panic-index, format-append) that the release build did NOT catch because release build != clippy; the durable habit, now firmly relearned: run cargo clippy --workspace --all-targets on ANY new module BEFORE committing, never trust a green release build. WELL: the design ambiguity (what the cursor binds to) was resolved by a principle (computability forces the ceremony-gate binding) rather than a guess, and the end-to-end demo on a real complete sprint plus a crafted partial one proved both the permit and the refuse paths. Estimate 3 pts, delivered 3."; }
    part processCursorRetroGateR1 : TestResult { :>> id = "06334eb6-fce9-46ed-acdb-68ca688a9e66"; :>> outcome = VerdictKind::pass; :>> judgedAgainst = "cdd6fab87566075cee5338e2d549ccc43adc43df"; :>> judgedAt = "2026-08-23"; :>> judgedBy = "claudeFable5"; }
}
