// ProjectDeliveryS319 — Sprint 319: a resolver that cannot resolve is a violation, and a mistyped flag
// is an error instead of a path. CHANGE + EXECUTE. 5 pts.
package ProjectDeliveryS319 {
    private import EngineElement::*;
    private import EngineWork::*;
    private import EngineVerification::*;
    private import EngineRelationships::*;

    #CharteredBy dependency from triageFlagsStory to d0047;

    part triageFlagsStory : Story {
        :>> id = "0d8003a0-0814-63a0-9b3e-0000003003a0";
        :>> title = "Sprint 319: resolver-kind guard + the catch-all-as-root sweep (5 pts)";
        :>> createdAt = "2026-08-17"; :>> createdBy = "claudeOpus5"; :>> kind = WorkKind::code; :>> priority = WorkPriority::p0; :>> owner = "claudeOpus5"; :>> estimatedPoints = 5;
    }

    action def DeliveryRunS319 {
        action storyTriageFlags;
        verification storyTriageFlagsDoD : Test { :>> id = "0d8003a1-0814-63a1-9b3e-0000003003a1"; :>> method = VerificationMethod::test; :>> procedureText = "Two resolvers, one root cause — a wrong input accepted as a plausible one. (1) issue136 + guard `resolver-kind` (the 34th, hard-blocking): a #Resolves resolver must be a declared action or a Decision. Found because the frontier emptied and I checked whether the two remaining open issues were REALLY triaged: issue133's edge pointed at a viewer SystemRequirement, pasted from issue132's edge on the line above, and `open-issues` reported untriaged=false for both. VERIFIED BOTH WAYS, which is the only way a guard is verified: PASS at 135 edges, and when the bad edge is reintroduced it FAILS naming srViewerPersistedViewState and its type. (2) issue133's unfinished half: 28 subcommand parsers took their first argument as ROOT, so `keel audit --explan` made the root the literal string `--explan`; 4 more SKIPPED anything starting with `--`, so an unknown flag was silently ignored and the command ran with the wrong behaviour. All 28 now route through one `root_arg` helper that refuses an undeclared flag with the usage line. VERIFIED LIVE: `audit --explan` exits 2 with the usage line, `audit .` exits 0, `suspect --explain .` still works, `view decisions .` still resolves its trailing ROOT, and `migrate --dryrun` refuses instead of rewriting the current directory. clippy clean; 227 tests; validate 346 clean; check-engine clean; 34 guards green."; }
        part storyTriageFlagsDoDR1 : TestResult { :>> id = "0d8003a2-0814-63a2-9b3e-0000003003a2"; :>> outcome = VerdictKind::pass; :>> judgedAgainst = "5547107"; :>> judgedAt = "2026-08-17"; :>> judgedBy = "claudeOpus5"; }
    }

    verification tfRefineGate : Test { :>> id = "0d8003a3-0814-63a3-9b3e-0000003003a3"; :>> title = "Sprint 319 refine gate (DoR)"; :>> createdAt = "2026-08-17"; :>> createdBy = "claudeOpus5"; :>> method = VerificationMethod::inspect; :>> procedureText = "DoR. THE FRONTIER WAS EMPTY, which is a pause condition, and what filled it was checking the two open issues rather than accepting their reported state — `open-issues` said both were triaged and one provably was not. The three items were then declared as backlog actions BEFORE being worked (dcResolverKindGuard, dcRootArmSweep, dcNeed8ScopeNarrowing), so the work is chartered rather than ad-hoc: two rank ready and the third is blocked by construction. estimatedPoints=5."; }
    part tfRefineGateR1 : TestResult { :>> id = "0d8003a4-0814-63a4-9b3e-0000003003a4"; :>> outcome = VerdictKind::pass; :>> judgedAgainst = "5547107"; :>> judgedAt = "2026-08-17"; :>> judgedBy = "claudeOpus5"; }

    verification tfStandupGate : Test { :>> id = "0d8003a5-0814-63a5-9b3e-0000003003a5"; :>> title = "Sprint 319 standup gate"; :>> createdAt = "2026-08-17"; :>> createdBy = "claudeOpus5"; :>> method = VerificationMethod::inspect; :>> procedureText = "Approach: MEASURE the class before writing the control (of 134 #Resolves edges, 127 from actions, 5 from Decisions, exactly 2 from a requirement) so the rule matches the corpus and the guard starts at zero rather than needing a grandfather list. For the flag sweep, ONE shared helper rather than 28 hand-edits, since 28 copies of a rule is how the rule ends up applied 27 times. issue132 cannot be worked at all — the Need is human-owned — so it gets a PROPOSED Decision and a blocked action rather than a place on my frontier. No blockers."; }
    part tfStandupGateR1 : TestResult { :>> id = "0d8003a6-0814-63a6-9b3e-0000003003a6"; :>> outcome = VerdictKind::pass; :>> judgedAgainst = "5547107"; :>> judgedAt = "2026-08-17"; :>> judgedBy = "claudeOpus5"; }

    verification tfImplementGate : Test { :>> id = "0d8003a7-0814-63a7-9b3e-0000003003a7"; :>> title = "Sprint 319 implement gate"; :>> createdAt = "2026-08-17"; :>> createdBy = "claudeOpus5"; :>> method = VerificationMethod::test; :>> procedureText = "THE GUARD IS A BESPOKE PREDICATE AND THAT IS DELIBERATE, under D0107's bad-fit precedent rather than as a shortcut: `issuesTriagedRule` is an EdgeRule whose `objectType` filters by declared item TYPE, and an `action` is not a typed element — set it to anything but `*` and all 127 legitimate action resolvers fail. Extending the rule language to express 'action OR Decision' is the larger change; the rule keeps `objectType = \"*\"` because that is honestly all it can currently say, and the constraint is checked in Rust meanwhile. THREE THINGS THE COMPILER AND THE SWEEP CAUGHT that a careless pass would have shipped: `GUARD_NAMES` is a fixed-size array so the count had to move 33 -> 34 (a hard compile error, which is the right kind of control); two parsers build their usage line from a subcommand-name parameter, so a literal `\"keel {usage} [ROOT]\"` would have printed the braces — clippy flagged the un-interpolated literal; and `keel ls` had no usage line at all, so the mechanical sweep skipped it rather than inventing one, and it was converted by hand. Coverage of the class is REPORTED not claimed: 28 sites converted mechanically, 4 by hand, 0 of either shape remaining, re-scanned after the change."; }
    part tfImplementGateR1 : TestResult { :>> id = "0d8003a8-0814-63a8-9b3e-0000003003a8"; :>> outcome = VerdictKind::pass; :>> judgedAgainst = "5547107"; :>> judgedAt = "2026-08-17"; :>> judgedBy = "claudeOpus5"; }

    verification tfReviewGate : Test { :>> id = "0d8003a9-0814-63a9-9b3e-0000003003a9"; :>> title = "Sprint 319 review gate"; :>> createdAt = "2026-08-17"; :>> createdBy = "claudeOpus5"; :>> method = VerificationMethod::inspect; :>> procedureText = "Reviewed. A NOMINALLY-TRIAGED ISSUE IS WORSE THAN AN UNTRIAGED ONE and that is the finding worth keeping: an untriaged issue is reported as a gap and gets fixed, while issue133 reported as handled for two days with nothing on the hook for it, and it passed validate, check-engine, the fast gate and all 33 guards — because every one of them checked that the EDGE existed and none asked what was on the other end. Same shape as issue109 one level up: there the endpoint resolved to nothing, here it resolved to the wrong KIND of thing. The flag sweep is the same defect in the CLI: an input that could not be what it was taken for, accepted anyway. issue132 is untouched on purpose — D0108 forbids a non-owner editing a human's Need, so proposing D0156 and blocking the work is the whole of what I may do."; }
    part tfReviewGateR1 : TestResult { :>> id = "0d8003aa-0814-63aa-9b3e-0000003003aa"; :>> outcome = VerdictKind::pass; :>> judgedAgainst = "5547107"; :>> judgedAt = "2026-08-17"; :>> judgedBy = "claudeOpus5"; }

    verification tfCloseOutGate : Test { :>> id = "0d8003ab-0814-63ab-9b3e-0000003003ab"; :>> title = "Sprint 319 closeOut gate (autonomous, D0049)"; :>> createdAt = "2026-08-17"; :>> createdBy = "claudeOpus5"; :>> method = VerificationMethod::inspect; :>> procedureText = "Autonomous closeOut (D0049). issue133 and issue136 resolved; issue132 remains open and BLOCKED on D0156, which is proposed and awaiting wweatherholtz — it appears in `pendingAcceptances` and in the authority queue, not on the ready frontier. Doc-sync rode the change: guards.md 33 -> 34 guards and 24 -> 25 hard-blocking with the new row, and CLAUDE.md's guard count. clippy clean; 227 tests; validate 346 clean; check-engine clean; 34 guards green."; }
    part tfCloseOutGateR1 : TestResult { :>> id = "0d8003ac-0814-63ac-9b3e-0000003003ac"; :>> outcome = VerdictKind::pass; :>> judgedAgainst = "5547107"; :>> judgedAt = "2026-08-17"; :>> judgedBy = "claudeOpus5"; }

    verification tfRetroGate : Test { :>> id = "0d8003ad-0814-63ad-9b3e-0000003003ad"; :>> title = "Sprint 319 retro gate (autonomous, D0049)"; :>> createdAt = "2026-08-17"; :>> createdBy = "claudeOpus5"; :>> method = VerificationMethod::analyze; :>> procedureText = "Autonomous retro (D0049) under D0131's retroTrack. WELL: (1) not believing a computed view about itself — `open-issues` reported both remaining issues as triaged and the check found one that was not, which is the D0151 discipline applied to a report rather than to my own prose; (2) the guard was verified in the FAILING direction by reintroducing the exact defect, because a guard only ever tested green is a guard nobody has tested; (3) the class was measured before the rule was written, so the guard starts at zero with no grandfather list to maintain. AVOIDABLE-ISSUE: I reverted the injected test defect with `git checkout .tracking/issues.sysml`, which discarded the file's UNCOMMITTED work as well — the repointed edges and the whole of issue136 — and the guard then reported 2 violations, which I briefly read as the fix having failed. Re-authored from the transcript, so nothing was lost but the time. THE CONTROL IS TO INJECT SOMEWHERE ELSE: a defect injected into a file that holds uncommitted work cannot be undone by reverting that file, so inject into a temp copy of the tree, or undo by the exact inverse edit. `git checkout <path>` is not an undo — it is a discard, and it does not distinguish my injection from my work. Estimate 5 pts, delivered."; }
    part tfRetroGateR1 : TestResult { :>> id = "0d8003ae-0814-63ae-9b3e-0000003003ae"; :>> outcome = VerdictKind::pass; :>> judgedAgainst = "5547107"; :>> judgedAt = "2026-08-17"; :>> judgedBy = "claudeOpus5"; }
}
