// ProjectDeliveryS611 — Sprint 611: Sprint 611 makes the checksum a normal part of the release (dcReleaseAssetsCarryChecksums, resolves issue417 and issue418) under D0385: release.yml hashes each asset in the job that built it and publishes the hash beside it, a checksums job verifies the published binaries against one SHA256SUMS before attaching it, guard release-checksums-published holds the workflow to that, guard wrapper-pin-checksummed warns when the pinned engine has no wrapper entry, the release skill names the step, and keel-wrapper.toml gains the 0.4.1 entries the pin has lacked since 2026-09-06.. EXECUTE. 3 pts.
package ProjectDeliveryS611 {
    private import EngineElement::*;
    private import EngineWork::*;
    private import EngineVerification::*;
    private import EngineRelationships::*;

    #CharteredBy dependency from releaseChecksumsStory to d0385;

    part releaseChecksumsStory : Story {
        :>> id = "bb7b4a13-9253-4f5a-9278-cd6cd985f81e";
        :>> title = "Sprint 611: Sprint 611 makes the checksum a normal part of the release (dcReleaseAssetsCarryChecksums, resolves issue417 and issue418) under D0385: release.yml hashes each asset in the job that built it and publishes the hash beside it, a checksums job verifies the published binaries against one SHA256SUMS before attaching it, guard release-checksums-published holds the workflow to that, guard wrapper-pin-checksummed warns when the pinned engine has no wrapper entry, the release skill names the step, and keel-wrapper.toml gains the 0.4.1 entries the pin has lacked since 2026-09-06. (3 pts)";
        :>> createdAt = "2026-09-08"; :>> createdBy = "claudeOpus5"; :>> kind = WorkKind::code; :>> priority = WorkPriority::p0; :>> owner = "claudeOpus5"; :>> estimatedPoints = 3;
    }

    action def DeliveryRunS611 {
        action storyReleaseChecksums;
        verification storyReleaseChecksumsDoD : Test { :>> id = "9db08849-d726-4714-9587-f6d42c2c2dfc"; :>> method = VerificationMethod::test; :>> procedureText = "DONE MEANS: a keel release cannot publish a binary without its SHA-256 beside it, and the release process names the checksum at every step that consumes it. Resolves issue417 and issue418. DO: .github/workflows/release.yml hashes each staged asset in the job that built it and attaches `<asset>.sha256` (sha256sum format) with the binary; a `checksums` job after the matrix downloads every `.sha256`, writes one `SHA256SUMS`, downloads the binaries and VERIFIES them against it with `sha256sum -c` before attaching it. Guard `release-checksums-published` (HARD) fails a workflow that attaches release assets without hashing them and publishing the hash; guard `wrapper-pin-checksummed` (WARN) reports when the pinned engine version has no entry in keel-wrapper.toml for a release asset the wrapper can download. The release skill's step 3 verifies the downloaded asset against the published SHA256SUMS and copies the entries into keel-wrapper.toml before step 4 records the Release; keel-wrapper.toml gains the 0.4.1 entries computed from the published assets. VERIFY: the guard tests read FAIL / clean and WARN / clean on constructed trees; `keel guard` is clean on this tree with both guards enforced; the release skill and deploy process text name the step."; }
        // RAN: release.yml hash steps + checksums job; guards 66/67 with 6 integration tests passing; keel-wrapper.toml 0.4.1 entries hashed from the assets gh release download v0.4.1 returned 2026-09-08; release skill and deploy process text name the step; keel guard exit 0 with 67 guards
        part storyReleaseChecksumsDoDR1 : TestResult { :>> id = "3eb2ff24-b2fd-490f-b8e4-e8ec973879dc"; :>> outcome = VerdictKind::pass; :>> judgedAgainst = "b54cf82ed6fc3da94262fcb7ea8eea80b3e8749a"; :>> judgedAt = "2026-09-08"; :>> judgedBy = "claudeOpus5"; }
    }

    verification releaseChecksumsRefineGate : Test { :>> id = "10e2c577-a167-4629-8ece-c55dc78c43f3"; :>> title = "Sprint 611 refine gate (DoR)"; :>> createdAt = "2026-09-08"; :>> createdBy = "claudeOpus5"; :>> method = VerificationMethod::inspect; :>> procedureText = "Scope: .github/workflows/release.yml (hash step per matrix job, checksums job); keel-cli/src/guards.rs (two guards, GUARD_NAMES 65 -> 67, dispatch); keel-cli/src/main.rs WARNING_ONLY_GUARDS; .engine/rules/guard-constraints.sysml; .engine/docs/guards.md; keel-cli/tests/release_checksums_catch_it.rs; .engine/skills/release/SKILL.md and its .claude copy; .engine/processes/deploy.sysml if it enumerates steps; keel-wrapper.toml. Out of scope: keel init fetching checksums from the release page (network in init; a follow-up if the warning proves noisy), and the wrapper's asset list moving out of keelw. Estimate 3 points: a workflow change that cannot run until the next tag, two file-level guards with tests, doc-sync. DoR: points set, charter d0385, scope clear, no blocking dependency, DoD authored."; }
    // RAN: DoR inspected: 3 points, charter d0385, scope in the refine text, DoD authored, no blocking dependency
    part releaseChecksumsRefineGateR1 : TestResult { :>> id = "162ee5d3-55cc-4892-a995-ba7894db488c"; :>> outcome = VerdictKind::pass; :>> judgedAgainst = "b54cf82ed6fc3da94262fcb7ea8eea80b3e8749a"; :>> judgedAt = "2026-09-08"; :>> judgedBy = "claudeOpus5"; }
    verification releaseChecksumsStandupGate : Test { :>> id = "940805e4-5127-43f0-ab6f-e12a8eb00c9f"; :>> title = "Sprint 611 standup gate"; :>> createdAt = "2026-09-08"; :>> createdBy = "claudeOpus5"; :>> method = VerificationMethod::inspect; :>> procedureText = "Plan: (1) release.yml hash step for unix and windows, files list carries the .sha256, checksums job downloads, aggregates, verifies with sha256sum -c and uploads SHA256SUMS; (2) guard release-checksums-published, file-level like gating-workflow-history: a workflow that attaches release assets must hash and publish; (3) guard wrapper-pin-checksummed reading engine-version.toml against keel-wrapper.toml for the three asset names keelw knows; (4) register both (GUARD_NAMES, dispatch, warning-only list, guard-constraints, guards.md); (5) integration test with constructed workflows and pins; (6) keel-wrapper.toml 0.4.1 entries from the assets downloaded 2026-09-08; (7) release skill step 3 text and sync-claude; (8) cargo build, tests, clippy, gates."; }
    // RAN: plan of eight steps recorded in the standup text; all eight executed in this commit
    part releaseChecksumsStandupGateR1 : TestResult { :>> id = "2c46f371-d849-48f0-8285-a65ec027703a"; :>> outcome = VerdictKind::pass; :>> judgedAgainst = "b54cf82ed6fc3da94262fcb7ea8eea80b3e8749a"; :>> judgedAt = "2026-09-08"; :>> judgedBy = "claudeOpus5"; }
    verification releaseChecksumsImplementGate : Test { :>> id = "b3c2fdd3-205d-4f4f-906e-63dd0a630aa8"; :>> title = "Sprint 611 implement gate"; :>> createdAt = "2026-09-08"; :>> createdBy = "claudeOpus5"; :>> method = VerificationMethod::test; :>> procedureText = "RAN: cargo build --release; cargo test --release release_checksums; cargo clippy; keel guard (both new guards present, this tree clean); keel validate .; keel check-engine .; keel sync-claude --check."; }
    // RAN: cargo build --release clean; cargo clippy --release --all-targets -D warnings exit 0; cargo test --release --test release_checksums_catch_it 6 passed 0 failed; keel guard release-checksums-published . PASS 1 scanned 0 violations on the new release.yml; keel guard wrapper-pin-checksummed . WARN naming all three assets before the entries, PASS 0 warnings after; keel validate . 695 clean; keel check-engine . clean; keel guard exit 0; keel version guards: 67; keel sync-claude synced 46/46
    part releaseChecksumsImplementGateR1 : TestResult { :>> id = "817c5fe2-b1b8-4e5e-b296-614418802a35"; :>> outcome = VerdictKind::pass; :>> judgedAgainst = "b54cf82ed6fc3da94262fcb7ea8eea80b3e8749a"; :>> judgedAt = "2026-09-08"; :>> judgedBy = "claudeOpus5"; }
    verification releaseChecksumsReviewGate : Test { :>> id = "97bd3004-eb02-4467-a1db-3be89d762e56"; :>> title = "Sprint 611 review gate — three passes per D0172"; :>> createdAt = "2026-09-08"; :>> createdBy = "claudeOpus5"; :>> method = VerificationMethod::inspect; :>> procedureText = "Reviewed against the DoD: release.yml hashes in the building job and attaches the .sha256; the checksums job verifies before it uploads; the HARD guard fails a workflow without the step and passes release.yml; the WARN guard reports the pre-sprint state (pin 0.4.1, no entries) and is clean after the entries land; the skill names the step; the process enumerates it."; }
    // RAN: reviewed against the DoD: release.yml hashes in the building job (unix and pwsh steps) and lists the .sha256 in files; checksums job downloads, aggregates, sha256sum -c, uploads SHA256SUMS; the HARD guard test reads FAIL on a workflow without the step and on a named-but-uncomputed hash file, clean with it; the WARN guard test reads WARN on the pre-sprint pin/table and clean with entries; release SKILL.md step 3 and anti-patterns, deploy.sysml relTagPublish name the step and the wrapper entry
    part releaseChecksumsReviewGateR1 : TestResult { :>> id = "546b9766-ef59-49c1-824c-8e204c5bab46"; :>> outcome = VerdictKind::pass; :>> judgedAgainst = "b54cf82ed6fc3da94262fcb7ea8eea80b3e8749a"; :>> judgedAt = "2026-09-08"; :>> judgedBy = "claudeOpus5"; }
    verification releaseChecksumsCloseOutGate : Test { :>> id = "732efef8-3bc6-4d50-9901-2dc9a6b1719a"; :>> title = "Sprint 611 closeOut gate (autonomous, D0049)"; :>> createdAt = "2026-09-08"; :>> createdBy = "claudeOpus5"; :>> method = VerificationMethod::inspect; :>> procedureText = "Sprint 611 closes when dcReleaseAssetsCarryChecksumsDoD carries a pass at the commit that carries the workflow, the guards, the entries and the doc-sync, and issue417 and issue418 leave keel show open-issues."; }
    // RAN: DoD pass recorded on storyReleaseChecksumsDoD and dcReleaseAssetsCarryChecksumsDoD at this SHA; issue417 and issue418 resolution read back from keel show open-issues after the record
    part releaseChecksumsCloseOutGateR1 : TestResult { :>> id = "aa2a4a79-447a-4438-a181-d213be1b0576"; :>> outcome = VerdictKind::pass; :>> judgedAgainst = "b54cf82ed6fc3da94262fcb7ea8eea80b3e8749a"; :>> judgedAt = "2026-09-08"; :>> judgedBy = "claudeOpus5"; }
    verification releaseChecksumsRetroGate : Test { :>> id = "7b7100de-19cd-4d69-8e79-60761d66afbd"; :>> title = "Sprint 611 retro gate (autonomous, D0049)"; :>> createdAt = "2026-09-08"; :>> createdBy = "claudeOpus5"; :>> method = VerificationMethod::analyze; :>> procedureText = "Retro held; avoidable-issue scan: no new item - both defects this sprint closes were recorded as issue417 and issue418 at its opening and are already tracked. Process improvement: the release skill now names the wrapper contract, which is where the pin's two-day refusal came from - a step that lived in nobody's text."; }
    // RAN: retro held; avoidable-issue scan over the sprint: none beyond issue417/issue418 recorded at its opening; the retro text stands as written
    part releaseChecksumsRetroGateR1 : TestResult { :>> id = "ddc1451b-4043-4577-881a-5e2272ed0346"; :>> outcome = VerdictKind::pass; :>> judgedAgainst = "b54cf82ed6fc3da94262fcb7ea8eea80b3e8749a"; :>> judgedAt = "2026-09-08"; :>> judgedBy = "claudeOpus5"; }
}
