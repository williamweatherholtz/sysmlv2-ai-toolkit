// ProjectDeliveryS600 — Sprint 600: Rank 3 of D0367: one keel process opens each corpus file once and shares one model, validated by the file's own facts on every read (dcOneCorpusPerProcess, D0370). EXECUTE. 3 pts.
package ProjectDeliveryS600 {
    private import EngineElement::*;
    private import EngineWork::*;
    private import EngineVerification::*;
    private import EngineRelationships::*;

    #CharteredBy dependency from oneCorpusPerProcessStory to d0370;

    part oneCorpusPerProcessStory : Story {
        :>> id = "88b55a91-81dd-4ef9-8fe8-66acb620109d";
        :>> title = "Sprint 600: Rank 3 of D0367: one keel process opens each corpus file once and shares one model, validated by the file's own facts on every read (dcOneCorpusPerProcess, D0370) (3 pts)";
        :>> createdAt = "2026-09-07"; :>> createdBy = "claudeOpus5"; :>> kind = WorkKind::code; :>> priority = WorkPriority::p0; :>> owner = "claudeOpus5"; :>> estimatedPoints = 3;
    }

    action def DeliveryRunS600 {
        action storyOneCorpusPerProcess;
        verification storyOneCorpusPerProcessDoD : Test { :>> id = "1cbf6ae4-40aa-47b7-b6cd-e040779664de"; :>> method = VerificationMethod::test; :>> procedureText = "DELIVERED: new module keel-cli/src/corpus.rs - corpus::read_to_string(path) stats the file on every call and serves the process-cached text only when its (len, mtime) equal what was read and the mtime is at least two seconds old (git's racy rule), a missing file is std::fs::read_to_string's error and never a stale hit; corpus::collect_sysml serves its remembered walk only while every directory it entered still carries the mtime it had and never remembers an absent directory; crate::collect_sysml delegates to it and crate::collect_sysml_uncached is the walk fingerprint::compute reads; Model::build returns Arc<Model> (MODEL_CACHE holds an Arc, cached_model shares it, three signatures in view/mod.rs widened and a ResolvedSection alias named); all 61 std::fs::read_to_string sites in guards.rs and the model's own read go through the corpus; FILE_OPENS, CORPUS_HITS and WALK_HITS counted unconditionally and reported on the KEEL_PERF line. VERIFIED: corpus tests a_second_read_of_an_unchanged_file_does_not_open_it_and_a_rewrite_does (open counter unchanged on the second read of a settled file, raised by a rewrite), a_missing_file_is_an_error_even_after_it_was_cached, a_file_created_after_the_first_walk_is_seen (by collect_sysml_uncached in the same epoch and by the memoized walk via the directory's mtime), an_absent_directory_is_not_remembered pass in cargo test --release; clippy pedantic clean. MEASURED on this tree, shell timer, same binary shape, the f954788 binary against this one: keel guard 8293 / 7176 ms before, 6523 / 4587 / 5562 ms after; KEEL_PERF=1 before `25361 opens (implicit), 39 tree walk(s)`, after `1951 file open(s) (23410 from corpus)`, `21 tree walk(s) (116 from memo)`, parse 1294 ms to 559 ms; stdout identical modulo the lines carrying ms (66 PASS, 0 FAIL both sides, diff empty). keel orient . 2106 / 1847 ms to 1645 / 1554 ms, stdout byte-identical (diff). keel validate . 682 files clean. Resolves the corpus-reopen and clone terms of issue409."; }
        // RAN: cargo test --release -p keel-cli --lib: 407 passed (corpus tests a_second_read_of_an_unchanged_file_does_not_open_it_and_a_rewrite_does, a_missing_file_is_an_error_even_after_it_was_cached, a_file_created_after_the_first_walk_is_seen, an_absent_directory_is_not_remembered); cargo clippy pedantic clean; keel guard 8293/7176 ms -> 6523/4587/5562 ms, 1951 file open(s) (23410 from corpus), stdout identical modulo ms lines (66 PASS 0 FAIL); keel orient . 2106/1847 -> 1645/1554 ms byte-identical; keel validate . 682 clean
        part storyOneCorpusPerProcessDoDR1 : TestResult { :>> id = "86f77c8e-2004-490c-bbda-fdc54261a923"; :>> outcome = VerdictKind::pass; :>> judgedAgainst = "f954788ab41fc61408c77112469143ac634bd5b8"; :>> judgedAt = "2026-09-07T23:32:00-06:00"; :>> judgedBy = "claudeOpus5"; }
    }

    verification oneCorpusPerProcessRefineGate : Test { :>> id = "92731b5c-6bff-495c-a572-c6bcffe334f9"; :>> title = "Sprint 600 refine gate (DoR)"; :>> createdAt = "2026-09-07"; :>> createdBy = "claudeOpus5"; :>> method = VerificationMethod::inspect; :>> procedureText = "READY, 3 pts: one new module, three signatures widened, a mechanical read-path swap across guards.rs, four tests, a measurement - the DoD names the check for each. Chartered by D0370, a #ProspectiveChange because guards.rs is under the keystone lock (D0209 clause 2); it stays proposed for the human's word under D0337, and the work proceeds with the Decision co-committed, which is what the lock asks. The DoD was re-read for the issue372/sprint599 defect before any check ran: every command it names exists (`keel guard`, `keel orient .`, `KEEL_PERF=1`)."; }
    // RAN: cargo clippy --release -p keel-cli --all-targets clean; cargo test --release -p keel-cli --lib 407 passed; keel guard 8293/7176 ms -> 6523/4587/5562 ms, stdout identical modulo ms lines; keel orient 2106/1847 -> 1645/1554 ms byte-identical; keel validate . 682 clean
    part oneCorpusPerProcessRefineGateR1 : TestResult { :>> id = "5d4e9121-ad7f-483c-bea1-1970f6b275fc"; :>> outcome = VerdictKind::pass; :>> judgedAgainst = "f954788ab41fc61408c77112469143ac634bd5b8"; :>> judgedAt = "2026-09-07T23:30:00-06:00"; :>> judgedBy = "claudeOpus5"; }
    verification oneCorpusPerProcessStandupGate : Test { :>> id = "2369845a-d468-46af-bfe6-153c95300a64"; :>> title = "Sprint 600 standup gate"; :>> createdAt = "2026-09-07"; :>> createdBy = "claudeOpus5"; :>> method = VerificationMethod::inspect; :>> procedureText = "TWO CHOICES. First, validity is a fact the file carries - (len, mtime) for content, a directory's mtime for its entries - never a clear() the callers must remember: sprint 598's retro named a memo that was right only because its callers were serial, and a cache that depends on caller discipline is that defect waiting for a concurrent caller. Second, the counters are unconditional: the first cut counted opens behind KEEL_PERF and the DoD's own test failed at 'the first read opens the file' because the count was zero - a test that skips when instrumentation is off is not the receipt the DoD asked for, so the open count is always kept and an atomic add is the price."; }
    // RAN: cargo clippy --release -p keel-cli --all-targets clean; cargo test --release -p keel-cli --lib 407 passed; keel guard 8293/7176 ms -> 6523/4587/5562 ms, stdout identical modulo ms lines; keel orient 2106/1847 -> 1645/1554 ms byte-identical; keel validate . 682 clean
    part oneCorpusPerProcessStandupGateR1 : TestResult { :>> id = "05467277-b315-4ca2-9ed3-a8795d7756fa"; :>> outcome = VerdictKind::pass; :>> judgedAgainst = "f954788ab41fc61408c77112469143ac634bd5b8"; :>> judgedAt = "2026-09-07T23:30:00-06:00"; :>> judgedBy = "claudeOpus5"; }
    verification oneCorpusPerProcessImplementGate : Test { :>> id = "ac9ab13d-4463-4c18-b1e6-a2016bfbe4d2"; :>> title = "Sprint 600 implement gate"; :>> createdAt = "2026-09-07"; :>> createdBy = "claudeOpus5"; :>> method = VerificationMethod::test; :>> procedureText = "RAN: Write tool for corpus.rs; python patch_arc_model.py, fix_clippy_corpus.py, count_unconditionally.py (each replacement refusing unless its anchor occurs once); sed for the lib.rs module line, the fingerprint.rs walk, the five inline `&*Model::build(root)?` sites and the 61 guards.rs reads; cargo clippy --release -p keel-cli --all-targets (clean after five lints: struct_field_names, missing_errors_doc, significant_drop_tightening, duration_suboptimal_units, type_complexity); cargo build --release; cargo test --release -p keel-cli --lib -- corpus fingerprint, then the full lib suite; timed keel guard and keel orient runs from a copy of the binary (keel-serve.exe) against .keel/bin/keel.exe at f954788, diff of stdout; keel validate .; cp to .keel/bin/keel.exe."; }
    // RAN: cargo clippy --release -p keel-cli --all-targets clean; cargo test --release -p keel-cli --lib 407 passed; keel guard 8293/7176 ms -> 6523/4587/5562 ms, stdout identical modulo ms lines; keel orient 2106/1847 -> 1645/1554 ms byte-identical; keel validate . 682 clean
    part oneCorpusPerProcessImplementGateR1 : TestResult { :>> id = "13a73613-8b08-4bf5-a2df-d39d159e156f"; :>> outcome = VerdictKind::pass; :>> judgedAgainst = "f954788ab41fc61408c77112469143ac634bd5b8"; :>> judgedAt = "2026-09-07T23:30:00-06:00"; :>> judgedBy = "claudeOpus5"; }
    verification oneCorpusPerProcessReviewGate : Test { :>> id = "5f47b32a-fab4-4e35-ac87-5f9b96f80134"; :>> title = "Sprint 600 review gate — three passes per D0172"; :>> createdAt = "2026-09-07"; :>> createdBy = "claudeOpus5"; :>> method = VerificationMethod::inspect; :>> procedureText = "THREE QUESTIONS (D0172). Can a cached read be wrong? Only when a file is rewritten to the same length within the same mtime tick as the read that cached it - and that entry is not served for two seconds, so the window is the mtime resolution against a two-second bar, the same bar git's index trusts. Is the output the same? Identical guard verdicts (66 PASS, 0 FAIL, diff empty modulo timing) and byte-identical orient on this tree. What is NOT claimed: that a file opened once per process gains anything (write paths, status and serve stay on std::fs); that the wall time transfers (it is this host's Defender open cost); that git is now cheap - `git x44 in 6.4-9.1 s` under parallel contention is the residual, and it is what dcGateAnswersFromItsReceipt and dcGitReadsStayInProcess judge next."; }
    // RAN: cargo clippy --release -p keel-cli --all-targets clean; cargo test --release -p keel-cli --lib 407 passed; keel guard 8293/7176 ms -> 6523/4587/5562 ms, stdout identical modulo ms lines; keel orient 2106/1847 -> 1645/1554 ms byte-identical; keel validate . 682 clean
    part oneCorpusPerProcessReviewGateR1 : TestResult { :>> id = "da80ba98-b36d-4ce3-b3bf-aef2fd6fda29"; :>> outcome = VerdictKind::pass; :>> judgedAgainst = "f954788ab41fc61408c77112469143ac634bd5b8"; :>> judgedAt = "2026-09-07T23:30:00-06:00"; :>> judgedBy = "claudeOpus5"; }
    verification oneCorpusPerProcessCloseOutGate : Test { :>> id = "c83241be-1dd9-4ad0-843a-f6e034ce356b"; :>> title = "Sprint 600 closeOut gate (autonomous, D0049)"; :>> createdAt = "2026-09-07"; :>> createdBy = "claudeOpus5"; :>> method = VerificationMethod::inspect; :>> procedureText = "CLOSED. keel guard 7.2-8.3 s to 4.6-6.5 s on this tree, 23,410 of 25,361 reads served without an open; keel orient 1.8-2.1 s to 1.55-1.65 s. D0370 recorded as a #ProspectiveChange and awaits the human's word; the sprint's work is co-committed with it as the keystone lock requires. The frontier's next item is dcGateAnswersFromItsReceipt."; }
    // RAN: cargo clippy --release -p keel-cli --all-targets clean; cargo test --release -p keel-cli --lib 407 passed; keel guard 8293/7176 ms -> 6523/4587/5562 ms, stdout identical modulo ms lines; keel orient 2106/1847 -> 1645/1554 ms byte-identical; keel validate . 682 clean
    part oneCorpusPerProcessCloseOutGateR1 : TestResult { :>> id = "31e264ba-8e9e-4674-9480-c38e3f87e171"; :>> outcome = VerdictKind::pass; :>> judgedAgainst = "f954788ab41fc61408c77112469143ac634bd5b8"; :>> judgedAt = "2026-09-07T23:30:00-06:00"; :>> judgedBy = "claudeOpus5"; }
    verification oneCorpusPerProcessRetroGate : Test { :>> id = "026fc93d-f43b-4138-99f2-6760959aa19f"; :>> title = "Sprint 600 retro gate (autonomous, D0049)"; :>> createdAt = "2026-09-07"; :>> createdBy = "claudeOpus5"; :>> method = VerificationMethod::analyze; :>> procedureText = "AVOIDABLE-ISSUE SCAN HELD. One process finding: the first cut's test failed because the counter it read was gated on KEEL_PERF - a receipt that exists only when instrumentation is on is not a receipt, and the fingerprint test already carried the same shape (`if crate::perf::enabled()` around its assertion, fingerprint.rs); no new item - the correction here is the unconditional count, and the existing item dcGateAnswersFromItsReceipt is the receipt discipline this belongs to. One measurement finding kept for rank 4: with the corpus and the commit facts cached, the per-guard git spawns (x44, 6.4-9.1 s under contention) are now most of `keel guard`'s wall time, so the receipt item's before number is this sprint's after."; }
    // RAN: cargo clippy --release -p keel-cli --all-targets clean; cargo test --release -p keel-cli --lib 407 passed; keel guard 8293/7176 ms -> 6523/4587/5562 ms, stdout identical modulo ms lines; keel orient 2106/1847 -> 1645/1554 ms byte-identical; keel validate . 682 clean
    part oneCorpusPerProcessRetroGateR1 : TestResult { :>> id = "5b554e61-cd4a-4726-b067-802c15e92b0b"; :>> outcome = VerdictKind::pass; :>> judgedAgainst = "f954788ab41fc61408c77112469143ac634bd5b8"; :>> judgedAt = "2026-09-07T23:30:00-06:00"; :>> judgedBy = "claudeOpus5"; }
}
