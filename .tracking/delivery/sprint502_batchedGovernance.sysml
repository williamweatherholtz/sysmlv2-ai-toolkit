// ProjectDeliveryS502 — Sprint 502: batch the governance traversal so the antiquated-data question can be asked at all. EXECUTE. 5 pts.
package ProjectDeliveryS502 {
    private import EngineElement::*;
    private import EngineWork::*;
    private import EngineVerification::*;
    private import EngineRelationships::*;

    #CharteredBy dependency from batchedGovernanceStory to d0265;

    part batchedGovernanceStory : Story {
        :>> id = "65c7759c-4646-4265-8709-35108f4cce1f";
        :>> title = "Sprint 502: reprocess-candidates goes from never-finishes to 46 seconds (5 pts)";
        :>> createdAt = "2026-08-30"; :>> createdBy = "claudeOpus5"; :>> kind = WorkKind::code; :>> priority = WorkPriority::p0; :>> owner = "claudeOpus5"; :>> estimatedPoints = 5;
    }

    action def DeliveryRunS502 {
        action storyBatchedGovernance;
        verification storyBatchedGovernanceDoD : Test { :>> id = "882dbac0-09e9-4a54-b5e7-b864e2566390"; :>> method = VerificationMethod::test; :>> procedureText = "Resolves issue316, delivering proposal #1 from the vintage panel at the human's choice (st049). BEFORE, measured twice: reprocess-candidates did not finish - 240 seconds, exit 124, zero bytes - because each item cost a pickaxe search plus a merge-base per process-change Decision; a single item timed at ~15 seconds, so 501 stories is roughly two hours. AFTER: 46 seconds, exit 0, 142KB of answers. DELIVERED: one rev-list builds the child map and a forward-reachability set per marker commit so is_ancestor is a set lookup; one git log -p over .tracking/delivery maps every name to its introducing commit, faithful to the pickaxe it replaces; charter edges are read from the WORKING TREE, and decision-introduction commits and process-def touches come from one log each. VERIFY: batched_governance_agrees.rs 2/2 - the batched path is BYTE-IDENTICAL to the per-item resolver on three corpus items spanning vintages, and the corpus lens exits 0 with a NON-VACUOUS result. Workspace suite 0 FAILED; clippy -D warnings clean.: DELIVERED BACKLOG ITEMS: <items>. <what done means, verified how>."; }
        // RAN: // RAN: reprocess-candidates exit 124 @240s 0 bytes BEFORE, exit 0 @46s 142916 bytes AFTER; batched_governance_agrees 2/2 (byte-identical on 3 vintages + non-vacuous corpus result); workspace suite 0 FAILED; clippy clean
        part storyBatchedGovernanceDoDR1 : TestResult { :>> id = "1071cd35-791f-43b2-9a92-b2a82bdaaa0d"; :>> outcome = VerdictKind::pass; :>> judgedAgainst = "bd0d919"; :>> judgedAt = "2026-08-30"; :>> judgedBy = "claudeOpus5"; }
    }

    verification batchedGovernanceRefineGate : Test { :>> id = "bddddf29-b060-4263-aa89-610b005fac50"; :>> title = "Sprint 502 refine gate (DoR)"; :>> createdAt = "2026-08-30"; :>> createdBy = "claudeOpus5"; :>> method = VerificationMethod::inspect; :>> procedureText = "READY: the panel had already established the derivation is SOUND on four of five lenses and that the defect is purely reachability - pf55 named the fix as a batched traversal and explicitly not a design change. So this sprint's scope was a performance change with an equality obligation, and the DoD was written to make the equality half non-optional."; }
    verification batchedGovernanceStandupGate : Test { :>> id = "d838b9c7-695b-4b67-945f-dbf0a4a0b5d6"; :>> title = "Sprint 502 standup gate"; :>> createdAt = "2026-08-30"; :>> createdBy = "claudeOpus5"; :>> method = VerificationMethod::inspect; :>> procedureText = "No blocker. One judgment recorded: the per-item path STAYS. For a single item the index costs more than the resolve it replaces (a full git log -p over delivery history), so governing-version keeps the old path and only the corpus lens is batched. Two paths that must agree is a real cost, and the equality test is what converts it from a hazard into a controlled one."; }
    verification batchedGovernanceImplementGate : Test { :>> id = "690ed54a-8561-490d-8d2e-29aa776df0d0"; :>> title = "Sprint 502 implement gate"; :>> createdAt = "2026-08-30"; :>> createdBy = "claudeOpus5"; :>> method = VerificationMethod::test; :>> procedureText = "RAN: reprocess-candidates timed before and after on this corpus - exit 124 at 240s with zero bytes, then exit 0 at 46s with 142916 bytes. governing-version on one story timed at 15s, which is the number that makes 501 items impossible. cargo test --test batched_governance_agrees -> 2/2. cargo test --workspace --release -> 0 FAILED. clippy -D warnings clean: two lints fixed at the root - a case-sensitive extension comparison, and a public fn taking a HashSet, resolved by making build_index PRIVATE so the two public entry points are its only callers and the index cannot be built inconsistently from outside."; }
    verification batchedGovernanceReviewGate : Test { :>> id = "83f137ac-a844-492e-bcf1-fd249838236f"; :>> title = "Sprint 502 review gate — three passes per D0172"; :>> createdAt = "2026-08-30"; :>> createdBy = "claudeOpus5"; :>> method = VerificationMethod::inspect; :>> procedureText = "THREE PASSES. (1) IS IT THE SAME ANSWER: asserted byte-for-byte on three items chosen across vintages, because one item could agree by luck and because a fast lens that answers differently is worse than a slow correct one - the speed-up is visible, the divergence is not. (2) IS THE RESULT NON-VACUOUS: the corpus test asserts due_to appears, since this corpus HAS safety-change Decisions and items predating them, so an empty answer would be a mis-aimed lens rather than a clean bill of health - the pass-at-zero hazard that has now been caught three times in this codebase. (3) DID A PERFORMANCE CHANGE SMUGGLE IN A SEMANTIC ONE: no - issue317 (the unconditional Delivery fallback for item types the resolver does not cover) is deliberately NOT fixed here, because batching a resolver does not widen its coverage and conflating the two would hide a semantic change inside a speed-up."; }
    verification batchedGovernanceCloseOutGate : Test { :>> id = "53abd15c-4ecf-47a8-9084-9e7ebb980fcb"; :>> title = "Sprint 502 closeOut gate (autonomous, D0049)"; :>> createdAt = "2026-08-30"; :>> createdBy = "claudeOpus5"; :>> method = VerificationMethod::inspect; :>> procedureText = "CLOSED. The question the human asked - what antiquated data is out there, authored under what process - is answerable on this corpus for the first time. issue316 resolves. issue317 stays open with its own resolver, and the resolver edge for issue316 was RE-POINTED from the nearest-available task to the one that actually did the work."; }
    verification batchedGovernanceRetroGate : Test { :>> id = "617b8e0c-4cc0-479f-bfb2-0be271715cd5"; :>> title = "Sprint 502 retro gate (autonomous, D0049)"; :>> createdAt = "2026-08-30"; :>> createdBy = "claudeOpus5"; :>> method = VerificationMethod::analyze; :>> procedureText = "FINDING, and it is about my own filing: issues 317 and 318 were both recorded against dcNoOpInvarianceControl - a task that would not resolve either - because `record issue` REQUIRES a resolver and no honest one existed yet. That is the exact antipattern I wrote into the github-intake process this week: an issue routed to a resolver that will not resolve it looks handled and is not. Corrected here by authoring dcBatchedGovernanceIndex and re-pointing. THE GENERAL SHAPE is a real tension in the write API - requiring a resolver prevents untriaged issues and simultaneously pressures the filer to attach a false one. BECOMES TRACKED: not a new control, because the requirement is right and the pressure is the cost of it; what is filed instead is the observation, in this gate, that a resolver named at filing time should be re-checked when the work is actually done."; }
}
