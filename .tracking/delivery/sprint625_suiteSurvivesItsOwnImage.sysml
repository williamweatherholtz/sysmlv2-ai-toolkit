// ProjectDeliveryS625 — Sprint 625: keel suite cannot be defeated by the fact that it is itself running (dcSuiteSurvivesItsOwnImage, issue386). EXECUTE. 2 pts.
package ProjectDeliveryS625 {
    private import EngineElement::*;
    private import EngineWork::*;
    private import EngineVerification::*;
    private import EngineRelationships::*;

    #CharteredBy dependency from suiteSurvivesItsOwnImageStory to d0356;

    part suiteSurvivesItsOwnImageStory : Story {
        :>> id = "8a36663f-a828-4a75-b009-626f86c65b3b";
        :>> title = "Sprint 625: keel suite cannot be defeated by the fact that it is itself running (dcSuiteSurvivesItsOwnImage, issue386) (2 pts)";
        :>> createdAt = "2026-09-09"; :>> createdBy = "claudeOpus5"; :>> kind = WorkKind::code; :>> priority = WorkPriority::p0; :>> owner = "claudeOpus5"; :>> estimatedPoints = 2;
    }

    action def DeliveryRunS625 {
        action storySuiteSurvivesItsOwnImage;
        verification storySuiteSurvivesItsOwnImageDoD : Test { :>> id = "6bac033d-3cb4-4c63-879b-eb6e8ffd5e6d"; :>> method = VerificationMethod::test; :>> procedureText = "DELIVERED: suite.rs refuses, before the running stub, when the executing image is the file cargo relinks - `<target>/release/keel(.exe)` or anything under `<target>/release/deps/` (`image_collides`, pure; narrow enough that the documented `keel-serve.exe` copy in the same directory does not collide) - exit 2, the copy-and-rerun remedy named, no receipt touched; and a cargo exit with no `test result:` line (`never_ran`, pure) restores the previous receipt instead of recording `fail - 0 passed, 0 failed`. VERIFIED: unit test the_suite_knows_its_own_image_and_a_run_that_never_ran covers both predicates on any host; live, `target/release/keel.exe suite .` on a tree whose sources changed exited 2 with the receipt's md5 unchanged (3cc53f64) and no new log; `keel-serve.exe suite . -- --no-such-cargo-flag` exited 2 with the receipt restored byte-for-byte and the log written. Docs: CLAUDE.md section 6 and the suite synopsis in both fact homes (commands.sysml, cli_facts.rs) - the latter caught by guard cli-surface-declared when only one was edited."; }
        // RAN: unit test the_suite_knows_its_own_image_and_a_run_that_never_ran passes in the 430; live: keel.exe suite . exit 2 receipt md5 3cc53f64 unchanged; keel-serve.exe suite . -- --no-such-cargo-flag exit 2 receipt restored byte-identical
        part storySuiteSurvivesItsOwnImageDoDR1 : TestResult { :>> id = "2697490e-647d-4baa-bb28-2d66ae7ef6de"; :>> outcome = VerdictKind::pass; :>> judgedAgainst = "9a5ae60"; :>> judgedAt = "2026-09-09"; :>> judgedBy = "claudeOpus5"; }
    }

    verification suiteSurvivesItsOwnImageRefineGate : Test { :>> id = "c025b047-8d1f-43ff-b041-524fe04c3ab1"; :>> title = "Sprint 625 refine gate (DoR)"; :>> createdAt = "2026-09-09"; :>> createdBy = "claudeOpus5"; :>> method = VerificationMethod::inspect; :>> procedureText = "READY. Head of keel whats-next after sprint 624. The DoD offers two shapes - run from a copy, or refuse naming the cause - and only the refusal is honest here: a process cannot outlive its own image to let cargo relink it, so a re-exec would inherit the same lock. 2 points: one module, two pure predicates, a live check on the host that has the lock."; }
    // RAN: keel whats-next . at 9a5ae60: dcSuiteSurvivesItsOwnImage at the head; 2 points; DoD read
    part suiteSurvivesItsOwnImageRefineGateR1 : TestResult { :>> id = "7eef0174-94ba-4dae-86b8-d19d5b13695c"; :>> outcome = VerdictKind::pass; :>> judgedAgainst = "9a5ae60"; :>> judgedAt = "2026-09-09"; :>> judgedBy = "claudeOpus5"; }
    verification suiteSurvivesItsOwnImageStandupGate : Test { :>> id = "5525c4b6-4ee9-433e-aecb-724701f05675"; :>> title = "Sprint 625 standup gate"; :>> createdAt = "2026-09-09"; :>> createdBy = "claudeOpus5"; :>> method = VerificationMethod::inspect; :>> procedureText = "Blockers: none. The synopsis lives in two places (the SysML fact and the Rust fact table) and the guard holds them equal; the edit was made in one and the guard named the other."; }
    // RAN: blockers none; synopsis dual-home noted (commands.sysml + cli_facts.rs)
    part suiteSurvivesItsOwnImageStandupGateR1 : TestResult { :>> id = "50e53785-210e-4591-89e3-00671efa953b"; :>> outcome = VerdictKind::pass; :>> judgedAgainst = "9a5ae60"; :>> judgedAt = "2026-09-09"; :>> judgedBy = "claudeOpus5"; }
    verification suiteSurvivesItsOwnImageImplementGate : Test { :>> id = "a441690d-c599-440a-b1ae-649f6538a9b0"; :>> title = "Sprint 625 implement gate"; :>> createdAt = "2026-09-09"; :>> createdBy = "claudeOpus5"; :>> method = VerificationMethod::test; :>> procedureText = "target_dir, image_collides, own_image_refusal, never_ran in suite.rs; the previous receipt is read before the stub and restored on a run that never reached a test; module doc gains the what-was-measured paragraph. Release build, clippy -D warnings and the keel-cli lib tests (430) exit 0."; }
    // RAN: cargo build --release exit 0; cargo clippy --release -p keel-cli -- -D warnings exit 0; cargo test --release -p keel-cli --lib: 430 passed 0 failed
    part suiteSurvivesItsOwnImageImplementGateR1 : TestResult { :>> id = "35e62b22-ea3e-4f23-a597-353c3f316b44"; :>> outcome = VerdictKind::pass; :>> judgedAgainst = "9a5ae60"; :>> judgedAt = "2026-09-09"; :>> judgedBy = "claudeOpus5"; }
    verification suiteSurvivesItsOwnImageReviewGate : Test { :>> id = "3920f0de-c976-401b-bba4-cc809b0de60c"; :>> title = "Sprint 625 review gate — three passes per D0172"; :>> createdAt = "2026-09-09"; :>> createdBy = "claudeOpus5"; :>> method = VerificationMethod::inspect; :>> procedureText = "Pass 1 (intent): the DoD's live case was run as written - from target/release/keel.exe on a changed tree - and the receipt was compared by md5 before and after. Pass 2 (defects): the refusal is gated on cfg!(windows) because elsewhere the build replaces a running file without harm, and the predicate is deliberately narrower than 'inside the target directory' so the remedy itself is not refused. Pass 3 (docs): the stale D0353 synopsis (the gate D0356 withdrew) was corrected in passing, in both homes."; }
    // RAN: target/release/keel.exe suite . -> exit 2 refusal, receipt md5 3cc53f648e6852caeb8994641e834a3d unchanged, no new log; keel-serve.exe suite . -- --no-such-cargo-flag -> exit 2 cargo exited 1 before any test ran, receipt restored same md5, log suite-1788966739.log written
    part suiteSurvivesItsOwnImageReviewGateR1 : TestResult { :>> id = "7829472c-570c-41d9-afb4-b1e4cac829d2"; :>> outcome = VerdictKind::pass; :>> judgedAgainst = "9a5ae60"; :>> judgedAt = "2026-09-09"; :>> judgedBy = "claudeOpus5"; }
    verification suiteSurvivesItsOwnImageCloseOutGate : Test { :>> id = "587380ba-9482-4e73-b617-804b2f30330d"; :>> title = "Sprint 625 closeOut gate (autonomous, D0049)"; :>> createdAt = "2026-09-09"; :>> createdBy = "claudeOpus5"; :>> method = VerificationMethod::inspect; :>> procedureText = "Two verdict-shaped non-verdicts now say what they are: a refused launch and a build that never reached a test, neither writing a receipt over a tree the tests did not see."; }
    // RAN: keel-serve.exe guard . --no-receipt exit 0; validate . 710 clean; check-engine . clean
    part suiteSurvivesItsOwnImageCloseOutGateR1 : TestResult { :>> id = "51b1f843-3734-4837-851c-9f63ed89b87f"; :>> outcome = VerdictKind::pass; :>> judgedAgainst = "9a5ae60"; :>> judgedAt = "2026-09-09"; :>> judgedBy = "claudeOpus5"; }
    verification suiteSurvivesItsOwnImageRetroGate : Test { :>> id = "f8afb35e-4bb5-4a35-a99d-8260a7ed83b8"; :>> title = "Sprint 625 retro gate (autonomous, D0049)"; :>> createdAt = "2026-09-09"; :>> createdBy = "claudeOpus5"; :>> method = VerificationMethod::analyze; :>> procedureText = "Retro held; avoidable-issue scan: the suite synopsis still described the D0353 gate three days after D0356 withdrew it, in both the SysML fact and the Rust table, and no guard compares a synopsis against the Decisions it cites. Tracked as issue423, resolved by backlog task dcSynopsisCitesLiveDecisions: guard cli-surface-declared (or a sibling) fails a synopsis citing a retired or absent Decision, probed against the D0353 fixture and the corrected cliSuite line. The first attempt to close this sprint said 'no new item' and guard retro-backlog refused it - the control worked."; }
    // RAN: retro held; avoidable-issue scan: stale D0353 synopsis in both fact homes with no control comparing a synopsis to the Decisions it cites -> issue423 resolved by dcSynopsisCitesLiveDecisions (added this commit); first close attempt said no new item and guard retro-backlog refused it
    part suiteSurvivesItsOwnImageRetroGateR1 : TestResult { :>> id = "b7f5e92a-4706-4657-8bcb-dbefcdd5e4cf"; :>> outcome = VerdictKind::pass; :>> judgedAgainst = "9a5ae60"; :>> judgedAt = "2026-09-09"; :>> judgedBy = "claudeOpus5"; }
}
