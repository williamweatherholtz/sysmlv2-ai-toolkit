// ProjectDeliveryS565 — Sprint 565: recall follows the edges of the record the words named - parity with grep-plus-one-hop on the 50-case set, and an honest FAIL on the hand set. EXECUTE. 3 pts.
package ProjectDeliveryS565 {
    private import EngineElement::*;
    private import EngineWork::*;
    private import EngineVerification::*;
    private import EngineRelationships::*;

    #CharteredBy dependency from recallInheritsStory to d0325;

    part recallInheritsStory : Story {
        :>> id = "d9fd72ce-eb91-40a4-9076-574ae1ec11cd";
        :>> title = "Sprint 565: recall follows the edges of the record the words named - parity with grep-plus-one-hop on the 50-case set, and an honest FAIL on the hand set (3 pts)";
        :>> createdAt = "2026-09-05"; :>> createdBy = "claudeOpus5"; :>> kind = WorkKind::code; :>> priority = WorkPriority::p0; :>> owner = "claudeOpus5"; :>> estimatedPoints = 3;
    }

    action def DeliveryRunS565 {
        action storyRecallInherits;
        verification storyRecallInheritsDoD : Test { :>> id = "bd5a2228-1512-4454-b434-3577a9f327ee"; :>> method = VerificationMethod::test; :>> procedureText = "DELIVERED BACKLOG ITEMS: none marked done. recallRanksLinkedRecordsAsWellAsGrepDoes carries a FAIL result: 48/50 in a mean 13 rows (parity with the control on both measures, the DoD's first clause met) but the hand set reads 5/8 against the required 7/8. LANDED under D0325: neighbours of the top three seeds inherit the seed's rank-decayed score (INHERIT_SEEDS 3, INHERIT_DECAY 0.7); payloads cap at 13 rows and say so; recall_bench.py prints where the source landed per case; both harnesses pass KEEL_RECALL_* knobs through for future experiments."; }
        // RAN: cargo test --release 522/0 exit 0; the sprint's deliverable (D0325 landed, FAIL recorded on the item) is complete as stated
        part storyRecallInheritsDoDR1 : TestResult { :>> id = "6f3ee8df-5c7b-4e32-bf7d-17ec17dfc5e9"; :>> outcome = VerdictKind::pass; :>> judgedAgainst = "24782908c03af0c4d18a695d70304c0946be3228"; :>> judgedAt = "2026-09-05"; :>> judgedBy = "claudeOpus5"; }
    }

    verification recallInheritsRefineGate : Test { :>> id = "56067a6e-6a50-4bed-9c4c-ae50c2aa8379"; :>> title = "Sprint 565 refine gate (DoR)"; :>> createdAt = "2026-09-05"; :>> createdBy = "claudeOpus5"; :>> method = VerificationMethod::inspect; :>> procedureText = "READY: the DoD fixed the method - choose on the 50-case set, read the hand set afterwards, never fit - and the diagnostic made the failure legible in one run: the source was shown at position 1-3 in all thirteen misses, so the ranker found the record and failed to follow its edges."; }
    verification recallInheritsStandupGate : Test { :>> id = "a68ae1fa-ce90-49e7-8d73-8261f6e15627"; :>> title = "Sprint 565 standup gate"; :>> createdAt = "2026-09-05"; :>> createdBy = "claudeOpus5"; :>> method = VerificationMethod::inspect; :>> procedureText = "THE DOD'S TWO CLAUSES DID NOT MEET UNDER ANY MEASURED MECHANISM: every configuration that reached 48/50 on the linked-record set left the hand set at 5-6/8, and the one that reached 7/8 (a general second hop at 2.0) took the 50-case set to 45/50. Chosen on the 50-case set as the DoD demands; the hand-set clause fails and the result says so."; }
    verification recallInheritsImplementGate : Test { :>> id = "d8284e72-0e08-4233-a888-7488688f2d1f"; :>> title = "Sprint 565 implement gate"; :>> createdAt = "2026-09-05"; :>> createdBy = "claudeOpus5"; :>> method = VerificationMethod::test; :>> procedureText = "RAN: recall_bench.py grid - dominance 1.5/2/3 (39-40/50), inherit top-1/2/3/5 (44/48/49/49 of 50), decay 0.7 vs 1.0 (equal hits), second hop general 0.5/1.0/2.0 (48/48/45), second hop along chosen seeds 0.3/0.5/0.8 (48/48/46), row cap 13 (48/50, median position 2, 38/48 top-3); recall_ab.py read afterwards: 5/8 (d0129 x2, d0176 unreached). The first grid ran against a binary without the knobs - a denied heredoc had skipped the edit - and reported identical rows for every configuration, which is how the miss was caught; the grid was rerun on the rebuilt binary. clippy -D warnings clean; the full suite in the background to completion."; }
    verification recallInheritsReviewGate : Test { :>> id = "6e08322f-ccdb-4545-82e5-e804f0c239de"; :>> title = "Sprint 565 review gate — three passes per D0172"; :>> createdAt = "2026-09-05"; :>> createdBy = "claudeOpus5"; :>> method = VerificationMethod::inspect; :>> procedureText = "THREE PASSES. (1) WAS THE HAND SET FITTED: no - the hand set was read only after each 50-set choice, and the configuration that would have passed it was rejected on the 50-set. (2) IS 13 ROWS A LOSS ELSEWHERE: median position is 2 and 38 of 48 hits sit in the top three; the cap states itself in the payload. (3) IS THE FAIL HONEST: the DoD result carries both numbers and the item stays ready."; }
    verification recallInheritsCloseOutGate : Test { :>> id = "0896f438-fe7b-4ed4-b534-4ff203319fd8"; :>> title = "Sprint 565 closeOut gate (autonomous, D0049)"; :>> createdAt = "2026-09-05"; :>> createdBy = "claudeOpus5"; :>> method = VerificationMethod::inspect; :>> procedureText = "CLOSED with a FAIL result recorded on the item; D0325 accepted under standing consent; issue367 stays open."; }
    verification recallInheritsRetroGate : Test { :>> id = "1be0297d-ce8a-4d20-b9f5-0f7b37879c25"; :>> title = "Sprint 565 retro gate (autonomous, D0049)"; :>> createdAt = "2026-09-05"; :>> createdBy = "claudeOpus5"; :>> method = VerificationMethod::analyze; :>> procedureText = "no new item - already tracked: recallRanksLinkedRecordsAsWellAsGrepDoes stays on the frontier for a mechanism that reaches two hops without costing the linked-record set (the d0129 shape: a question whose answer is two edges from every word it uses); the 2-hop measurements in d0325 are the starting point. The lesson: when a grid shows no difference between configurations, suspect the knobs never reached the binary before suspecting the mechanism."; }
}
