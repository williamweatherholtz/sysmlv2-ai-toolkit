// ProjectDeliveryS284 — Sprint 284: surface the ONE human gate — decisions awaiting acceptance
// (dcPendingAcceptanceSurface, issue096). EXECUTE. 3 pts.
package ProjectDeliveryS284 {
    private import EngineElement::*;
    private import EngineWork::*;
    private import EngineVerification::*;
    private import EngineRelationships::*;

    #CharteredBy dependency from pendingAcceptanceStory to d0144;

    part pendingAcceptanceStory : Story {
        :>> id = "0d80016c-0814-616c-9b3e-00000030016c";
        :>> title = "Sprint 284: pending acceptances are computed and stated, empty included (3 pts)";
        :>> createdAt = "2026-08-15"; :>> createdBy = "claudeOpus5"; :>> kind = WorkKind::code; :>> priority = WorkPriority::p0; :>> owner = "claudeOpus5"; :>> estimatedPoints = 3;
    }

    action def DeliveryRunS284 {
        action storyPendingAcceptance;
        verification storyPendingAcceptanceDoD : Test { :>> id = "0d80016d-0814-616d-9b3e-00000030016d"; :>> method = VerificationMethod::demo; :>> procedureText = "Delivers dcPendingAcceptanceSurface; resolves issue096. Acceptance is the SINGLE human gate in an otherwise autonomous loop (D0049), and the console's Decisions surface was wired to the `keel decisions` SCORECARD, which filters to accepted — so an oversight surface rendered everything EXCEPT what needs action, and failed silently, since nothing anywhere stated that a decision was waiting. DELIVERED: `view::pending_acceptances` computes proposed Decisions from the model; `keel orient` emits `pendingAcceptances` ALWAYS, empty included; the `orient --html` dashboard gains an 'Awaiting your acceptance' card, toned `bad` rather than `warn` when non-empty because this BLOCKS the loop rather than merely ageing. The scorecard is untouched: accepted-only is correct for what it does, since scoring citations and critique coverage is meaningful only for a committed decision, so this asks the same authored facts a different question rather than widening a view that is right as it stands. VERIFIED LIVE by temporarily proposing two accepted decisions: orient reported exactly ['d0143','d0144'] by name; the scorecard moved 139 -> 137, confirming it filters out precisely what needs action; accepting d0143 back with NO other edit left ['d0144']; restoring both returned `pendingAcceptances: []` with the field still present and the scorecard back to 139; `git diff --stat .engine/decisions/` came back EMPTY, so the two attested Decision records are byte-identical to before the test. Unit test covers proposed-only selection (rejected and superseded are settled, not waiting) and that a non-Decision carrying the same attribute does not leak in. clippy clean; 173 tests; validate 306 clean; 29 guards green."; }
        part storyPendingAcceptanceDoDR1 : TestResult { :>> id = "0d80016e-0814-616e-9b3e-00000030016e"; :>> outcome = VerdictKind::pass; :>> judgedAgainst = "4ba45c8"; :>> judgedAt = "2026-08-15"; :>> judgedBy = "claudeOpus5"; }
    }

    verification paRefineGate : Test { :>> id = "0d80016f-0814-616f-9b3e-00000030016f"; :>> title = "Sprint 284 refine gate (DoR)"; :>> createdAt = "2026-08-15"; :>> createdBy = "claudeOpus5"; :>> method = VerificationMethod::inspect; :>> procedureText = "DoR. CONSUMER CHECK (dorConsumer, D0144): two consumers, `keel orient` (JSON, read by me every session) and the HTML dashboard (read by the human). Checking them first settled the source — both already build the Model, so reading proposed status from it costs nothing, whereas sourcing from the scorecard would have meant widening a view whose accepted-only scope is correct. It also settled that the field must be emitted when EMPTY: orient's JSON is consumed programmatically, and a key that vanishes on zero is indistinguishable from one nobody computed. estimatedPoints=3. DoR met."; }
    part paRefineGateR1 : TestResult { :>> id = "0d800170-0814-6170-9b3e-000000300170"; :>> outcome = VerdictKind::pass; :>> judgedAgainst = "4ba45c8"; :>> judgedAt = "2026-08-15"; :>> judgedBy = "claudeOpus5"; }

    verification paStandupGate : Test { :>> id = "0d800171-0814-6171-9b3e-000000300171"; :>> title = "Sprint 284 standup gate"; :>> createdAt = "2026-08-15"; :>> createdBy = "claudeOpus5"; :>> method = VerificationMethod::inspect; :>> procedureText = "Approach: the repo currently has ZERO proposed decisions, so the interesting case cannot be observed by just running the tool. Test it by temporarily proposing two accepted decisions, exercising every VERIFY condition against the live binary, then restoring and PROVING the restore with `git diff --stat` — those two records carry human attestations and must come back byte-identical, not approximately. No blockers."; }
    part paStandupGateR1 : TestResult { :>> id = "0d800172-0814-6172-9b3e-000000300172"; :>> outcome = VerdictKind::pass; :>> judgedAgainst = "4ba45c8"; :>> judgedAt = "2026-08-15"; :>> judgedBy = "claudeOpus5"; }

    verification paImplementGate : Test { :>> id = "0d800173-0814-6173-9b3e-000000300173"; :>> title = "Sprint 284 implement gate"; :>> createdAt = "2026-08-15"; :>> createdBy = "claudeOpus5"; :>> method = VerificationMethod::test; :>> procedureText = "Two judgement calls worth stating. FIRST, the error default is the OPPOSITE of `superseded_names`': that one is conservative on error so a model-read failure cannot silently restore everything to ready, whereas here a clean empty list on failure would BE the silent failure issue096 is about — so a read failure surfaces as a named sentinel string the human will notice, not as a reassuring zero. SECOND, the status match is on the suffix `::proposed`: matching the bare word would also catch a hypothetical `counterproposed`, and matching the full enum path would silently stop working if the enum were renamed. Both encoded in the test rather than in a comment alone."; }
    part paImplementGateR1 : TestResult { :>> id = "0d800174-0814-6174-9b3e-000000300174"; :>> outcome = VerdictKind::pass; :>> judgedAgainst = "4ba45c8"; :>> judgedAt = "2026-08-15"; :>> judgedBy = "claudeOpus5"; }

    verification paReviewGate : Test { :>> id = "0d800175-0814-6175-9b3e-000000300175"; :>> title = "Sprint 284 review gate"; :>> createdAt = "2026-08-15"; :>> createdBy = "claudeOpus5"; :>> method = VerificationMethod::inspect; :>> procedureText = "Reviewed. The live test is the part that matters: with zero proposed decisions in the repo, a unit test alone would have proved the predicate and nothing about whether orient, the dashboard and the scorecard actually behave differently when something IS waiting. Temporarily proposing two real decisions exercised all four VERIFY conditions end to end, and the 139 -> 137 scorecard movement is direct evidence for issue096's central claim rather than a restatement of it. LIMITATION: `keel serve`'s Decisions API still returns the scorecard, so the pending list reaches the console through the orient dashboard rather than through that surface. That is the correct split — the scorecard should stay accepted-only — but a reader looking specifically at the Decisions page will not see pending there."; }
    part paReviewGateR1 : TestResult { :>> id = "0d800176-0814-6176-9b3e-000000300176"; :>> outcome = VerdictKind::pass; :>> judgedAgainst = "4ba45c8"; :>> judgedAt = "2026-08-15"; :>> judgedBy = "claudeOpus5"; }

    verification paCloseOutGate : Test { :>> id = "0d800177-0814-6177-9b3e-000000300177"; :>> title = "Sprint 284 closeOut gate (autonomous, D0049)"; :>> createdAt = "2026-08-15"; :>> createdBy = "claudeOpus5"; :>> method = VerificationMethod::inspect; :>> procedureText = "Autonomous closeOut (D0049). dcPendingAcceptanceSurface carries a passing DoD TestResult; issue096 resolves. All four VERIFY conditions demonstrated against the live binary, and the two attested Decision files proven byte-identical after the test. clippy clean; 173 tests; validate 306 clean; check-engine clean; 29 guards green. No gate bypassed."; }
    part paCloseOutGateR1 : TestResult { :>> id = "0d800178-0814-6178-9b3e-000000300178"; :>> outcome = VerdictKind::pass; :>> judgedAgainst = "4ba45c8"; :>> judgedAt = "2026-08-15"; :>> judgedBy = "claudeOpus5"; }

    verification paRetroGate : Test { :>> id = "0d800179-0814-6179-9b3e-000000300179"; :>> title = "Sprint 284 retro gate (autonomous, D0049)"; :>> createdAt = "2026-08-15"; :>> createdBy = "claudeOpus5"; :>> method = VerificationMethod::analyze; :>> procedureText = "Autonomous retro (D0049) under D0131's retroTrack. WELL: (1) the zero-state was treated as a testing PROBLEM rather than a reason to ship on a unit test — temporarily proposing two real decisions is what turned every VERIFY line into an observation; (2) the restore was PROVEN with `git diff --stat` rather than assumed, on files carrying human attestations, which is the standing rule about not co-mingling my writes with theirs applied to a test rather than to a commit; (3) the error default was chosen against the precedent in the same module and the reason recorded, because copying `superseded_names`' conservatism here would have produced exactly the silent zero this sprint exists to remove. NO AVOIDABLE ISSUE this sprint: the scope was small, the DoD's VERIFY list was already precise, and nothing had to be rewritten. Recording that plainly rather than manufacturing a finding — a retro that always finds something is as uninformative as one that never does. Estimate 3 pts, delivered."; }
    part paRetroGateR1 : TestResult { :>> id = "0d80017a-0814-617a-9b3e-00000030017a"; :>> outcome = VerdictKind::pass; :>> judgedAgainst = "4ba45c8"; :>> judgedAt = "2026-08-15"; :>> judgedBy = "claudeOpus5"; }
}
