// ProjectDeliveryS472 - Sprint 472: the workspace gate. Discovery asks git, the hook belongs to the repository, and a fresh workspace is armed at init. EXECUTE. 8 pts.
package ProjectDeliveryS472 {
    private import EngineElement::*;
    private import EngineWork::*;
    private import EngineVerification::*;
    private import EngineRelationships::*;

    #CharteredBy dependency from workspaceGateStory to d0238;

    part workspaceGateStory : Story {
        :>> id = "38906639-3e6a-49ae-a9e4-2f8a62a2f6e4";
        :>> title = "Sprint 472: two of the workspace Criticals - discovery that cannot miss a project, and a fresh workspace that is actually gated (8 pts)";
        :>> createdAt = "2026-08-27"; :>> createdBy = "claudeOpus5"; :>> kind = WorkKind::code; :>> priority = WorkPriority::p0; :>> owner = "claudeOpus5"; :>> estimatedPoints = 8;
    }

    action def DeliveryRunS472 {
        action storyWorkspaceGate;
        verification storyWorkspaceGateDoD : Test { :>> id = "081ea2c4-930b-4998-975a-0cba4442ffa1"; :>> method = VerificationMethod::test; :>> procedureText = "DELIVERED: dcWorkspaceDiscoveryIsComplete (issue275), dcWorkspaceIsWireable (issue278) and dcOwnerOfMatchesOnWindows, under D0238. Discovery derives the project set from git ls-files instead of a depth-3 walk that returned at the first project, so nested and deep projects are found; init REFUSES a target inside an existing project; the pre-commit hook is written at the git repository ROOT with core.hooksPath armed at init time; the hook body is one unconditional keel gate --workspace call, replacing a branch that tested [ ! -d .engine ] and therefore gated only the root project in a repo whose root is itself a project; workspace::canon is the single path normaliser; and the advice string names a command that gates instead of keel hook pre-commit, which is not a hook event."; }
    // RAN: cargo test --release => 11 suites, 0 failures (279 lib + init_smoke 2 + the new discovery_finds_nested_and_deep_projects) | discovery: a real git repo with a ROOT project, a NESTED project, and one at depth 4 - all three found, is_multi true, and the nested project owns its own files | gate escape CLOSED end to end in C:/kt/w4: git init + keel init alpha + keel init beta wrote the hook at the REPO ROOT and armed core.hooksPath ('.githooks'), the clean commit passed gating BOTH projects, then a broken file in beta BLOCKED the commit exit 1 naming beta - the identical reproduction exited 0 with the gate clean before this | init nesting: keel init sub inside a project REFUSES exit 2 naming the host and, when the host is the repo root, the two remedies; a relative non-existent target used to print an empty host and test the process cwd, fixed and re-verified | keel projects: 'you are here' marker prints and current:true, previously false in all nine repos | nine real keel repos swept: exactly one project each, no nested false positives - non-vacuous now that discovery descends.
        part storyWorkspaceGateDoDR1 : TestResult { :>> id = "4ebf986c-0fe4-4675-8c09-fa320ab632bb"; :>> outcome = VerdictKind::pass; :>> judgedAgainst = "e7d2683"; :>> judgedAt = "2026-08-27"; :>> judgedBy = "claudeOpus5"; }
    }

    verification workspaceGateRefineGate : Test { :>> id = "273ace07-ed20-4d1e-b724-66712d2f9771"; :>> title = "Sprint 472 refine gate (DoR)"; :>> createdAt = "2026-08-27"; :>> createdBy = "claudeOpus5"; :>> method = VerificationMethod::inspect; :>> procedureText = "DoR: after sprint 471 the frontier ranked the four workspace Criticals at the top, and 275 and 278 are coupled - 275's DoD requires that the escape COMMIT be blocked, which cannot happen while no hook is wired, which is 278. Taken together for that reason. Both reproduced first: the nested project invisible to discovery, and a two-peer workspace with no hooksPath, no root hook, and no .git/hooks/pre-commit. Resolvers: dcWorkspaceDiscoveryIsComplete, dcWorkspaceIsWireable, dcOwnerOfMatchesOnWindows. estimatedPoints=8. #CharteredBy d0238."; }
    part workspaceGateRefineGateR1 : TestResult { :>> id = "32d7b627-ce63-4d0d-a590-02198d2e239d"; :>> outcome = VerdictKind::pass; :>> judgedAgainst = "e7d2683"; :>> judgedAt = "2026-08-27"; :>> judgedBy = "claudeOpus5"; }
    verification workspaceGateStandupGate : Test { :>> id = "7885f1a6-ad24-48f2-a653-a8e3cc2adb17"; :>> title = "Sprint 472 standup gate"; :>> createdAt = "2026-08-27"; :>> createdBy = "claudeOpus5"; :>> method = VerificationMethod::inspect; :>> procedureText = "Approach: ask git rather than deepen the walk, because git's answer is exactly the set a push can carry - a project git does not know about is out of scope by definition rather than by accident. Install the hook at the repo root and arm hooksPath there, never overwriting an existing hook (D0108: a non-owner may add, never overwrite in place, and in a workspace that file is shared). Make the hook body unconditional rather than fixing its branch, since the branch was a second answer to a question gate --workspace already answers. This is an ENFORCEMENT SURFACE change, so it rides a co-committed #SafetyChange Decision (D0238)."; }
    part workspaceGateStandupGateR1 : TestResult { :>> id = "c0a53aa9-535c-4ffc-a0c8-e1f0ed82713b"; :>> outcome = VerdictKind::pass; :>> judgedAgainst = "e7d2683"; :>> judgedAt = "2026-08-27"; :>> judgedBy = "claudeOpus5"; }
    verification workspaceGateImplementGate : Test { :>> id = "c0639df4-65ea-4e8e-ac02-c333c58aa708"; :>> title = "Sprint 472 implement gate"; :>> createdAt = "2026-08-27"; :>> createdBy = "claudeOpus5"; :>> method = VerificationMethod::test; :>> procedureText = "Implemented and verified end to end against real git repos rather than fixtures, because the whole fix is what git reports. Three defects were found DURING the work by the checks themselves rather than by looking for them: the new discovery test failed on owner_of, which turned out to be dcOwnerOfMatchesOnWindows in a second form (git resolves the 8.3 short name that env::temp_dir hands back, so two spellings of one directory never matched); the refusal message printed an EMPTY host path for a relative non-existent target - init's normal case - because canonicalize fails on it so the parent was the empty path and is_project(\"\") silently tested the process cwd; and the init smoke test caught the hook body change, which is the control doing its job one sprint after it was built."; }
    // RAN: cargo test --release => 11 suites, 0 failures (279 lib + init_smoke 2 + the new discovery_finds_nested_and_deep_projects) | discovery: a real git repo with a ROOT project, a NESTED project, and one at depth 4 - all three found, is_multi true, and the nested project owns its own files | gate escape CLOSED end to end in C:/kt/w4: git init + keel init alpha + keel init beta wrote the hook at the REPO ROOT and armed core.hooksPath ('.githooks'), the clean commit passed gating BOTH projects, then a broken file in beta BLOCKED the commit exit 1 naming beta - the identical reproduction exited 0 with the gate clean before this | init nesting: keel init sub inside a project REFUSES exit 2 naming the host and, when the host is the repo root, the two remedies; a relative non-existent target used to print an empty host and test the process cwd, fixed and re-verified | keel projects: 'you are here' marker prints and current:true, previously false in all nine repos | nine real keel repos swept: exactly one project each, no nested false positives - non-vacuous now that discovery descends.
    part workspaceGateImplementGateR1 : TestResult { :>> id = "2f259dd1-fefc-4a84-851e-e9ed40e6978a"; :>> outcome = VerdictKind::pass; :>> judgedAgainst = "e7d2683"; :>> judgedAt = "2026-08-27"; :>> judgedBy = "claudeOpus5"; }
    verification workspaceGateReviewGate : Test { :>> id = "ceefcd0c-eff2-4400-8ffe-10a5372cbc07"; :>> title = "Sprint 472 review gate"; :>> createdAt = "2026-08-27"; :>> createdBy = "claudeOpus5"; :>> method = VerificationMethod::inspect; :>> procedureText = "Diff reviewed. The narrowing is stated rather than buried: a repo whose root is already a project can no longer gain a peer, which is deliberate - a workspace is projects in subdirectories with none at the root - and the refusal names the two remedies instead of leaving the author at a cliff. Two stale claims corrected in the same commit: the module doc's \"both real repositories ... no nested false positives\", which undercounted by seven and was vacuous because the short-circuit meant no subdirectory was ever examined, and the init narration that read git init && git config core.hooksPath after a cd into the project - followed literally from inside a peer it created a nested repository and destroyed the workspace. NOT claimed: byte-identical single-project behaviour. The scaffolded hook body did change for new projects and init now arms hooksPath where it previously printed the step; the single-project claim made for the earlier workspace change was an over-claim the panel refuted, and it is not repeated."; }
    part workspaceGateReviewGateR1 : TestResult { :>> id = "e972ccad-71f1-4d39-ba72-e6b3fc879222"; :>> outcome = VerdictKind::pass; :>> judgedAgainst = "e7d2683"; :>> judgedAt = "2026-08-27"; :>> judgedBy = "claudeOpus5"; }
    verification workspaceGateCloseOutGate : Test { :>> id = "fba689c4-9fa7-44cf-9238-c6e0290f7e58"; :>> title = "Sprint 472 closeOut gate (autonomous, D0049)"; :>> createdAt = "2026-08-27"; :>> createdBy = "claudeOpus5"; :>> method = VerificationMethod::inspect; :>> procedureText = "Autonomous closeOut (D0049): both DoDs recorded pass with their RAN receipts; the frontier was read back from keel whats-next. Two of the four workspace Criticals are closed. STILL OPEN and named rather than implied: issue276, the repo-root enforcement surface belongs to no project so the keystone lock covers it with no guard, and issue277, audit-adherence derives its signature from repo-root-relative pathspecs and is blind one directory down. The gate now RUNS across a workspace; whether it can be WEAKENED without a signature is the next question, and both remaining Criticals are that question. Self-evidencing (D0051): no human confirmation claimed."; }
    part workspaceGateCloseOutGateR1 : TestResult { :>> id = "1c257d94-5192-4699-a720-585e193a10ef"; :>> outcome = VerdictKind::pass; :>> judgedAgainst = "e7d2683"; :>> judgedAt = "2026-08-27"; :>> judgedBy = "claudeOpus5"; }
    verification workspaceGateRetroGate : Test { :>> id = "61cb6b20-51ea-477b-9cad-8429c52d3d19"; :>> title = "Sprint 472 retro gate (autonomous, D0049)"; :>> createdAt = "2026-08-27"; :>> createdBy = "claudeOpus5"; :>> method = VerificationMethod::analyze; :>> procedureText = "Autonomous retro (D0049). WELL: writing the test BEFORE the fix, against a real git repo, found a defect I was not looking for - owner_of - and then the same test found a second one in the refusal path. Both were platform path-spelling bugs of the class that a hand-built fixture from POSIX literals cannot see, which is precisely what the panel said about the original test. Reproducing the ungated workspace first meant the fix was measured against a known-bad state rather than reasoned about. FINDING: the hook body already CONTAINED a workspace branch, so the feature was written and shipped with a discriminator that was wrong for the commonest layout - the failure was not a missing capability but an untested one, and no test covered the hook body's behaviour in any layout until this sprint. AVOIDABLE-ISSUE SCAN: the init narration and the advice string were both authored in the SAME change that introduced the workspace, and both named actions that would harm the reader who followed them. Neither was exercised, because narration is not executed. Candidate forward control, stated not built: a check that every command string printed in guidance text resolves to a real subcommand - the keel hook pre-commit advice would have failed it instantly. Estimate 8 pts held."; }
    part workspaceGateRetroGateR1 : TestResult { :>> id = "c4fa68a3-69cd-4acb-a29a-8bbd3c6c92c8"; :>> outcome = VerdictKind::pass; :>> judgedAgainst = "e7d2683"; :>> judgedAt = "2026-08-27"; :>> judgedBy = "claudeOpus5"; }
}
