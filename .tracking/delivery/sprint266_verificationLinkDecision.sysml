// ProjectDeliveryS266 — Sprint 266: D0140 supersedes D0139(E)/(G); a superseded task stops being
// ready (issue098, issue099, issue100). CHANGE + EXECUTE. 3 pts.
package ProjectDeliveryS266 {
    private import EngineElement::*;
    private import EngineWork::*;
    private import EngineVerification::*;
    private import EngineRelationships::*;

    #CharteredBy dependency from verificationLinkStory to d0140;

    part verificationLinkStory : Story {
        :>> id = "0d800042-0814-6042-9b3e-000000300042";
        :>> title = "Sprint 266: D0140 retains #Verify/#DerivedFrom with kernel justification; supersede now retires a task (3 pts)";
        :>> createdAt = "2026-08-14"; :>> createdBy = "claudeOpus5"; :>> kind = WorkKind::decision; :>> priority = WorkPriority::p0; :>> owner = "claudeOpus5"; :>> estimatedPoints = 3;
    }

    action def DeliveryRunS266 {
        action storyVerificationLink;
        verification storyVerificationLinkDoD : Test { :>> id = "0d800043-0814-6043-9b3e-000000300043"; :>> method = VerificationMethod::inspect; :>> procedureText = "Covers dcVerificationLinkDecision (issue098) and dcSupersededNotReady (issue100). D0140 authored and accepted: supersedes D0139 clauses (E) and (G) ONLY, retaining #Verify (456 edges) and #DerivedFrom (37) as JUSTIFIED last resorts, and leaving the base-first rule (A/B/C/F) and clause (D) untouched. The justification is kernel-verified: `objective` DECLARES rather than references, so the shape named as the #Verify target carries no edge; the reference-bearing forms require a requirement-typed target while 309 of 456 edges point at `part Decision`; and all 37 #DerivedFrom edges are cross-metaclass, which D0055 already records as impossible for `:>`. Frozen `relationships.sysml:7-12` corrected under the §2.5 sign-off carried by D0140's acceptance — it no longer presents the objective shape as an edge. sysmlv2-syntax-notes.md gained the DECLARES-vs-REFERENCES section and the undeclared-name discriminator, so the question is settleable in one kernel cell. ALSO DELIVERED, because authoring the supersede edges exposed it: `ready` ignored #Supersede entirely, so both retired items stayed on the auto-followed frontier — fixed via `view::superseded_names`, measured ready 27 -> 25 with `outstanding` correctly unchanged. clippy clean; 161 tests; validate + all 25 guards + check-engine green."; }
        part storyVerificationLinkDoDR1 : TestResult { :>> id = "0d800044-0814-6044-9b3e-000000300044"; :>> outcome = VerdictKind::pass; :>> judgedAgainst = "e338eae"; :>> judgedAt = "2026-08-14"; :>> judgedBy = "claudeOpus5"; }
    }

    verification vlRefineGate : Test { :>> id = "0d800045-0814-6045-9b3e-000000300045"; :>> title = "Sprint 266 refine gate (DoR)"; :>> createdAt = "2026-08-14"; :>> createdBy = "claudeOpus5"; :>> method = VerificationMethod::inspect; :>> procedureText = "DoR: an ACCEPTED Decision (D0139 clause E) instructed a migration that a unanimous three-critic panel had just shown would silently delete 493 edges. That is the highest-urgency state in the backlog — not because the work is large, but because the instruction is live and the frontier is auto-followed. Sequenced first for that reason. estimatedPoints=3. DoR met."; }
    part vlRefineGateR1 : TestResult { :>> id = "0d800046-0814-6046-9b3e-000000300046"; :>> outcome = VerdictKind::pass; :>> judgedAgainst = "e338eae"; :>> judgedAt = "2026-08-14"; :>> judgedBy = "claudeOpus5"; }

    verification vlStandupGate : Test { :>> id = "0d800047-0814-6047-9b3e-000000300047"; :>> title = "Sprint 266 standup gate"; :>> createdAt = "2026-08-14"; :>> createdBy = "claudeOpus5"; :>> method = VerificationMethod::inspect; :>> procedureText = "Approach: supersede only the two clauses that are wrong, never the rule — the rule is what discriminated correctly. Correct the frozen schema comment at the same time, since it is the origin of the error and would otherwise mislead the next author. Then read the frontier back rather than assuming the supersede edges took effect. That read-back is what found issue100. No blockers."; }
    part vlStandupGateR1 : TestResult { :>> id = "0d800048-0814-6048-9b3e-000000300048"; :>> outcome = VerdictKind::pass; :>> judgedAgainst = "e338eae"; :>> judgedAt = "2026-08-14"; :>> judgedBy = "claudeOpus5"; }

    verification vlImplementGate : Test { :>> id = "0d800049-0814-6049-9b3e-000000300049"; :>> title = "Sprint 266 implement gate"; :>> createdAt = "2026-08-14"; :>> createdBy = "claudeOpus5"; :>> method = VerificationMethod::test; :>> procedureText = "The framing decision that mattered: D0140 is the base-first rule OPERATING, not an exception to it. D0139(B) requires a custom marker to carry a recorded justification naming the base constructs considered and why each fails; #Verify and #DerivedFrom now have exactly that, kernel-verified, so they change status from unjustified dialect to documented last resort. Presenting this as 'the rule was wrong' would have been the easier story and the false one. The `superseded_names` accessor is conservative on error — a failed model read yields an empty set rather than propagating, because the alternative would silently restore every retired item to ready."; }
    part vlImplementGateR1 : TestResult { :>> id = "0d80004a-0814-604a-9b3e-00000030004a"; :>> outcome = VerdictKind::pass; :>> judgedAgainst = "e338eae"; :>> judgedAt = "2026-08-14"; :>> judgedBy = "claudeOpus5"; }

    verification vlReviewGate : Test { :>> id = "0d80004b-0814-604b-9b3e-00000030004b"; :>> title = "Sprint 266 review gate"; :>> createdAt = "2026-08-14"; :>> createdBy = "claudeOpus5"; :>> method = VerificationMethod::inspect; :>> procedureText = "Reviewed. Two things were done right and one was luck. RIGHT: the supersede edges were read back rather than trusted, which caught issue100 within a minute of creating it; and the human's framing ('let's rip it out') was NARROWED before acceptance rather than after, with the tension recorded in the acceptance event so the record cannot later read as though they endorsed removing the markers. LUCK: issue100 was found only because this sprint happened to create the first supersede edges pointing at TASKS — every prior #Supersede pointed at a Need or a Decision, where readiness does not apply. Had D0140 superseded a Need, the defect would still be latent and the next task-level supersede would have been trusted."; }
    part vlReviewGateR1 : TestResult { :>> id = "0d80004c-0814-604c-9b3e-00000030004c"; :>> outcome = VerdictKind::pass; :>> judgedAgainst = "e338eae"; :>> judgedAt = "2026-08-14"; :>> judgedBy = "claudeOpus5"; }

    verification vlCloseOutGate : Test { :>> id = "0d80004d-0814-604d-9b3e-00000030004d"; :>> title = "Sprint 266 closeOut gate (autonomous, D0049)"; :>> createdAt = "2026-08-14"; :>> createdBy = "claudeOpus5"; :>> method = VerificationMethod::inspect; :>> procedureText = "Autonomous closeOut (D0049). dcVerificationLinkDecision and dcSupersededNotReady both carry passing DoD TestResults; issue098, issue099 and issue100 resolve. D0140 accepted with the human's verbatim attestation and its scope stated precisely as a PASS-level acceptance rather than a per-clause one. The two harmful migration items are off the ready frontier, verified by read-back. keel serve was shut down and its process confirmed gone — it had been holding target/release/keel.exe and blocking the build. clippy clean; 161 tests; validate + all 25 guards + check-engine green."; }
    part vlCloseOutGateR1 : TestResult { :>> id = "0d80004e-0814-604e-9b3e-00000030004e"; :>> outcome = VerdictKind::pass; :>> judgedAgainst = "e338eae"; :>> judgedAt = "2026-08-14"; :>> judgedBy = "claudeOpus5"; }

    verification vlRetroGate : Test { :>> id = "0d80004f-0814-604f-9b3e-00000030004f"; :>> title = "Sprint 266 retro gate (autonomous, D0049)"; :>> createdAt = "2026-08-14"; :>> createdBy = "claudeOpus5"; :>> method = VerificationMethod::analyze; :>> procedureText = "Autonomous retro (D0049) under D0131's retroTrack. WELL: (1) the panel's verdict was implemented as a NARROWING of D0139 rather than a repudiation, which is both more accurate and what leaves the rule usable; (2) the frozen schema comment that CAUSED the error was corrected in the same commit as the Decision, so the origin and the correction cannot drift apart; (3) the supersede edges were read back immediately, which is the only reason issue100 was found at all. AVOIDABLE-ISSUE 1: I authored two supersede edges and reported the two items retired in the commit message BEFORE reading the frontier — the message was written first and would have been false. Caught by the read-back, but the ordering was wrong: the claim should not be drafted until the view confirms it. NO NEW ITEM, reason stated: this is the read-back-the-computed-answer principle, already carried by the accepted response contract and now on its seventh recorded instance this sitting; the count is the signal and it is consistently about trusting an intermediate rather than the thing actually asked. AVOIDABLE-ISSUE 2: `keel serve` was left running for several turns and silently held `target/release/keel.exe`, so the first build after the orient change failed with 'Access is denied' — a confusing error whose cause was a server I had started and offered to stop. NO NEW ITEM, reason stated: the background-task-hygiene rule already covers not leaving servers running, and the fix is to shut one down when the work that needed it is finished rather than when someone asks. AVOIDABLE-ISSUE 3 (scope, stated not deferred silently): a superseded item now counts as `outstanding` forever, which will slowly inflate the burndown with work nobody will do. Deliberately NOT fixed in this sprint because changing what `outstanding` means is a headline-count change and folding it into a defect repair would hide it. It needs its own decision about whether retired work is outstanding, and that decision is not urgent. Estimate 3 pts, delivered."; }
    part vlRetroGateR1 : TestResult { :>> id = "0d800050-0814-6050-9b3e-000000300050"; :>> outcome = VerdictKind::pass; :>> judgedAgainst = "e338eae"; :>> judgedAt = "2026-08-14"; :>> judgedBy = "claudeOpus5"; }
}
