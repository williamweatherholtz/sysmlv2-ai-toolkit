// ProjectDeliveryS269 — Sprint 269: the parser READS `:>` specialization (issue102 construct 1/6), and
// the latent scope bug that exposed (issue103). EXECUTE. 3 pts.
package ProjectDeliveryS269 {
    private import EngineElement::*;
    private import EngineWork::*;
    private import EngineVerification::*;
    private import EngineRelationships::*;

    #CharteredBy dependency from readSpecializeStory to d0140;

    part readSpecializeStory : Story {
        :>> id = "0d800077-0814-6077-9b3e-000000300077";
        :>> title = "Sprint 269: read + validate `:>` specialization; fix same-package scope (3 pts)";
        :>> createdAt = "2026-08-14"; :>> createdBy = "claudeOpus5"; :>> kind = WorkKind::code; :>> priority = WorkPriority::p0; :>> owner = "claudeOpus5"; :>> estimatedPoints = 3;
    }

    action def DeliveryRunS269 {
        action storyReadSpecialize;
        verification storyReadSpecializeDoD : Test { :>> id = "0d800078-0814-6078-9b3e-000000300078"; :>> method = VerificationMethod::test; :>> procedureText = "Covers dcParserReadSpecialize (issue103) — construct 1 of 6 for dcParserReadBase, ranked first because `:>` is the derivation form D0140 names as the only valid replacement for #DerivedFrom, and all 52 clauses were unread so the type hierarchy was invisible to every guard and view. DELIVERED: `TypeDef.specializes`, `parse_specializes`, an extracted `type_def_tail` used at all six def sites (the extraction removes duplication this change introduced, so it belongs to this change), and target resolution through the existing `check_type_ref`. VERIFIED WITH BOTH POLARITIES: undeclared supertype FAILS with a semantic diagnostic; declared same-package supertype PASSES; no clause PASSES; the real repo and `.engine` stay clean. The positive control is what earned its keep — it exposed issue103, a latent scope bug where `resolve_scope` walked only IMPORTED namespaces so a package could not reference its OWN declarations, which had lain dormant because every reference in practice crossed a package boundary and the one construct that routinely does not (`:>`) was the unread one. Two defects concealing each other. ALSO corrected the parser-coverage metric: capturing `:>` moved 52 records from ColonGt to LBrace WITHOUT changing the total, proving it counted skip_item INVOCATIONS rather than unread statements; `{` and `;` leads are no longer recorded and the figure fell 165 -> 74, which now means what its name says. clippy clean (including an extracted-function fix for a 106-line `parse_item`); 161 tests; validate + all 27 guards + check-engine green."; }
        part storyReadSpecializeDoDR1 : TestResult { :>> id = "0d800079-0814-6079-9b3e-000000300079"; :>> outcome = VerdictKind::pass; :>> judgedAgainst = "662a94b"; :>> judgedAt = "2026-08-14"; :>> judgedBy = "claudeOpus5"; }
    }

    verification rsRefineGate : Test { :>> id = "0d80007a-0814-607a-9b3e-00000030007a"; :>> title = "Sprint 269 refine gate (DoR)"; :>> createdAt = "2026-08-14"; :>> createdBy = "claudeOpus5"; :>> method = VerificationMethod::inspect; :>> procedureText = "DoR: dcParserReadBase names six constructs; `:>` is first because D0140 depends on it and because 52 unread clauses is the largest single gap. Taking one construct per sprint rather than all six at once is deliberate — the DoD requires per-construct verification, and a six-construct sprint would verify in aggregate and hide exactly the kind of defect issue103 turned out to be. estimatedPoints=3. DoR met."; }
    part rsRefineGateR1 : TestResult { :>> id = "0d80007b-0814-607b-9b3e-00000030007b"; :>> outcome = VerdictKind::pass; :>> judgedAgainst = "662a94b"; :>> judgedAt = "2026-08-14"; :>> judgedBy = "claudeOpus5"; }

    verification rsStandupGate : Test { :>> id = "0d80007c-0814-607c-9b3e-00000030007c"; :>> title = "Sprint 269 standup gate"; :>> createdAt = "2026-08-14"; :>> createdBy = "claudeOpus5"; :>> method = VerificationMethod::inspect; :>> procedureText = "Approach: capture the clause, then resolve it through the EXISTING `check_type_ref` rather than writing a second resolution path — a `:>` target is an ordinary type reference and giving it its own checker would let the two drift. Then run both polarities, not just the negative. No blockers."; }
    part rsStandupGateR1 : TestResult { :>> id = "0d80007d-0814-607d-9b3e-00000030007d"; :>> outcome = VerdictKind::pass; :>> judgedAgainst = "662a94b"; :>> judgedAt = "2026-08-14"; :>> judgedBy = "claudeOpus5"; }

    verification rsImplementGate : Test { :>> id = "0d80007e-0814-607e-9b3e-00000030007e"; :>> title = "Sprint 269 implement gate"; :>> createdAt = "2026-08-14"; :>> createdBy = "claudeOpus5"; :>> method = VerificationMethod::test; :>> procedureText = "Only the FIRST `:>` target is captured. SysML v2 permits several; nothing in this schema declares more than one, and building multi-supertype support with no instance to test it against is how unused schema accumulates — the precedent is rules.sysml:63-66, where `OrderingRule` was removed as dead schema with the explicit rule 're-add it THEN, with an instance'. The same reasoning applied to the parser rather than the model."; }
    part rsImplementGateR1 : TestResult { :>> id = "0d80007f-0814-607f-9b3e-00000030007f"; :>> outcome = VerdictKind::pass; :>> judgedAgainst = "662a94b"; :>> judgedAt = "2026-08-14"; :>> judgedBy = "claudeOpus5"; }

    verification rsReviewGate : Test { :>> id = "0d800080-0814-6080-9b3e-000000300080"; :>> title = "Sprint 269 review gate"; :>> createdAt = "2026-08-14"; :>> createdBy = "claudeOpus5"; :>> method = VerificationMethod::inspect; :>> procedureText = "Reviewed. The sprint's real lesson is methodological and worth more than the construct: a NEGATIVE test alone would have shipped issue103, because the undeclared-supertype case failed correctly for the wrong reason — everything failed. Only the positive control distinguished 'the checker works' from 'the checker rejects everything'. That is the second time in this pass that the discriminating test mattered more than the feature, after the undeclared-name probe on `objective`. Five constructs remain for dcParserReadBase: use-case usages (56 unread), `ref`, `assert`/`require constraint`, ports/interface/connect, and `flow` (18)."; }
    part rsReviewGateR1 : TestResult { :>> id = "0d800081-0814-6081-9b3e-000000300081"; :>> outcome = VerdictKind::pass; :>> judgedAgainst = "662a94b"; :>> judgedAt = "2026-08-14"; :>> judgedBy = "claudeOpus5"; }

    verification rsCloseOutGate : Test { :>> id = "0d800082-0814-6082-9b3e-000000300082"; :>> title = "Sprint 269 closeOut gate (autonomous, D0049)"; :>> createdAt = "2026-08-14"; :>> createdBy = "claudeOpus5"; :>> method = VerificationMethod::inspect; :>> procedureText = "Autonomous closeOut (D0049). dcParserReadSpecialize carries a passing DoD TestResult; issue103 resolves. dcParserReadBase remains OUTSTANDING — five of six constructs are unread, and partial progress is tracked by the sub-item rather than by editing the umbrella's criterion, which would be prose state. parser-coverage now reports 74 (was 165, of which 52 were absorbed and 39 were miscounted braces/semicolons). clippy clean; 161 tests; validate + all 27 guards + check-engine green. No gate bypassed."; }
    part rsCloseOutGateR1 : TestResult { :>> id = "0d800083-0814-6083-9b3e-000000300083"; :>> outcome = VerdictKind::pass; :>> judgedAgainst = "662a94b"; :>> judgedAt = "2026-08-14"; :>> judgedBy = "claudeOpus5"; }

    verification rsRetroGate : Test { :>> id = "0d800084-0814-6084-9b3e-000000300084"; :>> title = "Sprint 269 retro gate (autonomous, D0049)"; :>> createdAt = "2026-08-14"; :>> createdBy = "claudeOpus5"; :>> method = VerificationMethod::analyze; :>> procedureText = "Autonomous retro (D0049) under D0131's retroTrack. WELL: (1) running BOTH polarities found issue103, a bug latent for the project's entire life, and the negative-only version of the same test would have passed while proving nothing; (2) resolution reused `check_type_ref` instead of adding a parallel path, so `:>` cannot drift from every other type reference; (3) the metric was corrected the moment it was shown to be measuring the wrong thing, rather than after the number had been quoted a few more times — a wrong measure is worse than none because it is trusted. AVOIDABLE-ISSUE 1: I wrote the DoD criterion as 'parser-coverage drops by exactly the number of statements each step absorbs' and it did NOT drop — the total held at 165 while 52 records merely changed label. The criterion was wrong, not the work; it assumed the metric measured unread statements when it measured skip invocations. NO NEW ITEM, reason stated: the criterion's failure is what exposed the metric defect, so the mechanism worked as intended; the transferable point is that a verification criterion phrased against a NUMBER must first establish what that number counts, and it is now recorded here and in the corrected guard. AVOIDABLE-ISSUE 2: clippy's 100-line limit fired on `parse_item` only after I had added the same three lines to six call sites — the duplication was visible while I was writing it and I extracted it only when forced. NO NEW ITEM, reason stated: clippy IS the control and it caught it in the same sprint; the cost was one build cycle. Estimate 3 pts, delivered."; }
    part rsRetroGateR1 : TestResult { :>> id = "0d800085-0814-6085-9b3e-000000300085"; :>> outcome = VerdictKind::pass; :>> judgedAgainst = "662a94b"; :>> judgedAt = "2026-08-14"; :>> judgedBy = "claudeOpus5"; }
}
