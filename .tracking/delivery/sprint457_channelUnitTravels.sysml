// ProjectDeliveryS457 — Sprint 457: the decision channel moves as a unit and names no owner, so another project can adopt it without forking the mechanism (issue251, D0219). EXECUTE. 3 pts.
package ProjectDeliveryS457 {
    private import EngineElement::*;
    private import EngineWork::*;
    private import EngineVerification::*;
    private import EngineRelationships::*;

    #CharteredBy dependency from channelUnitTravelsStory to d0219;

    part channelUnitTravelsStory : Story {
        :>> id = "6a3186e9-5bed-4049-a7ab-2389427c7972";
        :>> title = "Sprint 457: the channel travels, and nobody inherits my identity (3 pts)";
        :>> createdAt = "2026-08-24"; :>> createdBy = "claudeFable5"; :>> kind = WorkKind::code; :>> priority = WorkPriority::p0; :>> owner = "claudeFable5"; :>> estimatedPoints = 3;
    }

    action def DeliveryRunS457 {
        action storyChannelUnitTravels;
        verification storyChannelUnitTravelsDoD : Test { :>> id = "281d5828-265c-48d3-978d-f0660def1165"; :>> method = VerificationMethod::test; :>> procedureText = "DELIVERED: dcChannelUnitTravels (resolves issue251, HIGH, discoveredInField). The human asked to activate the GitHub decision channel on asirobots/penumbra with the constraint: do not force me to be owner of every new project, be modular and careful. FOUR defects, three of which would have BROKEN rather than degraded on the first adoption. (1) TRANSFER: export produced three files - definition, skill, unit.toml - while the five that ARE the channel stayed home; the guard travelled BY NAME and the machinery not at all, violating srPortModularProcessUnit (a unit moves without leaving its enforcement behind), the same class as issue241 and issue245. (2) OWNER-AS-PERSON: the opener assigned to github.repository_owner, which is not a person - for asirobots/penumbra it is an ORG, and gh issue create --assignee <org> FAILS. (3) IDENTITY IN SOURCE: the decider login was a literal in decision-record.yml three times, so every adopter had to edit the workflow, forking the mechanism and touching its own frozen enforcement surface. (4) WORST, found only by round-trip test: keel init shipped THIS project's github-actors.toml verbatim, so every new project silently inherited MY login as its authorized decider and would have recorded acceptances in my name - the issue243 class landing on the single most consequential instance fact in the tree. WHAT WAS BUILT: unit-extras.toml declares per-unit files AND the prerequisites a receiving project must satisfy, carried by export and listed by process show so an importer is TOLD rather than discovering it when nothing records; keel github-decider [<login>] is the ONE implementation of who-may-decide, read from the committed table, so the workflow gate and the recorder can no longer drift; the workflow's job condition is structural only (decision label, human commenter) with authorization a step, and an outsider's comment leaves the run GREEN with an explanation because a bystander is not a build failure; assignment goes to the declared deciders or to nobody, with the decision label carrying discoverability; and github-actors.toml joins init's instance-contract reset, starting as an empty commented template that states the repo owner is not automatically a decider and an ORG can never be one. TWO FURTHER BUGS the round trip caught, both of which had been REPORTING SUCCESS: export derived destinations by stripping .engine, and for a file outside .engine the strip FAILED so the absolute-path fallback made join discard the base - it copied the file onto ITSELF and died with 'used by another process'; and the --update loop had its own .engine-join, writing .github/workflows/x.yml into .engine/.github/workflows/x.yml, inert and in the wrong place, while printing '6 file(s) from upstream'. Both loops now share one destination mapper. VERIFIED: export yields 6 files + unit.toml at exit 0; a round trip into a throwaway inited project lands the workflows and scripts in .github/ with that project's own keel-gate.yml intact and nothing in .engine/.github/; a fresh init declares NO decider and refuses my login with the remedy; 256 lib tests pass; clippy clean; validate 508 + all 49 guards + check-engine + rules green."; }
        part storyChannelUnitTravelsDoDR1 : TestResult { :>> id = "a9e5e0a1-9312-4b7a-95a4-81907336d910"; :>> outcome = VerdictKind::pass; :>> judgedAgainst = "d129343588ed2ab4dd901d9c28b4c598bc3be2bb"; :>> judgedAt = "2026-08-24"; :>> judgedBy = "claudeFable5"; }
    }

    verification channelUnitTravelsRefineGate : Test { :>> id = "9dc002bd-4361-4788-8e90-25cc4a353993"; :>> title = "Sprint 457 refine gate (DoR)"; :>> createdAt = "2026-08-24"; :>> createdBy = "claudeFable5"; :>> method = VerificationMethod::inspect; :>> procedureText = "DoR. Resolves issue251, raised in the field by the human wanting to adopt the channel elsewhere. Scope: make the unit carry its mechanism, and remove every trace of one project's identity from that mechanism. The human's modularity constraint is a REQUIREMENT here, not a preference. 3 points."; }
    part channelUnitTravelsRefineGateR1 : TestResult { :>> id = "f89e3069-f4c7-4d9c-b8f5-21a3bbc205ac"; :>> outcome = VerdictKind::pass; :>> judgedAgainst = "d129343588ed2ab4dd901d9c28b4c598bc3be2bb"; :>> judgedAt = "2026-08-24"; :>> judgedBy = "claudeFable5"; }
    verification channelUnitTravelsStandupGate : Test { :>> id = "b391605e-5a1e-464e-9cfb-81172be436f3"; :>> title = "Sprint 457 standup gate"; :>> createdAt = "2026-08-24"; :>> createdBy = "claudeFable5"; :>> method = VerificationMethod::inspect; :>> procedureText = "Approach: the two goals are one goal - a mechanism cannot travel while it has a project's identity welded into it, so de-hardcoding the decider is a PRECONDITION of transferability rather than a separate courtesy. Declare extras as data (the D0184 rule-owners precedent) so a project adds its own units without a fork. Keep the decider table as the single authorization source per D0105: 'who may decide' and 'whose judgment is attributable' are one fact, and the recorder had always enforced exactly that - only the workflow disagreed. Touching .github/workflows means the frozen enforcement surface, so D0219 co-commits. No blockers."; }
    part channelUnitTravelsStandupGateR1 : TestResult { :>> id = "ad6c5691-ea08-4629-b2fb-6d66c8aa32b5"; :>> outcome = VerdictKind::pass; :>> judgedAgainst = "d129343588ed2ab4dd901d9c28b4c598bc3be2bb"; :>> judgedAt = "2026-08-24"; :>> judgedBy = "claudeFable5"; }
    verification channelUnitTravelsImplementGate : Test { :>> id = "37fe7b71-6a5c-4f6b-8232-095834171459"; :>> title = "Sprint 457 implement gate"; :>> createdAt = "2026-08-24"; :>> createdBy = "claudeFable5"; :>> method = VerificationMethod::test; :>> procedureText = "Verified by running the freshness-checked binary and by an actual ROUND TRIP rather than an export alone: export yields 6 files + unit.toml at exit 0; importing into a throwaway inited project with --update --assume-local-base lands both workflows and both scripts under .github/ while the project's own keel-gate.yml survives and .engine/.github/ is empty; process show in the receiving project lists the files and the three prerequisites; a fresh keel init reports no declared decider and refuses williamweatherholtz at exit 1 naming the remedy. cargo test --lib -> 256 passed including three new github tests and the extended init-reset test; clippy --workspace --all-targets clean after several lint passes; validate 508 + all 49 guards + check-engine + rules green."; }
    part channelUnitTravelsImplementGateR1 : TestResult { :>> id = "5c09f261-1224-4d9c-8ac3-434673da380d"; :>> outcome = VerdictKind::pass; :>> judgedAgainst = "d129343588ed2ab4dd901d9c28b4c598bc3be2bb"; :>> judgedAt = "2026-08-24"; :>> judgedBy = "claudeFable5"; }
    verification channelUnitTravelsReviewGate : Test { :>> id = "79e4e32a-6083-4ace-aa5c-1a87aa02a822"; :>> title = "Sprint 457 review gate — three passes per D0172"; :>> createdAt = "2026-08-24"; :>> createdBy = "claudeFable5"; :>> method = VerificationMethod::inspect; :>> procedureText = "PASS 1, CLAIMS: every exit code, file listing and refusal message is a quoted read-back from the built binary, and the two copy bugs are quoted from the failing runs rather than reasoned about. PASS 2, BOUNDARY: (i) the channel still requires the receiving repo to allow its Actions token to push to the default branch - declared in requires, not solved here; (ii) only decision-channel has extras declared, so this closes the mechanism-transfer hole for that unit and gives every other unit the same facility unused; (iii) a bundle entry is treated as repo-relative iff its first path component starts with '.', which is a convention rather than a type - a future extra at a non-dot path would land under .engine, and that is stated rather than guarded; (iv) EXISTING downstream projects that already inherited this repo's github-actors.toml keep it until they change it: the init fix is forward-only, because rewriting another project's declared deciders without being asked would be the same defect in reverse. PASS 3, OWN DIFF: the two copy bugs are the finding I would most want a reviewer to weigh, because both REPORTED SUCCESS - one printed '6 file(s) from upstream' while putting them somewhere inert. I found them only because I ran the round trip instead of trusting the export, which is the exit-code-is-not-the-claim lesson from sprint446 applied one level up: the file COUNT is not the claim either. I also hit the nested-heredoc escaping trap again and switched to literal edits. WHAT A REVIEWER SHOULD ATTACK: the dot-prefix convention for repo-relative extras, and whether declaring prerequisites as prose in a contract is strong enough - nothing checks that a receiving project actually satisfied them, so an importer can still land the unit and have it sit silent."; }
    part channelUnitTravelsReviewGateR1 : TestResult { :>> id = "f1b17edf-df14-430b-bdf4-92afd256f38d"; :>> outcome = VerdictKind::pass; :>> judgedAgainst = "d129343588ed2ab4dd901d9c28b4c598bc3be2bb"; :>> judgedAt = "2026-08-24"; :>> judgedBy = "claudeFable5"; }
    verification channelUnitTravelsCloseOutGate : Test { :>> id = "d46df19a-3071-4a4c-83fc-9e5f2b47287b"; :>> title = "Sprint 457 closeOut gate (autonomous, D0049)"; :>> createdAt = "2026-08-24"; :>> createdBy = "claudeFable5"; :>> method = VerificationMethod::inspect; :>> procedureText = "Autonomous closeOut (D0049). issue251 resolved: the channel exports and round-trips whole, no file needs editing to adopt it, and no project inherits another's decider. validate + all 49 guards + check-engine + rules green. The adoption on penumbra is the next act and is deliberately NOT bundled into this sprint - the capability lands first, then it gets used."; }
    part channelUnitTravelsCloseOutGateR1 : TestResult { :>> id = "82e102d2-9562-452f-871e-03a8242c76c0"; :>> outcome = VerdictKind::pass; :>> judgedAgainst = "d129343588ed2ab4dd901d9c28b4c598bc3be2bb"; :>> judgedAt = "2026-08-24"; :>> judgedBy = "claudeFable5"; }
    verification channelUnitTravelsRetroGate : Test { :>> id = "2735a13c-88e5-4fff-93a4-7f9e4184e971"; :>> title = "Sprint 457 retro gate (autonomous, D0049)"; :>> createdAt = "2026-08-24"; :>> createdBy = "claudeFable5"; :>> method = VerificationMethod::analyze; :>> procedureText = "Autonomous retro (D0049). AVOIDABLE-ISSUE SCAN under rcRecurrence: (1) THE finding: two separate copy paths each reported success while doing the wrong thing, and only a ROUND TRIP exposed them - an export that exits 0 and prints a file count proves neither that the files are readable at the destination nor that they are in the right place. The durable rule extends sprint446's exit-code-is-not-the-claim: for anything that MOVES data, the claim is the state at the destination, so verify by reading the destination. (2) The same-rule-in-two-loops class caused it: fresh-import and --update each had their own .engine-join, so fixing one left the other wrong; they now share one mapper. (3) The nested-heredoc escaping trap recurred a fourth time this session and cost a cycle. WELL: the human's constraint - do not make me the owner of every project - turned out to be a precondition of the portability requirement rather than a competing preference, and following it uncovered that every keel init project had been silently inheriting my authority to accept decisions. That is the most consequential single defect found in this whole run, and it surfaced only because they said be modular and careful. Estimate 3 pts, delivered 3."; }
    part channelUnitTravelsRetroGateR1 : TestResult { :>> id = "5ff6cf58-2753-4732-9e91-880354a5d9e7"; :>> outcome = VerdictKind::pass; :>> judgedAgainst = "d129343588ed2ab4dd901d9c28b4c598bc3be2bb"; :>> judgedAt = "2026-08-24"; :>> judgedBy = "claudeFable5"; }
}
