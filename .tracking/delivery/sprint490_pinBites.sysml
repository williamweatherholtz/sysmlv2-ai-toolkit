// ProjectDeliveryS490 — Sprint 490: the pin bites: engine-version.toml is now binding for writes and gates. EXECUTE. 5 pts.
package ProjectDeliveryS490 {
    private import EngineElement::*;
    private import EngineWork::*;
    private import EngineVerification::*;
    private import EngineRelationships::*;

    #CharteredBy dependency from pinBitesStory to d0251;

    part pinBitesStory : Story {
        :>> id = "c5f3724a-e511-4a42-8d30-c5abdffdffe1";
        :>> title = "Sprint 490: the engine pin becomes binding - writes and gates refuse on skew, reads warn (5 pts)";
        :>> createdAt = "2026-08-29"; :>> createdBy = "claudeOpus5"; :>> kind = WorkKind::code; :>> priority = WorkPriority::p0; :>> owner = "claudeOpus5"; :>> estimatedPoints = 5;
    }

    action def DeliveryRunS490 {
        action storyPinBites;
        verification storyPinBitesDoD : Test { :>> id = "f18a39d1-5b58-4f05-8965-c74c97fa6cd3"; :>> method = VerificationMethod::test; :>> procedureText = "Discharges srProjectPinsItsEngine and srWorkspacePinIsCoherent (dcPinBites, increment 1 of the readiness plan, D0251 clauses A/C). engine-version.toml escalates from a parity WARNING to a BINDING pin: every model write refuses on skew at the with_file_lock choke point (all write paths by construction), every gate surface refuses (gate_problems - the one gate body, covering gate/sync/land/pre-commit - plus validate, guard, gate --fast at their entries), reads warn loudly and proceed, version and migrate never refuse, an absent declaration keeps working (D0136). Workspace coherence falls out of the one-body design: disagreeing pins cannot both match one binary, so the mismatched project refuses under its own tag. VERIFY: six Gherkin scenarios in keel-cli/tests/pin_actually_bites.rs, written RED first (0/6 against the old binary), now 6/6; clippy; 18 suites; migrate announces the escalation at re-stamp.: DELIVERED BACKLOG ITEMS: <items>. <what done means, verified how>."; }
        // RAN: // RAN: cargo test --release -p keel-cli --test pin_actually_bites -> RED 0/6 before implementation, GREEN 6/6 after; cargo clippy -D warnings clean; cargo test --workspace --release -> 18 suites ok 0 FAILED (incl. the pre-existing no_public_write_reads_outside_the_lock meta-control, which caught the first draft); keel guard 54 guards 0 FAIL; gate --fast clean
        part storyPinBitesDoDR1 : TestResult { :>> id = "7c62e6d9-edfa-4e9c-8ca2-6350d4fc952b"; :>> outcome = VerdictKind::pass; :>> judgedAgainst = "5fcaad7"; :>> judgedAt = "2026-08-29"; :>> judgedBy = "claudeOpus5"; }
    }

    verification pinBitesRefineGate : Test { :>> id = "08ca9a0b-9578-4da5-8f09-c55f0e6e9ca6"; :>> title = "Sprint 490 refine gate (DoR)"; :>> createdAt = "2026-08-29"; :>> createdBy = "claudeOpus5"; :>> method = VerificationMethod::inspect; :>> procedureText = "READY: chartered by accepted D0251; the requirement thresholds were authored in Phase 2 and accepted with the Need baseline (engineNeedsAccept). The Gherkin was written BEFORE implementation and run to RED: 0/6 initially - which itself caught two fixture defects (no on-disk schema, migrate needs git) before any implementation line was written."; }
    verification pinBitesStandupGate : Test { :>> id = "599043a1-2f26-466c-bf3e-b52cb04d9485"; :>> title = "Sprint 490 standup gate"; :>> createdAt = "2026-08-29"; :>> createdBy = "claudeOpus5"; :>> method = VerificationMethod::inspect; :>> procedureText = "No external blocker. Sequencing note: the six scenarios went RED -> fixture-corrected RED (2 allow-cases green, 4 feature-cases red) -> GREEN, which is the TDD shape the plan promised (st033)."; }
    verification pinBitesImplementGate : Test { :>> id = "3c92d873-5dbd-4f6c-8233-1b7ccf865486"; :>> title = "Sprint 490 implement gate"; :>> createdAt = "2026-08-29"; :>> createdBy = "claudeOpus5"; :>> method = VerificationMethod::test; :>> procedureText = "RAN: cargo test --release -p keel-cli --test pin_actually_bites -> 6/6; clippy -D warnings clean; cargo test --workspace --release -> 18 suites 0 FAILED; keel guard 54 0 FAIL. DESIGN: pin_skew lives in lib.rs and is consumed at TWO choke points - with_file_lock (writes, all paths by construction) and workspace::gate_problems (verdicts, one body three callers per issue282) - plus the three direct gate entries (validate, guard, gate --fast) and a loud stderr warning in orient. AN EXISTING META-CONTROL CAUGHT THE FIRST DRAFT: write.rs's no_public_write_reads_outside_the_lock failed on pin_skew reading engine-version.toml from inside the write module - the pf12-class control I had called candidate work ALREADY EXISTED, and it fired on me. Resolved by moving pin_skew to lib.rs, respecting the invariant rather than widening its exemption list."; }
    verification pinBitesReviewGate : Test { :>> id = "83b23d33-d694-43e1-9ba0-c83d0fafd7ad"; :>> title = "Sprint 490 review gate — three passes per D0172"; :>> createdAt = "2026-08-29"; :>> createdBy = "claudeOpus5"; :>> method = VerificationMethod::inspect; :>> procedureText = "THREE PASSES. (1) CLASS COVERAGE BY CONSTRUCTION: the write refusal sits inside with_file_lock, so a write path that skips the pin skips the LOCK - which the write-lock probe exposes as lost writes. The propriety lens applied at design time. (2) THE OVER-STRICT FAILURE AVOIDED: reads proceed (orient warns on stderr so its JSON stays parseable), version/migrate never refuse - blocking the diagnostic and repair commands is how a gate trains its actor to disable it (D0197). (3) ESCALATION IS ANNOUNCED WHERE IT IS ACTIONABLE: migrate prints the D0251 notice at re-stamp, so an existing project hears that the stamp's meaning changed at the exact moment it acquires a current stamp."; }
    verification pinBitesCloseOutGate : Test { :>> id = "e6c4aff7-6ae3-4a39-a101-27d332a4369e"; :>> title = "Sprint 490 closeOut gate (autonomous, D0049)"; :>> createdAt = "2026-08-29"; :>> createdBy = "claudeOpus5"; :>> method = VerificationMethod::inspect; :>> procedureText = "CLOSED. Increment 1 of 5 done; dcPinBites discharges. RESIDUAL, named: the pin compares EXACT strings - a binary built from a dirty tree still reports its crate version, so 0.3.0+dirty passes a 0.3.0 pin (the +dirty suffix is not in CARGO_PKG_VERSION). Sharper identity (build commit in the pin) was considered and rejected by D0251 clause A: a legitimate rebuild at the same version must not read as tampering. Next: dcKeelWrapper (increment 2)."; }
    verification pinBitesRetroGate : Test { :>> id = "b6d13319-bda5-455a-addd-fca2240313d1"; :>> title = "Sprint 490 retro gate (autonomous, D0049)"; :>> createdAt = "2026-08-29"; :>> createdBy = "claudeOpus5"; :>> method = VerificationMethod::analyze; :>> procedureText = "FINDING: the meta-control that caught pin_skew's placement (no_public_write_reads_outside_the_lock) is exactly the control the propriety panel had marked as pf12's candidate work - it already existed, and neither the panel nor its author knew. The control map now has 15 declared controls and this one is in NONE of them: the implemented-but-undeclared class (D0254) demonstrably extends to META-controls over the write API. Not filed as a new issue: issue304's resolver landed the event-anchored reconciliation, and event-less controls were pf07's ACCEPTED residual - this is a live instance of that acceptance, recorded here as evidence the disposition should weigh."; }
    // The #Verify edges these DoDs EARNED and never carried (found by the rigor audit,
    // 2026-08-30): the work was verified, the REQUIREMENT was not (issue082).
    #Verify dependency from storyPinBitesDoD to srProjectPinsItsEngine;
    #Verify dependency from storyPinBitesDoD to srWorkspacePinIsCoherent;
}
