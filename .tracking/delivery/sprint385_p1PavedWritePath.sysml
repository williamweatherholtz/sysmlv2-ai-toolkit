// ProjectDeliveryS385 — Sprint 385: P1 - the write path is paved: three tiers, the never-exempt human channel, rules wired into every gate. EXECUTE. 13 pts.
package ProjectDeliveryS385 {
    private import EngineElement::*;
    private import EngineWork::*;
    private import EngineVerification::*;
    private import EngineRelationships::*;

    #CharteredBy dependency from p1PavedWritePathStory to d0176;

    part p1PavedWritePathStory : Story {
        :>> id = "6ef2b3d7-9518-4d51-8813-332dc7912235";
        :>> title = "Sprint 385: P1 - the paved write path, human channels, and rules with teeth (13 pts)";
        :>> createdAt = "2026-08-21"; :>> createdBy = "claudeFable5"; :>> kind = WorkKind::code; :>> priority = WorkPriority::p0; :>> owner = "claudeFable5"; :>> estimatedPoints = 13;
    }

    action def DeliveryRunS385 {
        action storyP1PavedWritePath;
        verification storyP1PavedWritePathDoD : Test { :>> id = "a62a2a83-4ef1-484a-8c13-16cfb4793d47"; :>> method = VerificationMethod::test; :>> procedureText = "DELIVERED BACKLOG ITEMS: p1TieredDeny, p1BashMatcher, p1HumanChannel, p1ControlPlane, p1RulesWired, p1AuditHistoryCi, p1RedYield. THE TIERS (d0176), all run live on a strict scaffold: tier 1 hard-denies API-owned surfaces naming the sanctioned command; tier 2 asks on other .tracking writes; tier 3 is `keel override <path> --reason` - single-use (second write re-denied, proven), path-bound, 900s expiry, consumption recording an orient-visible obligation Issue ONE FILE PER FACT so recording never deadlocks on the file being repaired, with a local-ledger fallback on tracked-write failure. Control plane (d0179): .claude/settings.json, .githooks/, the output style, plus Bash core.hooksPath/deactivate/actor mutation route to ask with a recorded fact under strict - and the pure-shell test covers control-plane paths, so they are denied even with NO binary. THE MATCHER (d0176/d0178) tokenizes argv - a commit message DESCRIBING --no-verify is one quoted token and does not match (tested); unambiguous blocks: redirection/tee/sed -i into fact surfaces, --no-verify, SKIP_VALIDATE/SKIP_KEEL, core.hooksPath; keel-argv0 commands are exempt EXCEPT the never-exempt set DERIVED from write.rs's WRITE_OPS declared-attribute table (accept, apply-review, actor, enroll, deactivate) and any invocation carrying KEEL_ACTOR/--by/--judged-by naming a registered Person. HUMAN CHANNEL (d0178), three layers: the write layer refuses AI-kind and unregistered judges on accept_decision AND on method=confirmation results (unit-tested both ways: Person passes, AI refused, method=test unaffected); the channel layer refuses `keel accept` in agent-marked sessions without a TTY - PROVEN BY THIS SESSION REFUSING ITSELF, live; the matcher layer above. RULES WIRED (d0177): blocking rules gate hook stop, the pre-commit (self-build script + scaffolded const), and CI via the new `keel rules --enforce`; the scaffolded CI template's rules step activated; hook_stop now routes guards through run_all so the ACTIVATION FILTER applies - the proposal's cited bypass (a deactivated process's guard blocking turns) is dead. AUDIT (d0179/K15): CI runs keel audit-history over the pushed range; CLAUDE.md's never-rebase line softened to what is actually enforced. RED-YIELD (d0176): the Stop hook's second red pass still yields but records a tracked obligation (ledger fallback when the actor is unbound, so the yield record can never deepen the red it records). The self-build declares profile=guided: every detection runs and the fire-ledger accrues the D0180 evidence; blocking here is a future promotion decision citing it (K14). 220 tests; clippy 0; 41 guards ALL PASS."; }
        part storyP1PavedWritePathDoDR1 : TestResult { :>> id = "12817c2b-64df-4b61-9187-83ce0885e664"; :>> outcome = VerdictKind::pass; :>> judgedAgainst = "894e394"; :>> judgedAt = "2026-08-21"; :>> judgedBy = "claudeFable5"; }
    }

    verification p1PavedWritePathRefineGate : Test { :>> id = "a2fda465-dbd8-40ac-a801-09d7ae5fd367"; :>> title = "Sprint 385 refine gate (DoR)"; :>> createdAt = "2026-08-21"; :>> createdBy = "claudeFable5"; :>> method = VerificationMethod::inspect; :>> procedureText = "DoR. P1's seven chartered items, the P0-P1 chain being the one hard prerequisite path everything shares. The accepted decision texts (d0176-d0179) were read as the spec before any code. estimatedPoints=13."; }
    part p1PavedWritePathRefineGateR1 : TestResult { :>> id = "3f71a302-c98d-40df-bed3-afa1835987f1"; :>> outcome = VerdictKind::pass; :>> judgedAgainst = "894e394"; :>> judgedAt = "2026-08-21"; :>> judgedBy = "claudeFable5"; }
    verification p1PavedWritePathStandupGate : Test { :>> id = "d6a393f6-0d56-40df-85ef-f8191cdc13c8"; :>> title = "Sprint 385 standup gate"; :>> createdAt = "2026-08-21"; :>> createdBy = "claudeFable5"; :>> method = VerificationMethod::inspect; :>> procedureText = "Approach: enforcement points live where they already fire - the tiers in hook pre-write, the matcher in hook pre-bash, the human-channel refusals INSIDE the write functions under the lock (no caller or transport can route around them), rules in the three gate surfaces that already exist. The never-exempt set is DERIVED from a declared table per d0178's own charter note, so apply-review and future judgment ops are covered without a hand list. Session-binding on the override is realized as single-use + path-bound + 900s TTL + consumed-by-session recorded, because a CLI cannot know the harness session a priori - stated in the code where the deviation lives."; }
    part p1PavedWritePathStandupGateR1 : TestResult { :>> id = "d0832f73-d221-4fc3-9459-e66e525c6253"; :>> outcome = VerdictKind::pass; :>> judgedAgainst = "894e394"; :>> judgedAt = "2026-08-21"; :>> judgedBy = "claudeFable5"; }
    verification p1PavedWritePathImplementGate : Test { :>> id = "64852bd8-1ac3-47b2-987a-e2a743dc0e6d"; :>> title = "Sprint 385 implement gate"; :>> createdAt = "2026-08-21"; :>> createdBy = "claudeFable5"; :>> method = VerificationMethod::test; :>> procedureText = "Every tier and branch RUN: strict scaffold - tier1 deny, tier2 ask, control-plane ask, override arm/consume/re-deny cycle with the obligation file read back; guided self-build - advisory lines for the same probes; the matcher probed with eleven commands including the quoted-prose negative; `keel accept` refused THIS session (agent markers, no TTY); rules --enforce clean over the real tree; the K6 write-layer refusals unit-tested (AI refused, unregistered refused, Person passes, method=test unaffected). Notable: the live accept-as-AI probe was SHADOWED by the channel layer refusing first - correct ordering, and the write layer got its own tests instead of a weaker live claim."; }
    part p1PavedWritePathImplementGateR1 : TestResult { :>> id = "10ddf2c3-ca6a-45a9-b420-eea937be5719"; :>> outcome = VerdictKind::pass; :>> judgedAgainst = "894e394"; :>> judgedAt = "2026-08-21"; :>> judgedBy = "claudeFable5"; }
    verification p1PavedWritePathReviewGate : Test { :>> id = "5aec4c09-a6e0-4172-9e05-8347c033228b"; :>> title = "Sprint 385 review gate — three passes per D0172"; :>> createdAt = "2026-08-21"; :>> createdBy = "claudeFable5"; :>> method = VerificationMethod::inspect; :>> procedureText = "PASS 1, CLAIMS vs computed/emitted: every verdict above is from a run or a test, none from reading; 220 tests, clippy 0 after twelve real findings (two severed doc comments, two indexing panics, a dead tokenizer arm). PASS 2, BOUNDARY: the override expires (TTL branch), misses on a different path (path-bound branch), and its obligation write failure degrades to the ledger with a printed sync obligation; an unresolvable actor skips the tracked red-yield record entirely rather than fabricating createdBy. PASS 3, OWN DIFF: the tokenizer's dead arm and a no-op push/pop pair were this sprint's own code, caught by clippy and removed. WHAT A REVIEWER SHOULD ATTACK: python-driven writes (io.open in a Bash-run script) bypass the Write|Edit matcher entirely - acknowledged in the proposal (friction, not proof; layer 3 is the guarantee) and visible in this very sprint's own workflow; the strict-profile Bash tier narrows it downstream, and the fire-ledger records what fires here."; }
    part p1PavedWritePathReviewGateR1 : TestResult { :>> id = "c2f5c356-1509-4487-be58-3f8136f965f7"; :>> outcome = VerdictKind::pass; :>> judgedAgainst = "894e394"; :>> judgedAt = "2026-08-21"; :>> judgedBy = "claudeFable5"; }
    verification p1PavedWritePathCloseOutGate : Test { :>> id = "4ae90e20-3495-4205-9ede-ae2c83982235"; :>> title = "Sprint 385 closeOut gate (autonomous, D0049)"; :>> createdAt = "2026-08-21"; :>> createdBy = "claudeFable5"; :>> method = VerificationMethod::inspect; :>> procedureText = "Autonomous closeOut (D0049). Seven p1 DoDs flipped at the judging HEAD; the self-build's adoption profile DECLARED (guided) with its rationale in the contract; sync-claude re-run so the shipped surface includes the control-plane patterns; CLAUDE.md and the CI workflow doc-synced in the same change. validate clean; 41 guards ALL PASS; 220 tests; clippy 0."; }
    part p1PavedWritePathCloseOutGateR1 : TestResult { :>> id = "22e8f2ce-3994-4311-b73c-ae15d2c9622d"; :>> outcome = VerdictKind::pass; :>> judgedAgainst = "894e394"; :>> judgedAt = "2026-08-21"; :>> judgedBy = "claudeFable5"; }
    verification p1PavedWritePathRetroGate : Test { :>> id = "16fe1a66-510a-4e9b-9d64-fe0357f7b5e3"; :>> title = "Sprint 385 retro gate (autonomous, D0049)"; :>> createdAt = "2026-08-21"; :>> createdBy = "claudeFable5"; :>> method = VerificationMethod::analyze; :>> procedureText = "Autonomous retro (D0049). AVOIDABLE-ISSUE SCAN under rcRecurrence: (1) doc-comment severing by insertion recurred (occurrence two THIS PROGRAM: dispositions in sprint 383, actor::resolve here) - per D0172 second-occurrence this now carries its preventing change: insertions above a documented item are made ABOVE the doc comment, stated as the mechanical rule; clippy's missing-errors-doc is the backstop that caught both. (2) The live-probe-shadowed-by-earlier-layer pattern (accept channel refusing before the write layer could be observed) is a first: the practice - when layers stack, each layer gets its own test at its own seam - is recorded here. WELL: (1) the channel control REFUSING ITS OWN AUTHOR is the strongest live evidence a control can produce; (2) deriving the never-exempt set from the declared table killed the hand-list drift class the panel flagged; (3) reading the accepted decision texts as the spec (not the proposal summary) caught scope the summary compressed away - the charter notes were implemented, not just the headlines. Estimate 13 pts, delivered."; }
    part p1PavedWritePathRetroGateR1 : TestResult { :>> id = "5c78d2ee-8c80-4f45-a0dc-23c33722803e"; :>> outcome = VerdictKind::pass; :>> judgedAgainst = "894e394"; :>> judgedAt = "2026-08-21"; :>> judgedBy = "claudeFable5"; }
}
