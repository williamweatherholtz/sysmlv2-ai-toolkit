// ProjectDeliveryS270 — Sprint 270: use case usages + flow are READ; parser-coverage reaches ZERO
// (issue102 constructs 2 and 6, issue104 recorded). EXECUTE. 3 pts.
package ProjectDeliveryS270 {
    private import EngineElement::*;
    private import EngineWork::*;
    private import EngineVerification::*;
    private import EngineRelationships::*;

    #CharteredBy dependency from readUseCaseFlowStory to d0139;

    part readUseCaseFlowStory : Story {
        :>> id = "0d800089-0814-6089-9b3e-000000300089";
        :>> title = "Sprint 270: read use case usages (56) + flow (18); parser-coverage 74 -> 0 (3 pts)";
        :>> createdAt = "2026-08-14"; :>> createdBy = "claudeOpus5"; :>> kind = WorkKind::code; :>> priority = WorkPriority::p0; :>> owner = "claudeOpus5"; :>> estimatedPoints = 3;
    }

    action def DeliveryRunS270 {
        action storyReadUseCaseFlow;
        verification storyReadUseCaseFlowDoD : Test { :>> id = "0d80008a-0814-608a-9b3e-00000030008a"; :>> method = VerificationMethod::test; :>> procedureText = "Covers dcParserReadUseCaseAndFlow. Constructs 2 and 6 of dcParserReadBase, taken together because both are statements PRESENT and unread; the remaining three (ref, assert/require constraint, ports/connect) have zero instances and are future capability rather than current blindness. USE CASE USAGES: skipped entirely, only `use case def` handled, so all 56 carried unchecked type references and unchecked enum literals and were absent from every view. Added `Item::UseCase(UseCaseUsage)` as its OWN variant rather than reusing Part — a use case is not a structural part — following the precedent Verification already sets, with registry type + attribute checking and Model ingestion. FLOW: all 18 sit inside `action def` workflow bodies; added `FlowEdge`, `ActionDef.flows`, and `parse_flow` matched on the IDENTIFIER `flow`, since promoting it to a keyword would change that word's behaviour everywhere for one construct's benefit. Dotted endpoints are kept whole; the Model takes the root, which is the granularity it actually has. VERIFIED, each measured: use case usage with an UNDECLARED type FAILS, declared PASSES, with attributes PASSES; `attribute def` still parses — a regression check that mattered, because an earlier patch of mine landed in the attribute arm by mistake and had to be reverted; `parser-coverage` 74 -> 18 -> 0, dropping by exactly 56 then exactly 18. EVERY STATEMENT IN THE MODEL IS NOW READ. clippy clean; 161 tests; validate + all 27 guards + check-engine green."; }
        part storyReadUseCaseFlowDoDR1 : TestResult { :>> id = "0d80008b-0814-608b-9b3e-00000030008b"; :>> outcome = VerdictKind::pass; :>> judgedAgainst = "dedc999"; :>> judgedAt = "2026-08-14"; :>> judgedBy = "claudeOpus5"; }
    }

    verification ufRefineGate : Test { :>> id = "0d80008c-0814-608c-9b3e-00000030008c"; :>> title = "Sprint 270 refine gate (DoR)"; :>> createdAt = "2026-08-14"; :>> createdBy = "claudeOpus5"; :>> method = VerificationMethod::inspect; :>> procedureText = "DoR: after `:>` landed, `parser-coverage` reported exactly two remaining kinds — 56 use case usages and 18 flows. Both present, both unread, both verifiable independently, so they belong in one sprint; the three constructs with zero instances do not, because 'reads a construct nothing uses' cannot be verified against the model. estimatedPoints=3. DoR met."; }
    part ufRefineGateR1 : TestResult { :>> id = "0d80008d-0814-608d-9b3e-00000030008d"; :>> outcome = VerdictKind::pass; :>> judgedAgainst = "dedc999"; :>> judgedAt = "2026-08-14"; :>> judgedBy = "claudeOpus5"; }

    verification ufStandupGate : Test { :>> id = "0d80008e-0814-608e-9b3e-00000030008e"; :>> title = "Sprint 270 standup gate"; :>> createdAt = "2026-08-14"; :>> createdBy = "claudeOpus5"; :>> method = VerificationMethod::inspect; :>> procedureText = "Approach: give the use case its own Item variant so the compiler enumerates every consumer needing an update — the tactic that worked in sprint 267 — and drive each construct to a measured drop in parser-coverage rather than to a subjective 'it parses now'. No blockers."; }
    part ufStandupGateR1 : TestResult { :>> id = "0d80008f-0814-608f-9b3e-00000030008f"; :>> outcome = VerdictKind::pass; :>> judgedAgainst = "dedc999"; :>> judgedAt = "2026-08-14"; :>> judgedBy = "claudeOpus5"; }

    verification ufImplementGate : Test { :>> id = "0d800090-0814-6090-9b3e-000000300090"; :>> title = "Sprint 270 implement gate"; :>> createdAt = "2026-08-14"; :>> createdBy = "claudeOpus5"; :>> method = VerificationMethod::test; :>> procedureText = "A real self-inflicted defect is recorded here because it nearly shipped silently. My first patch for the use-case arm was applied by a script using replace-first on a block that appears verbatim in the `attribute` arm EARLIER in the file, so the change landed in the wrong arm: `attribute` usages would have been parsed as use cases, and `use case` usages stayed skipped. Nothing failed — the repo still validated clean, because package-level `attribute` usages do not occur here. It was caught only because the VERIFICATION showed no change: the undeclared-type case still passed and parser-coverage still reported 74. A test that asserts an EFFECT rather than an absence of errors is what made a silent misplacement visible."; }
    part ufImplementGateR1 : TestResult { :>> id = "0d800091-0814-6091-9b3e-000000300091"; :>> outcome = VerdictKind::pass; :>> judgedAgainst = "dedc999"; :>> judgedAt = "2026-08-14"; :>> judgedBy = "claudeOpus5"; }

    verification ufReviewGate : Test { :>> id = "0d800092-0814-6092-9b3e-000000300092"; :>> title = "Sprint 270 review gate"; :>> createdAt = "2026-08-14"; :>> createdBy = "claudeOpus5"; :>> method = VerificationMethod::inspect; :>> procedureText = "Reviewed. parser-coverage at ZERO is a genuine milestone — every statement in the model is now read, which is the precondition the whole base-first pass was blocked on. But it must not be overstated: zero means nothing is SKIPPED, not that everything is fully MODELLED. Two limits are recorded rather than glossed. First, flow endpoints are dotted feature paths and the Model resolves only their root, because feature-level resolution does not exist. Second, and found while verifying this sprint, `.engine/workflows` is not in the Model's source directories at all (issue104), so the flow edges have nowhere to land yet — the emission is correct and unexercised, and that is stated in the Issue so nobody later reads it as dead code."; }
    part ufReviewGateR1 : TestResult { :>> id = "0d800093-0814-6093-9b3e-000000300093"; :>> outcome = VerdictKind::pass; :>> judgedAgainst = "dedc999"; :>> judgedAt = "2026-08-14"; :>> judgedBy = "claudeOpus5"; }

    verification ufCloseOutGate : Test { :>> id = "0d800094-0814-6094-9b3e-000000300094"; :>> title = "Sprint 270 closeOut gate (autonomous, D0049)"; :>> createdAt = "2026-08-14"; :>> createdBy = "claudeOpus5"; :>> method = VerificationMethod::inspect; :>> procedureText = "Autonomous closeOut (D0049). dcParserReadUseCaseAndFlow carries a passing DoD TestResult. parser-coverage reports 0 across 475 files. issue104 recorded with dcModelIngestWorkflows as its resolver, deliberately NOT folded into this sprint: adding a directory to the Model changes what every guard evaluates at once, and mixing that blast radius into a parser sprint would defeat the point of making the parser trustworthy. dcParserReadBase remains OUTSTANDING for the three zero-instance constructs. clippy clean; 161 tests; validate + all 27 guards + check-engine green. No gate bypassed."; }
    part ufCloseOutGateR1 : TestResult { :>> id = "0d800095-0814-6095-9b3e-000000300095"; :>> outcome = VerdictKind::pass; :>> judgedAgainst = "dedc999"; :>> judgedAt = "2026-08-14"; :>> judgedBy = "claudeOpus5"; }

    verification ufRetroGate : Test { :>> id = "0d800096-0814-6096-9b3e-000000300096"; :>> title = "Sprint 270 retro gate (autonomous, D0049)"; :>> createdAt = "2026-08-14"; :>> createdBy = "claudeOpus5"; :>> method = VerificationMethod::analyze; :>> procedureText = "Autonomous retro (D0049) under D0131's retroTrack. WELL: (1) driving each construct to a MEASURED drop in parser-coverage (74 -> 18 -> 0, by exactly 56 then exactly 18) turned 'it parses now' into an arithmetic check, and it is what caught the misplaced patch; (2) the use case got its own Item variant, so the compiler enumerated the consumer needing an update rather than leaving a silent gap; (3) issue104 was recorded and NOT fixed, keeping a large blast radius out of a sprint whose purpose was trustworthiness. AVOIDABLE-ISSUE 1: a replace-first script patched the WRONG match arm because the target block appears verbatim earlier in the file, and nothing failed — the repo validated clean, since package-level `attribute` usages do not occur here. This is the THIRD regex-patching failure this sitting (sprint 265 anchor mismatch, sprint 268 unicode crash, now a silent misplacement) and it is the worst of the three, because the other two announced themselves. NO NEW ITEM, reason stated: the existing guidance is to use the Edit tool with exact surrounding text on source files, and the two prior retros already recorded it; what this instance adds is that replace-first on a NON-UNIQUE block fails SILENTLY, so the rule is not 'prefer Edit' but 'never patch by a pattern you have not confirmed is unique'. AVOIDABLE-ISSUE 2: I emitted flow edges into the Model before checking whether the Model ingests the directory those flows live in, so the emission is currently unexercised. NO NEW ITEM: tracked as issue104's resolver, and the emission is correct rather than wrong — but the ordering was backwards, and checking the consumer before writing the producer would have surfaced issue104 first. Estimate 3 pts, delivered."; }
    part ufRetroGateR1 : TestResult { :>> id = "0d800097-0814-6097-9b3e-000000300097"; :>> outcome = VerdictKind::pass; :>> judgedAgainst = "dedc999"; :>> judgedAt = "2026-08-14"; :>> judgedBy = "claudeOpus5"; }
}
