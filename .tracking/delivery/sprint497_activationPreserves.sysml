// ProjectDeliveryS497 — Sprint 497: activate/deactivate edit the manifest instead of regenerating it, so no fact is lost. EXECUTE. 3 pts.
package ProjectDeliveryS497 {
    private import EngineElement::*;
    private import EngineWork::*;
    private import EngineVerification::*;
    private import EngineRelationships::*;

    #CharteredBy dependency from activationPreservesStory to d0164;

    part activationPreservesStory : Story {
        :>> id = "c703c8f7-7f80-480b-af38-1c629259da9c";
        :>> title = "Sprint 497: activation writes preserve every fact they do not intend to change (3 pts)";
        :>> createdAt = "2026-08-30"; :>> createdBy = "claudeOpus5"; :>> kind = WorkKind::code; :>> priority = WorkPriority::p0; :>> owner = "claudeOpus5"; :>> estimatedPoints = 3;
    }

    action def DeliveryRunS497 {
        action storyActivationPreserves;
        verification storyActivationPreservesDoD : Test { :>> id = "a060ccba-043f-4cef-aeb0-55412a7c5439"; :>> method = VerificationMethod::test; :>> procedureText = "Resolves issue293. TWO defects, one write path. (1) write_activation REGENERATED activation.toml from a header template, deleting charteredBy = d0226 and the comment explaining it (the D0225 charter - a set without a charter is a collection of switches nobody can account for). Fixed: replace_active_line rewrites ONLY the `active = [...]` line inside the named section, preserving comments, charteredBy, blank lines, ordering and line endings; only a MISSING or unparseable manifest falls through to the template. (2) The process list was rebuilt from unit_names(), which knows only SWITCHABLE processes, so decision-authoring ([always], asserts no guard) vanished on every write - and omission from a PRESENT list marks a process INACTIVE (D0138/D0164), so the writer deactivated it by silence. Fixed: recorded_active reads the list the file RECORDS and uses it as the base; both the process branch and the viewpoint branch now do so. VERIFY: TDD RED first, 4/4 failing with both losses reproduced verbatim, then GREEN 4/4; a LIVE round trip on this repository's own keystone-locked file leaves git diff EMPTY; clippy -D warnings clean; workspace suite 0 FAILED.: DELIVERED BACKLOG ITEMS: <items>. <what done means, verified how>."; }
        // RAN: // RAN: activation_round_trip_loses_nothing RED 4/4 then GREEN 4/4; live deactivate+activate on this repo leaves git diff EMPTY on the keystone-locked file; clippy clean; workspace 0 FAILED
        part storyActivationPreservesDoDR1 : TestResult { :>> id = "867cc694-2292-4cdb-bf3c-0bbdcf0276fa"; :>> outcome = VerdictKind::pass; :>> judgedAgainst = "761e2e2"; :>> judgedAt = "2026-08-30"; :>> judgedBy = "claudeOpus5"; }
    }

    verification activationPreservesRefineGate : Test { :>> id = "acbe83e3-a438-477d-b08a-3fae4d0aa704"; :>> title = "Sprint 497 refine gate (DoR)"; :>> createdAt = "2026-08-30"; :>> createdBy = "claudeOpus5"; :>> method = VerificationMethod::inspect; :>> procedureText = "READY: the DoD named both losses and their measurement precisely (authored when the issue was raised), so the scope was to make the named claims true, not to redesign activation. Bounded by what it excludes: no change to what activation MEANS, no schema change, no change to activation.toml's contents - the file is byte-identical after this sprint."; }
    verification activationPreservesStandupGate : Test { :>> id = "569743b1-9954-403c-8a9a-ad7da383ee75"; :>> title = "Sprint 497 standup gate"; :>> createdAt = "2026-08-30"; :>> createdBy = "claudeOpus5"; :>> method = VerificationMethod::inspect; :>> procedureText = "No blocker. The dependency worth naming is that this write path fights its OWN control: activation.toml is under the keystone lock, so before this fix any legitimate `keel activate` either lost facts or demanded a signed Decision to re-add them. That is why the live round-trip-produces-empty-git-diff check is the sprint's strongest evidence - it proves the write path and its guard now agree."; }
    verification activationPreservesImplementGate : Test { :>> id = "05fd7866-473e-43eb-94e3-4ff8ced74396"; :>> title = "Sprint 497 implement gate"; :>> createdAt = "2026-08-30"; :>> createdBy = "claudeOpus5"; :>> method = VerificationMethod::test; :>> procedureText = "RAN, RED FIRST: cargo test --test activation_round_trip_loses_nothing -> 4 FAILED before any source change, with the diff showing exactly the two documented losses (charteredBy plus its comment gone; decision-authoring missing from the list). Then GREEN 4/4. LIVE: keel deactivate knowledge-graph-memory && keel activate knowledge-graph-memory on this repository -> git diff --stat on .engine/contracts/activation.toml is EMPTY. keel activation still reports decision-authoring [always] and the charter present. clippy -D warnings clean (one push_str/format! lint fixed, not suppressed). cargo test --workspace --release -> 0 FAILED."; }
    verification activationPreservesReviewGate : Test { :>> id = "84d1ddd2-9ed1-46b8-a9b3-a4dd776ac2f6"; :>> title = "Sprint 497 review gate — three passes per D0172"; :>> createdAt = "2026-08-30"; :>> createdBy = "claudeOpus5"; :>> method = VerificationMethod::inspect; :>> procedureText = "THREE PASSES. (1) DOES PRESERVATION BECOME PARALYSIS: a fourth test asserts the target process is ACTUALLY removed and that the file differs ONLY where that process was - a writer that preserves by doing nothing would pass the first three tests and fail this one. (2) IS THE FALLBACK STILL CORRECT: only a missing or unparseable manifest regenerates from the template, which is the materialising path a project with no manifest needs; replace_active_line returns None rather than writing a manifest with a section missing, because an absent section means EVERYTHING ACTIVE and a partial write of a contract whose absence has meaning is data loss. (3) SYMMETRY: the viewpoint branch rewrites the process section too, so switching a viewpoint cannot drop an [always] process - the same defect through the other door, fixed in the same commit rather than left for a second discovery."; }
    verification activationPreservesCloseOutGate : Test { :>> id = "3bf30726-b1a6-437a-858d-c4f87c596cbe"; :>> title = "Sprint 497 closeOut gate (autonomous, D0049)"; :>> createdAt = "2026-08-30"; :>> createdBy = "claudeOpus5"; :>> method = VerificationMethod::inspect; :>> procedureText = "CLOSED. issue293 resolves. The write path and the keystone lock now agree: a legitimate activation change produces a one-line diff, not a rewritten file demanding a Decision to restore what it deleted."; }
    verification activationPreservesRetroGate : Test { :>> id = "529154f6-b1ee-4dc7-867e-35dcf4012221"; :>> title = "Sprint 497 retro gate (autonomous, D0049)"; :>> createdAt = "2026-08-30"; :>> createdBy = "claudeOpus5"; :>> method = VerificationMethod::analyze; :>> procedureText = "FINDING: nothing DETECTED either loss - the keystone lock caught the FILE changing, and only because the file happens to be locked. A write path whose only audit is the control guarding its output is unaudited for every output that is not locked. The general form is regenerate-from-model writers: any command that rebuilds a human-edited file from the engine's view of it will silently drop whatever the engine's view cannot represent, which here was comments, a charter reference, and the entire category of non-switchable processes. BECOMES TRACKED WORK rather than a note: an audit of the other writers that regenerate a file a human may have edited (sync-claude is the obvious next one - it already merges user entries, which is the correct shape, and is worth confirming by test rather than by reading). Filed as an issue with this sprint as its evidence."; }
}
