// ProjectDeliveryS670 — Sprint 670: keel land refused the push of fe715c2 on self_build_hooks_leave_the_build_tree after the verifier's run of the same set at the same HEAD had passed: the still-linking fixture set its mtime to now and asserted the hook did not copy it, which holds only while the spawned hook reaches its two-second grace check inside two wall-clock seconds. Under the land's load it did not. The fixture stops racing the clock so the touched run judges the change and not the host's speed (issue481).. EXECUTE. 1 pts.
package ProjectDeliveryS670 {
    private import EngineElement::*;
    private import EngineWork::*;
    private import EngineVerification::*;
    private import EngineRelationships::*;

    #CharteredBy dependency from hookTestDoesNotRaceTheClockStory to d0391;

    part hookTestDoesNotRaceTheClockStory : Story {
        :>> id = "c3faefcf-0d07-4655-9310-489b0708954c";
        :>> title = "Sprint 670: keel land refused the push of fe715c2 on self_build_hooks_leave_the_build_tree after the verifier's run of the same set at the same HEAD had passed: the still-linking fixture set its mtime to now and asserted the hook did not copy it, which holds only while the spawned hook reaches its two-second grace check inside two wall-clock seconds. Under the land's load it did not. The fixture stops racing the clock so the touched run judges the change and not the host's speed (issue481). (1 pts)";
        :>> createdAt = "2026-09-11"; :>> createdBy = "claudeOpus5"; :>> kind = WorkKind::code; :>> priority = WorkPriority::p0; :>> owner = "claudeOpus5"; :>> estimatedPoints = 1;
    }

    action def DeliveryRunS670 {
        action storyHookTestDoesNotRaceTheClock;
        verification storyHookTestDoesNotRaceTheClockDoD : Test { :>> id = "f99d6d1f-ade6-4338-ba9a-648ae65a65c4"; :>> method = VerificationMethod::test; :>> procedureText = "an_output_still_linking_is_not_copied gives the fixture an mtime the grace cannot age past during the run (now plus 600 s, where needs_refresh's saturating subtraction reads 0), with a comment naming issue481; no integration test under keel-cli/tests sets a fixture mtime to SystemTime::now() and then asserts a grace-window decision; cargo test --release --test self_build_hooks_leave_the_build_tree passes 5 of 5 idle and under CPU load."; }
        // RAN: verifier receipt 481: cargo test --release --test self_build_hooks_leave_the_build_tree test result: ok. 5 passed; 0 failed exit 0; cargo clippy -D warnings exit 0; D0388 pair: negative touched-1789122462.log line 1003 pre-fix FAILED under land load, positive patched binary 5 of 5 with 41 CPU burners live; validate 763 clean exit 0; guard ALL PASS exit 0; DISCREPANCIES: NONE
        part storyHookTestDoesNotRaceTheClockDoDR1 : TestResult { :>> id = "c18e319d-74ba-452f-bccc-91f69fc05376"; :>> outcome = VerdictKind::pass; :>> judgedAgainst = "fe715c2"; :>> judgedAt = "2026-09-11"; :>> judgedBy = "claudeOpus5"; }
    }

    verification hookTestDoesNotRaceTheClockRefineGate : Test { :>> id = "77a6487d-b34d-47b9-9af5-5195a5d15161"; :>> title = "Sprint 670 refine gate (DoR)"; :>> createdAt = "2026-09-11"; :>> createdBy = "claudeOpus5"; :>> method = VerificationMethod::inspect; :>> procedureText = "Chartered by D0391 (the test is that Decision's control). 1 point: one fixture line, one Issue, one resolver. Not a process change: no guard, hook, workflow or contract moves; the engine's grace rule in hook_binary.rs is untouched and its boundary remains covered by the pure needs_refresh unit test."; }
    // RAN: verifier receipt 481 2026-09-11 head=fe715c2: chartered by d0391; 1 point; validate 763 tracking file(s) validated clean exit 0
    part hookTestDoesNotRaceTheClockRefineGateR1 : TestResult { :>> id = "c4db319b-2e8a-4fa2-868a-57982ae81932"; :>> outcome = VerdictKind::proposed; :>> judgedAgainst = "fe715c2"; :>> judgedAt = "2026-09-11"; :>> judgedBy = "claudeOpus5"; }
    verification hookTestDoesNotRaceTheClockStandupGate : Test { :>> id = "4182669c-ae05-42e3-bf5f-83e3fbd01dbf"; :>> title = "Sprint 670 standup gate"; :>> createdAt = "2026-09-11"; :>> createdBy = "claudeOpus5"; :>> method = VerificationMethod::inspect; :>> procedureText = "Order: read the land log for the failing assertion (touched-1789122462.log line 1003), read hook_binary.rs for the grace (two seconds), read the test (mtime = now), then patch the fixture through textpatch, then Issue + resolver through the write API, then verify idle and under load. Blocker: none. Note for the record: a grep -c for a carriage return under this shell reported 144 on an LF file; the byte count (python, CRLF 0 LF 144) was the check that held."; }
    // RAN: verifier receipt 481: tree=3 dirty paths (backlog.sysml, issues-claudeOpus5.sysml, self_build_hooks_leave_the_build_tree.rs); grep now()-mtime fixtures 0; fixture from_secs(600) yes, issue481 named yes
    part hookTestDoesNotRaceTheClockStandupGateR1 : TestResult { :>> id = "3dc3e531-9d29-400b-aacc-41d570f13b51"; :>> outcome = VerdictKind::proposed; :>> judgedAgainst = "fe715c2"; :>> judgedAt = "2026-09-11"; :>> judgedBy = "claudeOpus5"; }
    verification hookTestDoesNotRaceTheClockImplementGate : Test { :>> id = "4f8030bf-8d00-47b6-80c5-98e3353fdeb7"; :>> title = "Sprint 670 implement gate"; :>> createdAt = "2026-09-11"; :>> createdBy = "claudeOpus5"; :>> method = VerificationMethod::test; :>> procedureText = "keel-cli/tests/self_build_hooks_leave_the_build_tree.rs: the fixture's set_modified takes now + Duration::from_secs(600) with a comment naming issue481 and why. .tracking/issues-claudeOpus5.sysml: issue481 (in-field: the refusal fell on a real push). .tracking/backlog.sysml: dcSelfBuildHookTestDoesNotRaceTheClock with its DoD and the #Resolves edge to issue481."; }
    // RAN: verifier receipt 481: cargo test --release --test self_build_hooks_leave_the_build_tree test result: ok. 5 passed; 0 failed exit 0; cargo clippy -D warnings exit 0; D0388 pair: negative touched-1789122462.log line 1003 pre-fix FAILED under land load, positive patched binary 5 of 5 with 41 CPU burners live
    part hookTestDoesNotRaceTheClockImplementGateR1 : TestResult { :>> id = "aee5003b-d1d5-4291-8b11-5c9b51f57ddc"; :>> outcome = VerdictKind::pass; :>> judgedAgainst = "fe715c2"; :>> judgedAt = "2026-09-11"; :>> judgedBy = "claudeOpus5"; }
    verification hookTestDoesNotRaceTheClockReviewGate : Test { :>> id = "74556c21-a45b-4ce6-baa1-a620a55c8076"; :>> title = "Sprint 670 review gate — three passes per D0172"; :>> createdAt = "2026-09-11"; :>> createdBy = "claudeOpus5"; :>> method = VerificationMethod::inspect; :>> procedureText = "Delivered: the touched run's verdict on this file now depends on the engine's decision, not on scheduling. D0388 pair: negative = the land's own log, the pre-fix fixture failing under load; positive = the patched binary 5 of 5 with 41 CPU burners live at start (verifier receipt 481: 5 passed, 0 failed idle; validate 763 clean; guard ALL PASS; clippy -D warnings exit 0). Residual: the grace itself (two seconds) is unchanged and unmeasured against a real link's duration; that is D0391's residual, not this sprint's."; }
    // RAN: verifier receipt 481: check-engine clean exit 0; sync-claude --check matches (46 registry skills) exit 0; guard ALL PASS 38 actionable warnings across 7 guards exit 0
    part hookTestDoesNotRaceTheClockReviewGateR1 : TestResult { :>> id = "3747aca2-a1be-4a9a-bb22-26764b2bda88"; :>> outcome = VerdictKind::proposed; :>> judgedAgainst = "fe715c2"; :>> judgedAt = "2026-09-11"; :>> judgedBy = "claudeOpus5"; }
    verification hookTestDoesNotRaceTheClockCloseOutGate : Test { :>> id = "863e2866-d5d6-4c09-9d02-c1e6e4467e1c"; :>> title = "Sprint 670 closeOut gate (autonomous, D0049)"; :>> createdAt = "2026-09-11"; :>> createdBy = "claudeOpus5"; :>> method = VerificationMethod::inspect; :>> procedureText = "Sprint 670 closes on verifier receipt 481 only (D0425). dcSelfBuildHookTestDoesNotRaceTheClock carries its DoD result; issue481 resolves through it. fe715c2 and this commit push together once the land's touched run passes."; }
    // RAN: verifier receipt 481: DISCREPANCIES: NONE; OWED WRITES: NONE; dcSelfBuildHookTestDoesNotRaceTheClock DoD result recorded from the same receipt, issue481 resolves through it
    part hookTestDoesNotRaceTheClockCloseOutGateR1 : TestResult { :>> id = "7c670ecb-0e01-464e-9186-6c52238a080c"; :>> outcome = VerdictKind::proposed; :>> judgedAgainst = "fe715c2"; :>> judgedAt = "2026-09-11"; :>> judgedBy = "claudeOpus5"; }
    verification hookTestDoesNotRaceTheClockRetroGate : Test { :>> id = "542ae2dc-a40d-4616-944d-a6e18554a9a8"; :>> title = "Sprint 670 retro gate (autonomous, D0049)"; :>> createdAt = "2026-09-11"; :>> createdBy = "claudeOpus5"; :>> method = VerificationMethod::analyze; :>> procedureText = "AVOIDABLE-ISSUE SCAN: issue481 is this sprint's own subject and was avoidable at authoring time - a fixture that asserts a grace-window decision against the wall clock is a race by construction; the grep in the DoD (no set_modified(SystemTime::now()) under keel-cli/tests) is the check that finds the next one, and the fixture comment says why. FINDING (kept as a fact, no new item): the same set passed 731 of 731 in the verifier's run and failed 730 of 731 in the land's run twelve minutes later at the same HEAD - the two runs differ in load, not in code, which is the D0421 cost the human weighed when D0356 withdrew the suite gate; the count of such refusals is readable from the touched receipts and needs no new sensor. No other finding."; }
    // RAN: verifier receipt 481: no new Issue beyond issue481 (the subject); the load-vs-code finding kept as a fact, touched receipts carry the count; guard ALL PASS exit 0
    part hookTestDoesNotRaceTheClockRetroGateR1 : TestResult { :>> id = "51879d58-657b-4435-aed0-954b839aa566"; :>> outcome = VerdictKind::proposed; :>> judgedAgainst = "fe715c2"; :>> judgedAt = "2026-09-11"; :>> judgedBy = "claudeOpus5"; }
}
