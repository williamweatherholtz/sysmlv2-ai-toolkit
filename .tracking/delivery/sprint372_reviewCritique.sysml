// ProjectDeliveryS372 — Sprint 372: reviews critique, retros produce items, and the deck's async
// feedback stops destroying its own saves. First sprint run UNDER the new process. EXECUTE. 5 pts.
package ProjectDeliveryS372 {
    private import EngineElement::*;
    private import EngineWork::*;
    private import EngineVerification::*;
    private import EngineRelationships::*;

    #CharteredBy dependency from reviewCritiqueStory to d0172;

    part reviewCritiqueStory : Story {
        :>> id = "0d8006f0-0814-66f0-9b3e-0000003006f0";
        :>> title = "Sprint 372: the review-critique process, and deck v3 — async feedback isolated from the sync region (5 pts)";
        :>> createdAt = "2026-08-20"; :>> createdBy = "claudeOpus5"; :>> kind = WorkKind::code; :>> priority = WorkPriority::p0; :>> owner = "claudeOpus5"; :>> estimatedPoints = 5;
    }

    action def DeliveryRunS372 {
        action storyReviewCritique;
        verification storyReviewCritiqueDoD : Test { :>> id = "0d8006f1-0814-66f1-9b3e-0000003006f1"; :>> method = VerificationMethod::test; :>> procedureText = "DELIVERED BACKLOG ITEMS: dcAuthorViaWriteTool declared, dcRetroGuardTiesFinding declared; addresses us014/us015 under D0172. TWO DELIVERABLES. (A) THE PROCESS: review-critique.sysml, deployed by BOTH ceremony skills - three named critique passes per review (claims vs computed/emitted, boundary on a copy, the sprint's own diff), review findings become items before the gate closes, and a SECOND-OCCURRENCE retro finding becomes a tracked item or carries a recorded reason. Founded on measured evidence: the shell-authoring failure class appears in FIVE retros with zero items, because the retro-backlog guard is satisfied by ANY co-staged item (issue189). Catalogue 20 to 21 processes, process-skill PASS at 21. (B) DECK v3: their report - press but no latch - was the async half of issue188. The tap path was clean; confirmSaved's PROMISE CALLBACKS wrote sv.textContent, an async script write to the synced region, so the runtime cut the region and REVERTED the tap being confirmed. All async feedback now goes to data-local attributes rendered by CSS attr() or the artifact-local event log; the verdict is re-asserted inside sync(fn) where attribution is explicit; a 1.2s readback says REVERTED on the card if the write moved. VERIFIED FROM THE EMITTED HTML: zero async synced-DOM writes, marker last, v3 stamp. Their FAIL is recorded as R2 on dcDeckButtonsLive and the demo confirmation remains theirs. validate 404 clean; check-engine clean; 38 guards ALL PASS."; }
        part storyReviewCritiqueDoDR1 : TestResult { :>> id = "0d8006f2-0814-66f2-9b3e-0000003006f2"; :>> outcome = VerdictKind::pass; :>> judgedAgainst = "46806bd"; :>> judgedAt = "2026-08-20"; :>> judgedBy = "claudeOpus5"; }
    }

    verification rvRefineGate : Test { :>> id = "0d8006f3-0814-66f3-9b3e-0000003006f3"; :>> title = "Sprint 372 refine gate (DoR)"; :>> createdAt = "2026-08-20"; :>> createdBy = "claudeOpus5"; :>> method = VerificationMethod::inspect; :>> procedureText = "DoR. Their statement carried two parts and both are worked here: the process ask (us014) and the latch bug (us015). THE ANSWER TO THEIR QUESTION CAME FROM THE GUARD'S SOURCE, NOT FROM MY MEMORY: retro_backlog_warnings returns empty when the commit stages ANY tracked item, so the honest answer was NO with a mechanism, not a reassurance. Their word `two` read as `too`; `the 3 critique pass` read as the three-pass shape the hardening series used, since that is the referent in context. estimatedPoints=5."; }
    part rvRefineGateR1 : TestResult { :>> id = "0d8006f4-0814-66f4-9b3e-0000003006f4"; :>> outcome = VerdictKind::pass; :>> judgedAgainst = "46806bd"; :>> judgedAt = "2026-08-20"; :>> judgedBy = "claudeOpus5"; }

    verification rvStandupGate : Test { :>> id = "0d8006f5-0814-66f5-9b3e-0000003006f5"; :>> title = "Sprint 372 standup gate"; :>> createdAt = "2026-08-20"; :>> createdBy = "claudeOpus5"; :>> method = VerificationMethod::inspect; :>> procedureText = "Approach for the bug: read the ASYNC path, since their correction ruled the tap path in (`they press`) and the latch out. The mechanism fell out in one reading: synchronous gesture writes are the save, async script writes cut the region, and confirmSaved did the second three lines after the first. Approach for the process: name the passes the hardening series actually ran, because that series found sixteen defects and the ceremony it bypassed found none. No blockers."; }
    part rvStandupGateR1 : TestResult { :>> id = "0d8006f6-0814-66f6-9b3e-0000003006f6"; :>> outcome = VerdictKind::pass; :>> judgedAgainst = "46806bd"; :>> judgedAt = "2026-08-20"; :>> judgedBy = "claudeOpus5"; }

    verification rvImplementGate : Test { :>> id = "0d8006f7-0814-66f7-9b3e-0000003006f7"; :>> title = "Sprint 372 implement gate"; :>> createdAt = "2026-08-20"; :>> createdBy = "claudeOpus5"; :>> method = VerificationMethod::test; :>> procedureText = "THE IRONY IS THE FINDING: the feedback mechanism built to CONFIRM saves was DESTROYING them. issue188 round 1 removed the load-time write and I verified eight properties of the emitted HTML - and the eight properties did not include `no async write into the synced region`, because I had not yet understood that the rule covers promise callbacks. Round 2's invariant is mechanical and now part of the skill's pass-4 checklist: no .then/.catch/setTimeout body assigns textContent or innerHTML outside the artifact-local panel, counted in the emitted HTML. THE VERIFIER CAUGHT MY FIX BEING INCOMPLETE: first count after the patch was ONE remaining offender - the copy dialog's `Copied` label, set from the clipboard promise - which I would have shipped again. THE DEBUG PANEL is an artifact-local element, exempt from sync entirely, so the next field report can name the failing STEP: it logs sync rejections with codes, window.onerror, region-off events, and readback reverts."; }
    part rvImplementGateR1 : TestResult { :>> id = "0d8006f8-0814-66f8-9b3e-0000003006f8"; :>> outcome = VerdictKind::pass; :>> judgedAgainst = "46806bd"; :>> judgedAt = "2026-08-20"; :>> judgedBy = "claudeOpus5"; }

    verification rvReviewGate : Test { :>> id = "0d8006f9-0814-66f9-9b3e-0000003006f9"; :>> title = "Sprint 372 review gate — THREE PASSES, per the process this sprint ships"; :>> createdAt = "2026-08-20"; :>> createdBy = "claudeOpus5"; :>> method = VerificationMethod::inspect; :>> procedureText = "PASS 1, CLAIMS vs the emitted artifact: zero async synced-DOM writes (counted over every .then/.catch/setTimeout body), marker last, v3 stamp present, sv rendered by attr(), artifact-local panel present - all checked in the OUTPUT, none asserted from the generator. PASS 2, BOUNDARY: the generator was re-run against the live tree and parses; the emitted page carries the copy fallback for the unwritable-view case; the readback covers the revert case the runtime could still produce; checked-clean beyond that - a phone tap is not exercisable from here, which is pass 2's stated limit. PASS 3, THE SPRINT'S OWN DIFF: found ONE defect in this sprint's own work before commit - the copy dialog's async `Copied` label, the exact class being fixed, introduced by the very fix - and the counter caught it because the invariant was mechanical. WHAT A REVIEWER SHOULD ATTACK: I diagnosed the latch failure from the contract's text, not from reproducing it; if the true cause is something else, v3's event log is the instrument that will say so, and that is the honest reason it exists. THE DEMO STAYS THEIRS: R2 on dcDeckButtonsLive is their FAIL, recorded; only their tap can produce the pass."; }
    part rvReviewGateR1 : TestResult { :>> id = "0d8006fa-0814-66fa-9b3e-0000003006fa"; :>> outcome = VerdictKind::pass; :>> judgedAgainst = "46806bd"; :>> judgedAt = "2026-08-20"; :>> judgedBy = "claudeOpus5"; }

    verification rvCloseOutGate : Test { :>> id = "0d8006fb-0814-66fb-9b3e-0000003006fb"; :>> title = "Sprint 372 closeOut gate (autonomous, D0049)"; :>> createdAt = "2026-08-20"; :>> createdBy = "claudeOpus5"; :>> method = VerificationMethod::inspect; :>> procedureText = "Autonomous closeOut (D0049). D0172 PROPOSED; the process is live for this sprint's own ceremony regardless, because running it is not a schema change. issue189 recorded with resolver dcRetroGuardTiesFinding; dcAuthorViaWriteTool declared as the item five retros owed; deck v3 republished to the same URL; their FAIL on the buttons recorded as R2 rather than papered over. validate 404 clean; check-engine clean; 38 guards ALL PASS; 21 processes all with deploying skills."; }
    part rvCloseOutGateR1 : TestResult { :>> id = "0d8006fc-0814-66fc-9b3e-0000003006fc"; :>> outcome = VerdictKind::pass; :>> judgedAgainst = "46806bd"; :>> judgedAt = "2026-08-20"; :>> judgedBy = "claudeOpus5"; }

    verification rvRetroGate : Test { :>> id = "0d8006fd-0814-66fd-9b3e-0000003006fd"; :>> title = "Sprint 372 retro gate (autonomous, D0049) — first retro under rcRecurrence"; :>> createdAt = "2026-08-20"; :>> createdBy = "claudeOpus5"; :>> method = VerificationMethod::analyze; :>> procedureText = "Autonomous retro (D0049), running rcRecurrence for the first time. THE RECURRENCE CHECK, APPLIED: this sprint's near-miss - the copy dialog's async label, caught by the counter - is occurrence TWO of `async feedback into synced DOM` (occurrence one shipped in round 1 and reached the human). Under the new rule that makes it an ITEM, and it is: the invariant is in the skill as rule 6 with a mechanical check, and the emitted-HTML counter is the control. THE SHELL-AUTHORING CLASS, occurrence six, FINALLY became dcAuthorViaWriteTool - the item five retros owed - and this retro cites it instead of re-describing it, which is what rcRecurrence is for. WELL: (1) their correction narrowed the bug and the narrowing was used - the tap path was ruled in by their words before any code was read; (2) the counter caught my fix reintroducing the class it fixed; (3) the process was applied to its own delivery sprint, three passes named in the review gate above; (4) the answer to their retro question came from the guard's source with a mechanism, not from memory with a reassurance. AVOIDABLE-ISSUE, occurrence one, watch for recurrence: I verified round 1 with a checklist that lacked the property that mattered, because the checklist was written from what I understood rather than from the contract's full rule - the fix for a rule violation must quote THE RULE, not my paraphrase of it. Estimate 5 pts, delivered."; }
    part rvRetroGateR1 : TestResult { :>> id = "0d8006fe-0814-66fe-9b3e-0000003006fe"; :>> outcome = VerdictKind::pass; :>> judgedAgainst = "46806bd"; :>> judgedAt = "2026-08-20"; :>> judgedBy = "claudeOpus5"; }
}
