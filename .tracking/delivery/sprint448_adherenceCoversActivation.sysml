// ProjectDeliveryS448 — Sprint 448: the enforcement signature covers EFFECTIVE guard state, so capturing or deactivating a guard is a detected weakening (issue242, D0213). EXECUTE. 2 pts.
package ProjectDeliveryS448 {
    private import EngineElement::*;
    private import EngineWork::*;
    private import EngineVerification::*;
    private import EngineRelationships::*;

    #CharteredBy dependency from adherenceCoversActivationStory to d0213;

    part adherenceCoversActivationStory : Story {
        :>> id = "8f843ee4-d78d-497b-b431-2880fde60f40";
        :>> title = "Sprint 448: the gate can now see the two ways a control gets disarmed (2 pts)";
        :>> createdAt = "2026-08-24"; :>> createdBy = "claudeFable5"; :>> kind = WorkKind::code; :>> priority = WorkPriority::p0; :>> owner = "claudeFable5"; :>> estimatedPoints = 2;
    }

    action def DeliveryRunS448 {
        action storyAdherenceCoversActivation;
        verification storyAdherenceCoversActivationDoD : Test { :>> id = "ae52aa5a-afd4-4583-b0c4-0e321501134e"; :>> method = VerificationMethod::test; :>> procedureText = "DELIVERED: dcAdherenceCoversActivation (resolves issue242, HIGH). THE DEFECT: audit-adherence, the D0209 clause-1 gate built the same morning for the issue236 self-modification class, read only .engine/rules/ trees - so two routes disarmed a control entirely invisibly to it. (a) CAPTURE: adding one `assert constraint <x> : <guardName>;` line to a guard-less process file converts a CORE, never-deactivatable guard into that process's switchable property, because guard_state returns Core only while NO unit claims the guard; the panel's operations lens reproduced it live, turning core stale-gate-prose into [INACTIVE] report whose run became 'PASS - 0 scanned, 1 warning' - and the CLI's own deactivate refusal ADVISED exactly that edit. (b) NARROWING: removing a process from activation.toml's active list disarms every guard that process owns. Both land inside the commit keystone, but clause 1 exists precisely because a bypassed hook leaves no trace at commit time - and the hook WAS bypassed on this machine for an entire session (issue240), which is the scenario clause 1 was built for. THE FIX: the signature now derives, per commit and per declared guard, its EFFECTIVE STATE from the tree - CORE when no process claims it, ACTIVE when a claiming process is in the declared active set, INACTIVE when a declared manifest omits the claimer - ranked CORE > ACTIVE > INACTIVE > absent, so both a capture and a deactivation rank as weakenings needing a co-committed marked Decision. An ABSENT activation.toml still means everything is active (D0138/issue090), so absent and declared-but-omitting stay distinguishable and no project that never adopted a manifest is reported as disarmed. The deactivate refusal text no longer advises the disarming edit; it names the consequence. VERIFIED by two hook-bypassed negative probes in a throwaway git worktree, each exit 1: capturing stale-gate-prose into the guard-less report process reported 'guardstate:stale-gate-prose: blocking/bound/core -> present/inactive', and removing doc-sync from the active list reported 'guardstate:doc-sync: warning/active -> present/inactive'. Real history over HEAD~12 still PASSES, so the widened signature does not false-positive. Two unit tests pin the rank ordering and the camel-to-kebab convention shared with activation; full gate set green. NOT COVERED and not claimed: keel controls is a purely declarative hazard/control diff with no runtime-arming concept, tracked as dcControlsReportArming."; }
        part storyAdherenceCoversActivationDoDR1 : TestResult { :>> id = "873196fe-5ee2-46a7-a7d3-ce027f5aaec1"; :>> outcome = VerdictKind::pass; :>> judgedAgainst = "543e1fa967b8d9d301925a2e6c9d5152c01a0902"; :>> judgedAt = "2026-08-24"; :>> judgedBy = "claudeFable5"; }
    }

    verification adherenceCoversActivationRefineGate : Test { :>> id = "0cbcb6d6-c588-46b5-9b5c-c523b58e6a76"; :>> title = "Sprint 448 refine gate (DoR)"; :>> createdAt = "2026-08-24"; :>> createdBy = "claudeFable5"; :>> method = VerificationMethod::inspect; :>> procedureText = "DoR. Resolves issue242 (HIGH): a hole in a control shipped the same day, found by the panel's operations lens and reproduced live. Scope: widen the tree-derived enforcement signature to effective guard state, plus stop the CLI advising the attack. The declarative controls surface is out of scope and tracked. 2 points."; }
    part adherenceCoversActivationRefineGateR1 : TestResult { :>> id = "b7b31862-ee54-4b27-97e8-ca966ddb14eb"; :>> outcome = VerdictKind::pass; :>> judgedAgainst = "543e1fa967b8d9d301925a2e6c9d5152c01a0902"; :>> judgedAt = "2026-08-24"; :>> judgedBy = "claudeFable5"; }
    verification adherenceCoversActivationStandupGate : Test { :>> id = "f3a19063-d68a-4bfe-8d56-9a752e882aa0"; :>> title = "Sprint 448 standup gate"; :>> createdAt = "2026-08-24"; :>> createdBy = "claudeFable5"; :>> method = VerificationMethod::inspect; :>> procedureText = "Approach: the effective enforcement of a guard is a function of THREE tree facts - its declaration in .engine/rules/, which process claims it, and the activation manifest - so derive the STATE rather than the declaration. Rank CORE above ACTIVE because CORE cannot be switched at all, which is what makes a capture a weakening even when the guard nominally still runs. Keep absent-manifest semantics (everything active) so no downstream project is falsely reported disarmed. adherence.rs is on the frozen enforcement surface, so D0213 co-commits as the marked Decision. No blockers."; }
    part adherenceCoversActivationStandupGateR1 : TestResult { :>> id = "f8dfe486-df6d-4515-b1ff-7e7648074eda"; :>> outcome = VerdictKind::pass; :>> judgedAgainst = "543e1fa967b8d9d301925a2e6c9d5152c01a0902"; :>> judgedAt = "2026-08-24"; :>> judgedBy = "claudeFable5"; }
    verification adherenceCoversActivationImplementGate : Test { :>> id = "356a3f46-6fd6-4fec-9082-1f522e98d952"; :>> title = "Sprint 448 implement gate"; :>> createdAt = "2026-08-24"; :>> createdBy = "claudeFable5"; :>> method = VerificationMethod::test; :>> procedureText = "Verified by running the freshness-checked binary (grepped the exe for `guardstate:` before trusting any result): in a throwaway worktree with the hook bypassed via -c core.hooksPath=/dev/null and --no-verify, the capture probe returned exit 1 naming 'guardstate:stale-gate-prose: blocking/bound/core -> present/inactive' and the narrowing probe returned exit 1 naming 'guardstate:doc-sync: warning/active -> present/inactive'; audit-adherence over HEAD~12 of real history PASSES. cargo test --lib adherence -> 4 passed; cargo clippy --workspace --all-targets -D warnings clean after fixing an if-let/else lint; validate 499 + all 48 guards + check-engine + rules green."; }
    part adherenceCoversActivationImplementGateR1 : TestResult { :>> id = "30e7b38f-53c8-4398-9925-9c23656c1b08"; :>> outcome = VerdictKind::pass; :>> judgedAgainst = "543e1fa967b8d9d301925a2e6c9d5152c01a0902"; :>> judgedAt = "2026-08-24"; :>> judgedBy = "claudeFable5"; }
    verification adherenceCoversActivationReviewGate : Test { :>> id = "fca1ef85-d64a-46f7-880d-1bb0322e575a"; :>> title = "Sprint 448 review gate — three passes per D0172"; :>> createdAt = "2026-08-24"; :>> createdBy = "claudeFable5"; :>> method = VerificationMethod::inspect; :>> procedureText = "PASS 1, CLAIMS: both probe transitions and the real-history PASS are quoted read-backs, and binary freshness was checked before the runs. PASS 2, BOUNDARY: (i) the guard universe is the set of `constraint def` names in .engine/rules/ - a guard that exists only in Rust with no constraint declaration is outside the signature, which is the pre-existing scope of clause 1 and not widened here; (ii) activation.toml parsing is a line scan for `[processes] active = [...]`, so a reformatted TOML (multi-line array) would read as no manifest and, by the absent-means-active rule, report guards as ACTIVE rather than INACTIVE - that fails SAFE for false accusation but fails OPEN for detection, and is stated rather than hidden; (iii) viewpoint deactivation is not covered - it removes a lens, not a guard. PASS 3, OWN DIFF: the first probe read a FALSE CLEAN because I passed --since HEAD~1, giving a one-commit range with no parent to compare - the THIRD time this exact probe-design error has appeared (sprint441, sprint440, here). The durable rule, now recorded a third time: a control's negative probe must put the PARENT in range, and a clean result from a probe must itself be disbelieved until the probe is shown capable of failing. WHAT A REVIEWER SHOULD ATTACK: the absent-manifest rule means a project could delete activation.toml entirely and every guard would read ACTIVE - honest under D0138 but a plausible evasion; deleting the manifest is itself a keystone-locked contract change, which is the answer, but it is worth checking that path is really covered."; }
    part adherenceCoversActivationReviewGateR1 : TestResult { :>> id = "b30533e2-e596-44e3-9409-f9297b374f6e"; :>> outcome = VerdictKind::pass; :>> judgedAgainst = "543e1fa967b8d9d301925a2e6c9d5152c01a0902"; :>> judgedAt = "2026-08-24"; :>> judgedBy = "claudeFable5"; }
    verification adherenceCoversActivationCloseOutGate : Test { :>> id = "ffd96cd1-9e89-4131-9279-0fa834db8650"; :>> title = "Sprint 448 closeOut gate (autonomous, D0049)"; :>> createdAt = "2026-08-24"; :>> createdBy = "claudeFable5"; :>> method = VerificationMethod::inspect; :>> procedureText = "Autonomous closeOut (D0049). issue242 resolved with both disarm routes probed and caught; D0213 co-committed as the marked Decision satisfying the enforcement-surface lock; the CLI no longer advises the capture; validate + all 48 guards + check-engine + rules + audit-adherence green. Five panel findings remain: issue239, issue244, issue245, issue243, issue246."; }
    part adherenceCoversActivationCloseOutGateR1 : TestResult { :>> id = "c1c2ce76-28e2-4c50-b6d7-6337b63415e8"; :>> outcome = VerdictKind::pass; :>> judgedAgainst = "543e1fa967b8d9d301925a2e6c9d5152c01a0902"; :>> judgedAt = "2026-08-24"; :>> judgedBy = "claudeFable5"; }
    verification adherenceCoversActivationRetroGate : Test { :>> id = "65d58d1b-a74c-4323-841f-efe269be5d3d"; :>> title = "Sprint 448 retro gate (autonomous, D0049)"; :>> createdAt = "2026-08-24"; :>> createdBy = "claudeFable5"; :>> method = VerificationMethod::analyze; :>> procedureText = "Autonomous retro (D0049). AVOIDABLE-ISSUE SCAN under rcRecurrence: the negative-probe-range error recurred for the THIRD time (--since HEAD~1 leaves nothing to compare, so the probe read clean against a real weakening). Two sprints previously recorded 'a control's negative probe must reproduce the real bypass'; the missing half is now explicit - it must also put the PARENT IN RANGE, and a clean probe result is evidence of nothing until the probe has been shown able to fail. That is a candidate for a permanent control rather than a third lesson: audit-adherence could refuse a range of fewer than two commits as a USAGE error rather than printing 'Clean'. Recorded here and worth raising as its own item. WELL: a control shipped in the morning was attacked by an independent lens by evening, the hole was real, and both attack routes are now gated with probes that demonstrably fail - which is the control-evaluation discipline working end to end. Estimate 2 pts, delivered 2."; }
    part adherenceCoversActivationRetroGateR1 : TestResult { :>> id = "004c94a9-feaa-44ab-bb4d-cbd43af4769e"; :>> outcome = VerdictKind::pass; :>> judgedAgainst = "543e1fa967b8d9d301925a2e6c9d5152c01a0902"; :>> judgedAt = "2026-08-24"; :>> judgedBy = "claudeFable5"; }
}
