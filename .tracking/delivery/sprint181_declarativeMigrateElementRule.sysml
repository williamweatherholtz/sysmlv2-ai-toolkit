// ProjectDeliveryS181 — Sprint 181: declarativeMigrateElementRule (D0105 migration, MIGRATE step 2).
// Build the ElementRule PREDICATE engine (nonBlank/minLength, conjunction) + migrate guard:decision-rationale
// to a declared ElementRule at PARITY. Guards still run (nothing retired). EXECUTE. 1 pt. AUTONOMOUS (D0049).
package ProjectDeliveryS181 {
    private import EngineElement::*;
    private import EngineWork::*;
    private import EngineVerification::*;
    private import EngineRelationships::*;

    #CharteredBy dependency from declElemStory to d0105;

    part declElemStory : Story {
        :>> id = "63940516-2c7d-4e8f-c181-51627384c001";
        :>> title = "Sprint 181: declarativeMigrateElementRule (1 pt) - ElementRule predicate engine + guard:decision-rationale at parity (D0105 MIGRATE)";
        :>> createdAt = "2026-07-03"; :>> createdBy = "wweatherholtz"; :>> kind = WorkKind::code; :>> priority = WorkPriority::p1; :>> owner = "claudeOpus"; :>> estimatedPoints = 1;
    }

    action def DeliveryRunS181 {
        action storyDeclElem;
        verification storyDeclElemDoD : Test { :>> id = "63940516-2c7d-4e8f-c181-51627384c002"; :>> method = VerificationMethod::test; :>> procedureText = "D0105 MIGRATE step 2 (the FIRST ElementRule). (1) ElementRule predicate engine: eval_predicate_term (closed vocab so far: nonBlank(field) trimmed>0, minLength(field,n) trimmed>=n) + eval_predicate (TERMs joined by ' and '; None if any term unsupported -> rule reports evaluated=false, never a false pass) + element_rule_violations; check() now evaluates BOTH EdgeRule + ElementRule. (2) New rule .engine/rules/rules.sysml decisionRationaleRule (subject Decision, predicate 'minLength(context,20) and minLength(rationale,20)'), #JustifiedBy d0103 - mirrors guard:decision-rationale (D0103). (3) PARITY proven: unit test element_rule_reaches_parity_with_decision_rationale_guard (== the guard's blank-context-or-rationale logic) + LIVE: `keel rules` decisionRationaleRule 0 violations == `keel guard decision-rationale` 0 (106 scanned). NOTHING retired. VERIFY: clippy -D warnings clean; cargo test (all view::tests::e* pass) green; keel validate (194) + guard all (14) green; rule instance rust-validated (D0048)."; }
        part storyDeclElemDoDR1 : TestResult { :>> id = "63940516-2c7d-4e8f-c181-51627384c003"; :>> outcome = VerdictKind::pass; :>> judgedAgainst = "3b6148a"; :>> judgedAt = "2026-07-03"; :>> judgedBy = "claudeOpus"; }
    }

    verification declElemRefineGate : Test { :>> id = "63940516-2c7d-4e8f-c181-51627384c004"; :>> title = "Sprint 181 refine gate (DoR)"; :>> createdAt = "2026-07-03"; :>> createdBy = "claudeOpus"; :>> method = VerificationMethod::inspect; :>> procedureText = "DoR: 2 EdgeRules at parity; next is the ElementRule engine (per-element integrity). decision-rationale is the cleanest parity target (no scope, no git). estimatedPoints=1. #CharteredBy d0105. DoR met."; }
    part declElemRefineGateR1 : TestResult { :>> id = "63940516-2c7d-4e8f-c181-51627384c005"; :>> outcome = VerdictKind::pass; :>> judgedAgainst = "3b6148a"; :>> judgedAt = "2026-07-03"; :>> judgedBy = "claudeOpus"; }
    verification declElemStandupGate : Test { :>> id = "63940516-2c7d-4e8f-c181-51627384c006"; :>> title = "Sprint 181 standup gate"; :>> createdAt = "2026-07-03"; :>> createdBy = "claudeOpus"; :>> method = VerificationMethod::inspect; :>> procedureText = "Approach: eval_predicate_term/eval_predicate/element_rule_violations (nonBlank, minLength, conjunction); check() handles ElementRule; author decisionRationaleRule; parity vs guard (unit + live). No guard retired."; }
    part declElemStandupGateR1 : TestResult { :>> id = "63940516-2c7d-4e8f-c181-51627384c007"; :>> outcome = VerdictKind::pass; :>> judgedAgainst = "3b6148a"; :>> judgedAt = "2026-07-03"; :>> judgedBy = "claudeOpus"; }
    verification declElemImplementGate : Test { :>> id = "63940516-2c7d-4e8f-c181-51627384c008"; :>> title = "Sprint 181 implement gate"; :>> createdAt = "2026-07-03"; :>> createdBy = "claudeOpus"; :>> method = VerificationMethod::test; :>> procedureText = "predicate engine + decisionRationaleRule landed. LIVE: keel rules decisionRationaleRule 0 == guard decision-rationale 0 (106). clippy -D clean (fixed lifetime + doc-backtick + item-after-stmt lints); cargo test element_rule_reaches_parity + edge_rule_* pass; keel validate + guard green."; }
    part declElemImplementGateR1 : TestResult { :>> id = "63940516-2c7d-4e8f-c181-51627384c009"; :>> outcome = VerdictKind::pass; :>> judgedAgainst = "3b6148a"; :>> judgedAt = "2026-07-03"; :>> judgedBy = "claudeOpus"; }
    verification declElemReviewGate : Test { :>> id = "63940516-2c7d-4e8f-c181-51627384c00a"; :>> title = "Sprint 181 review gate"; :>> createdAt = "2026-07-03"; :>> createdBy = "claudeOpus"; :>> method = VerificationMethod::inspect; :>> procedureText = "Reviewed. Third guard at parity, and the FIRST of the ~5 structural guards — the ElementRule engine's fail-closed design (unsupported term -> evaluated=false, never a false pass) is the right safety default for a migration. Predicate vocab stays closed + small (nonBlank/minLength), matching D0105's bounded-vocabulary intent. Clean."; }
    part declElemReviewGateR1 : TestResult { :>> id = "63940516-2c7d-4e8f-c181-51627384c00b"; :>> outcome = VerdictKind::pass; :>> judgedAgainst = "3b6148a"; :>> judgedAt = "2026-07-03"; :>> judgedBy = "claudeOpus"; }
    verification declElemCloseOutGate : Test { :>> id = "63940516-2c7d-4e8f-c181-51627384c00c"; :>> title = "Sprint 181 closeOut gate (autonomous, D0049)"; :>> createdAt = "2026-07-03"; :>> createdBy = "claudeOpus"; :>> method = VerificationMethod::inspect; :>> procedureText = "Autonomous closeOut (D0049): DoD pass; 3 guards now have parity rules (rootedness, issues, decision-rationale) across BOTH EdgeRule + ElementRule kinds. clippy + cargo test + keel validate + guard green. Self-evidencing (D0051)."; }
    part declElemCloseOutGateR1 : TestResult { :>> id = "63940516-2c7d-4e8f-c181-51627384c00d"; :>> outcome = VerdictKind::pass; :>> judgedAgainst = "3b6148a"; :>> judgedAt = "2026-07-03"; :>> judgedBy = "claudeOpus"; }
    verification declElemRetroGate : Test { :>> id = "63940516-2c7d-4e8f-c181-51627384c00e"; :>> title = "Sprint 181 retro gate (autonomous, D0049)"; :>> createdAt = "2026-07-03"; :>> createdBy = "claudeOpus"; :>> method = VerificationMethod::analyze; :>> procedureText = "Autonomous retro (D0049). WELL: both rule kinds (EdgeRule + ElementRule) now have a working evaluator + a guard at parity; the fail-closed predicate engine keeps the migration honest. AVOIDABLE-ISSUE SCAN: recurring clippy -D lints on new code (closure-lifetime, item-after-statement, doc backticks) cost a round-trip; LESSON (repeat of sprint179) - run clippy -D BEFORE the parity/commit cycle when adding helper fns. Estimate 1 pt held. PROGRESS: 3 of ~14 guards mirrored. REMAINING: critic-independence (distinct predicate) + more ElementRules; the SCOPE sub-language (newlyAdded/whereStatus) for charter/sprint-coverage/acceptance-events; OrderingRule for ceremony; then CONTRACT retires each at parity + the `keel check` name reconciliation."; }
    part declElemRetroGateR1 : TestResult { :>> id = "63940516-2c7d-4e8f-c181-51627384c00f"; :>> outcome = VerdictKind::pass; :>> judgedAgainst = "3b6148a"; :>> judgedAt = "2026-07-03"; :>> judgedBy = "claudeOpus"; }
}
