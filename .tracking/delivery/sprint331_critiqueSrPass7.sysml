// ProjectDeliveryS331 — Sprint 331: critique pass 7 — five viewer SystemRequirements. EXECUTE. 3 pts.
package ProjectDeliveryS331 {
    private import EngineElement::*;
    private import EngineWork::*;
    private import EngineVerification::*;
    private import EngineRelationships::*;

    #CharteredBy dependency from critPass7Story to d0080;

    part critPass7Story : Story {
        :>> id = "0d800460-0814-6460-9b3e-000000300460";
        :>> title = "Sprint 331: critique pass 7 — 5 viewer SRs x Core-3, 10 fail / 5 pass (3 pts)";
        :>> createdAt = "2026-08-17"; :>> createdBy = "claudeOpus5"; :>> kind = WorkKind::modeling; :>> priority = WorkPriority::p0; :>> owner = "claudeOpus5"; :>> estimatedPoints = 3;
    }

    action def DeliveryRunS331 {
        action storyCritPass7;
        verification storyCritPass7DoD : Test { :>> id = "0d800461-0814-6461-9b3e-000000300461"; :>> method = VerificationMethod::analyze; :>> procedureText = "Pass 7: srViewerCreateLinkage, srViewerDatePredicates, srViewerExportShare, srViewerGenerativeUi, srViewerGraphExpand. 10 fail, 5 pass. THE BEST FINDING CAME FROM DISTRUSTING A RATIONALE: srViewerDatePredicates asserts that date/range comparisons are what 'the current equality/set-membership-only vocabulary cannot express', and that premise is already out of date — D0075 (accepted) declares the select-predicate form as type, equality, in-set, TIME-RANGE and has/missing-edge, and DateFilter (attr, since, until) is implemented in view.rs and wired into /api/slice, documented as the N-5 time-as-query-filter. What I did NOT establish, and said so in the critique rather than guessing, is whether the TOML select evaluator honours the time-range D0075 declares — no shipped .view.toml uses since or until. That unknown is the content the requirement should have carried: not ADD date predicates, but RECONCILE a declared predicate with its implementation. SECOND: that requirement defers its bound to 'a follow-on Decision (open question Q3)' and no such Decision exists — so it is blocked on an unwritten Decision, and nothing surfaces that. The engine can express blocked WORK (a #DependsOn to a proposed Decision drops an action off the frontier) and cannot express a blocked REQUIREMENT. THIRD: srViewerGenerativeUi's parenthetical cites 'shape B', which D0152 superseded — the fourth stale reference this session has found. READ BACK: SystemRequirement coverage 15 -> 20 of 72."; }
        part storyCritPass7DoDR1 : TestResult { :>> id = "0d800462-0814-6462-9b3e-000000300462"; :>> outcome = VerdictKind::pass; :>> judgedAgainst = "59994b0"; :>> judgedAt = "2026-08-17"; :>> judgedBy = "claudeOpus5"; }
    }

    verification c7RefineGate : Test { :>> id = "0d800463-0814-6463-9b3e-000000300463"; :>> title = "Sprint 331 refine gate (DoR)"; :>> createdAt = "2026-08-17"; :>> createdBy = "claudeOpus5"; :>> method = VerificationMethod::inspect; :>> procedureText = "DoR. Five viewer SRs. Four mechanisms were traced before judgment: D0075's declared predicate form, DateFilter and its wiring in serve.rs, the EdgeRule pair constraints (five rules, not a type-product table), and the D0114-to-D0152 supersession. Two of the four changed a verdict. estimatedPoints=3."; }
    part c7RefineGateR1 : TestResult { :>> id = "0d800464-0814-6464-9b3e-000000300464"; :>> outcome = VerdictKind::pass; :>> judgedAgainst = "59994b0"; :>> judgedAt = "2026-08-17"; :>> judgedBy = "claudeOpus5"; }

    verification c7StandupGate : Test { :>> id = "0d800465-0814-6465-9b3e-000000300465"; :>> title = "Sprint 331 standup gate"; :>> createdAt = "2026-08-17"; :>> createdBy = "claudeOpus5"; :>> method = VerificationMethod::inspect; :>> procedureText = "Approach: treat a requirement's RATIONALE as a claim to be checked rather than as context — the pass's sharpest finding came from testing a rationale's assertion about the current implementation and finding it stale. Where a trace runs out, say what was not established instead of inferring. No blockers."; }
    part c7StandupGateR1 : TestResult { :>> id = "0d800466-0814-6466-9b3e-000000300466"; :>> outcome = VerdictKind::pass; :>> judgedAgainst = "59994b0"; :>> judgedAt = "2026-08-17"; :>> judgedBy = "claudeOpus5"; }

    verification c7ImplementGate : Test { :>> id = "0d800467-0814-6467-9b3e-000000300467"; :>> title = "Sprint 331 implement gate"; :>> createdAt = "2026-08-17"; :>> createdBy = "claudeOpus5"; :>> method = VerificationMethod::analyze; :>> procedureText = "A STRUCTURAL GAP IN THE ENGINE, not in any one element, and this pass is where it became visible: the model can express BLOCKED WORK and cannot express A BLOCKED REQUIREMENT. srViewerDatePredicates defers its acceptance bound to a follow-on Decision that was never authored. Had that been a backlog action, a #DependsOn edge to a proposed Decision would drop it off the ready frontier and it would appear in pendingAcceptances — visible, and correctly unschedulable. Because it is a REQUIREMENT, nothing computes its blocked-ness: it reads as an ordinary uncovered requirement, and its unverifiability looks like a coverage gap rather than a missing decision. I have NOT proposed a mechanism for it, because inventing one would be a schema-shaped change nobody has asked for; it is recorded here and in the critique so the observation survives. THE SAME UNWRITTEN FIXTURE now serves FIVE elements (nServeReuseModel, nViewerGenerativeUi, srViewerContextActions, srEncodingModular, srViewerGenerativeUi's own testability lens): change the declared model, require the surface to change with no code edit."; }
    part c7ImplementGateR1 : TestResult { :>> id = "0d800468-0814-6468-9b3e-000000300468"; :>> outcome = VerdictKind::pass; :>> judgedAgainst = "59994b0"; :>> judgedAt = "2026-08-17"; :>> judgedBy = "claudeOpus5"; }

    verification c7ReviewGate : Test { :>> id = "0d800469-0814-6469-9b3e-000000300469"; :>> title = "Sprint 331 review gate"; :>> createdAt = "2026-08-17"; :>> createdBy = "claudeOpus5"; :>> method = VerificationMethod::inspect; :>> procedureText = "Reviewed. TWO REQUIREMENTS EARNED CORRECTNESS PASSES FOR REPAIRING THEIR NEEDS, which is the pattern I most want this corpus to record: srViewerExportShare replaced N-12's as-of DATE with 'as-of date + scope + the source commit, so the snapshot is reproducible' — the right anchor in a system where every TestResult pins a commit precisely because a date is ambiguous; and srViewerGraphExpand replaced N-2's undefined 'stable layout' with 'does not re-shuffle on expand', which is both the property a walker needs and a mechanically checkable one (record positions, expand, require the pre-existing positions unchanged). Neither repair is cosmetic and both made a previously untestable clause testable. srViewerExportShare still carries its Need's audience defect — a share LINK cannot reach a non-user of a local-only console — so a requirement can fix one inherited defect and carry another, and the critique says which is which."; }
    part c7ReviewGateR1 : TestResult { :>> id = "0d80046a-0814-646a-9b3e-00000030046a"; :>> outcome = VerdictKind::pass; :>> judgedAgainst = "59994b0"; :>> judgedAt = "2026-08-17"; :>> judgedBy = "claudeOpus5"; }

    verification c7CloseOutGate : Test { :>> id = "0d80046b-0814-646b-9b3e-00000030046b"; :>> title = "Sprint 331 closeOut gate (autonomous, D0049)"; :>> createdAt = "2026-08-17"; :>> createdBy = "claudeOpus5"; :>> method = VerificationMethod::inspect; :>> procedureText = "Autonomous closeOut (D0049). SystemRequirement coverage 15 -> 20 of 72; 10 critiquable SRs and 22 critiquable Decisions remain. Zero open issues; ready frontier empty; D0159 queued. validate clean; check-engine clean; 35 guards ALL PASS; no code changed."; }
    part c7CloseOutGateR1 : TestResult { :>> id = "0d80046c-0814-646c-9b3e-00000030046c"; :>> outcome = VerdictKind::pass; :>> judgedAgainst = "59994b0"; :>> judgedAt = "2026-08-17"; :>> judgedBy = "claudeOpus5"; }

    verification c7RetroGate : Test { :>> id = "0d80046d-0814-646d-9b3e-00000030046d"; :>> title = "Sprint 331 retro gate (autonomous, D0049)"; :>> createdAt = "2026-08-17"; :>> createdBy = "claudeOpus5"; :>> method = VerificationMethod::analyze; :>> procedureText = "Autonomous retro (D0049) under D0131's retroTrack. WELL: (1) treating a RATIONALE as a claim rather than as context produced the pass's best finding — the date-predicate premise is stale, which changes the requirement from add-a-feature to reconcile-a-declaration; (2) where the trace ran out I recorded what was NOT established (whether the TOML select evaluator honours the declared time-range) instead of inferring it, and that unknown is more useful than either guess would have been; (3) the blocked-requirement gap was recorded as an observation and NOT converted into a proposed mechanism, because a schema-shaped fix nobody asked for is scope I do not own. AVOIDABLE-ISSUE: I spent four tool calls chasing the TOML select evaluator's internals before deciding the two facts I already had were enough to write an honest critique. The lesson is to decide what the finding NEEDS before hunting: the finding needed only that a time-range is declared and that a date filter ships, both of which I had after two calls. Estimate 3 pts, delivered."; }
    part c7RetroGateR1 : TestResult { :>> id = "0d80046e-0814-646e-9b3e-00000030046e"; :>> outcome = VerdictKind::pass; :>> judgedAgainst = "59994b0"; :>> judgedAt = "2026-08-17"; :>> judgedBy = "claudeOpus5"; }
}
