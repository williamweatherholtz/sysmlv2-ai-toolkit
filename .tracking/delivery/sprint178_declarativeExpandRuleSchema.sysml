// ProjectDeliveryS178 — Sprint 178: declarativeExpandRuleSchema (D0105 migration, EXPAND step 1).
// First step of the D0067 expand/migrate/contract guards->rules migration: add the Rule SCHEMA to
// schema/core ALONGSIDE the 14 guards (nothing retired). Three rule kinds + a bounded scope sub-language
// + exemptions + the closed edge-algebra enum. Frozen-core addition AUTHORIZED by D0105 (accepted). CR. 2 pt. AUTONOMOUS (D0049).
package ProjectDeliveryS178 {
    private import EngineElement::*;
    private import EngineWork::*;
    private import EngineVerification::*;
    private import EngineRelationships::*;

    #CharteredBy dependency from declExpandStory to d0105;

    part declExpandStory : Story {
        :>> id = "63940516-2c7d-4e8f-c178-51627384c001";
        :>> title = "Sprint 178: declarativeExpandRuleSchema (2 pt) - add the Rule schema to schema/core (D0105 migration EXPAND step 1)";
        :>> createdAt = "2026-07-03"; :>> createdBy = "wweatherholtz"; :>> kind = WorkKind::code; :>> priority = WorkPriority::p1; :>> owner = "claudeOpus"; :>> estimatedPoints = 2;
    }

    action def DeliveryRunS178 {
        action storyDeclExpand;
        verification storyDeclExpandDoD : Test { :>> id = "63940516-2c7d-4e8f-c178-51627384c002"; :>> method = VerificationMethod::inspect; :>> procedureText = "D0105 migration EXPAND step 1 (D0067 lifecycle). Added .engine/schema/core/rules.sysml (EngineRules): the spike-corrected surface - THREE rule kinds (EdgeRule conformance / ElementRule per-element integrity / OrderingRule succession-conformance) on a Rule base carrying severity (blocking/warning) + onViolation (block/warn/issue/suspect) + appliesWhen (the bounded SCOPE sub-language: all/governedSince/newlyAdded/whereStatus/cutoff) + exemptions (grandfather set w/ recorded basis); an EdgeKind enum NAMING the closed edge algebra + markers (no new edges). Registered in _schema_files.SCHEMA_ORDER (after element.sysml). NOTHING retired - the 14 guards still run (parity comes in guardsToRulesMigration). CR (schema/core change; D0105 is the governing accepted decision). Debugging notes for downstream: SysML v2 reserves satisfy/verify/allocate/dependency/supersede (relationship keywords) + subject (requirement keyword) - edge literals are Edge-suffixed, subject->subjectType; String needs `private import ScalarValues`. VERIFY: kernel validate_schema PASS (16/16); the schema-registration guard (_schema_files) satisfied; keel validate + guard all green (guards unchanged); doc-sync (keel-syntax-notes: the reserved-word gotcha)."; }
        part storyDeclExpandDoDR1 : TestResult { :>> id = "63940516-2c7d-4e8f-c178-51627384c003"; :>> outcome = VerdictKind::pass; :>> judgedAgainst = "683f847"; :>> judgedAt = "2026-07-03"; :>> judgedBy = "claudeOpus"; }
    }

    verification declExpandRefineGate : Test { :>> id = "63940516-2c7d-4e8f-c178-51627384c004"; :>> title = "Sprint 178 refine gate (DoR)"; :>> createdAt = "2026-07-03"; :>> createdBy = "claudeOpus"; :>> method = VerificationMethod::inspect; :>> procedureText = "DoR: D0105 accepted -> the frozen-core Rule schema is authorized. EXPAND step 1 = add the schema only (no evaluator, no guard retirement). estimatedPoints=2. #CharteredBy d0105. DoR met."; }
    part declExpandRefineGateR1 : TestResult { :>> id = "63940516-2c7d-4e8f-c178-51627384c005"; :>> outcome = VerdictKind::pass; :>> judgedAgainst = "683f847"; :>> judgedAt = "2026-07-03"; :>> judgedBy = "claudeOpus"; }
    verification declExpandStandupGate : Test { :>> id = "63940516-2c7d-4e8f-c178-51627384c006"; :>> title = "Sprint 178 standup gate"; :>> createdAt = "2026-07-03"; :>> createdBy = "claudeOpus"; :>> method = VerificationMethod::inspect; :>> procedureText = "Approach: author EngineRules (3 rule kinds + scope sublang + exemptions + EdgeKind enum); register in SCHEMA_ORDER; kernel-validate. Watch SysML reserved words. No guard changes this step."; }
    part declExpandStandupGateR1 : TestResult { :>> id = "63940516-2c7d-4e8f-c178-51627384c007"; :>> outcome = VerdictKind::pass; :>> judgedAgainst = "683f847"; :>> judgedAt = "2026-07-03"; :>> judgedBy = "claudeOpus"; }
    verification declExpandImplementGate : Test { :>> id = "63940516-2c7d-4e8f-c178-51627384c008"; :>> title = "Sprint 178 implement gate"; :>> createdAt = "2026-07-03"; :>> createdBy = "claudeOpus"; :>> method = VerificationMethod::inspect; :>> procedureText = "rules.sysml authored + registered; reserved-word + ScalarValues-import fixes applied. kernel validate_schema PASS; keel validate + guard all green (guards untouched)."; }
    part declExpandImplementGateR1 : TestResult { :>> id = "63940516-2c7d-4e8f-c178-51627384c009"; :>> outcome = VerdictKind::pass; :>> judgedAgainst = "683f847"; :>> judgedAt = "2026-07-03"; :>> judgedBy = "claudeOpus"; }
    verification declExpandReviewGate : Test { :>> id = "63940516-2c7d-4e8f-c178-51627384c00a"; :>> title = "Sprint 178 review gate"; :>> createdAt = "2026-07-03"; :>> createdBy = "claudeOpus"; :>> method = VerificationMethod::inspect; :>> procedureText = "Reviewed. The schema matches the sprint172-spike-corrected surface (3 kinds + scope sublang + exemptions), names the closed edge algebra without adding edges, and carries provenance via a #JustifiedBy edge (not prose). Pure EXPAND: guards untouched, so no behavior change + no risk yet. The parity gate + retirement come later. Clean."; }
    part declExpandReviewGateR1 : TestResult { :>> id = "63940516-2c7d-4e8f-c178-51627384c00b"; :>> outcome = VerdictKind::pass; :>> judgedAgainst = "683f847"; :>> judgedAt = "2026-07-03"; :>> judgedBy = "claudeOpus"; }
    verification declExpandCloseOutGate : Test { :>> id = "63940516-2c7d-4e8f-c178-51627384c00c"; :>> title = "Sprint 178 closeOut gate (autonomous, D0049)"; :>> createdAt = "2026-07-03"; :>> createdBy = "claudeOpus"; :>> method = VerificationMethod::inspect; :>> procedureText = "Autonomous closeOut (D0049): DoD pass; the Rule schema exists in schema/core, kernel-green, guards unchanged. Self-evidencing (D0051). EXPAND step 1 of the migration done."; }
    part declExpandCloseOutGateR1 : TestResult { :>> id = "63940516-2c7d-4e8f-c178-51627384c00d"; :>> outcome = VerdictKind::pass; :>> judgedAgainst = "683f847"; :>> judgedAt = "2026-07-03"; :>> judgedBy = "claudeOpus"; }
    verification declExpandRetroGate : Test { :>> id = "63940516-2c7d-4e8f-c178-51627384c00e"; :>> title = "Sprint 178 retro gate (autonomous, D0049)"; :>> createdAt = "2026-07-03"; :>> createdBy = "claudeOpus"; :>> method = VerificationMethod::analyze; :>> procedureText = "Autonomous retro (D0049). WELL: EXPAND-first (schema alongside guards, nothing retired) means zero behavior change + zero risk at this step - the safe way to start a frozen-core migration. AVOIDABLE-ISSUE SCAN: three avoidable kernel round-trips - (1) unregistered schema file (SCHEMA_ORDER), (2) SysML reserved words as identifiers (satisfy/verify/allocate/dependency/supersede/subject), (3) missing ScalarValues import for String; LESSON: before authoring a new schema/core file, register it in SCHEMA_ORDER, avoid the relationship/requirement keywords as names, and import ScalarValues - captured in doc-sync (keel-syntax-notes). Estimate 2 pt held. NEXT: EXPAND step 2 = the `keel check` evaluator (reads these rules), then MIGRATE (express guards as rules + parity gate), then CONTRACT."; }
    part declExpandRetroGateR1 : TestResult { :>> id = "63940516-2c7d-4e8f-c178-51627384c00f"; :>> outcome = VerdictKind::pass; :>> judgedAgainst = "683f847"; :>> judgedAt = "2026-07-03"; :>> judgedBy = "claudeOpus"; }
}
