// ProjectDeliveryS452 — Sprint 452: a number the engine can compute may not be typed into the doc surface - delete it, do not reconcile it (issue246, D0215). EXECUTE. 2 pts.
package ProjectDeliveryS452 {
    private import EngineElement::*;
    private import EngineWork::*;
    private import EngineVerification::*;
    private import EngineRelationships::*;

    #CharteredBy dependency from docCountsReconciledStory to d0215;

    part docCountsReconciledStory : Story {
        :>> id = "808de7cb-69ba-42b9-b22f-8c1bdd72ee92";
        :>> title = "Sprint 452: the guard count has one home again (2 pts)";
        :>> createdAt = "2026-08-24"; :>> createdBy = "claudeFable5"; :>> kind = WorkKind::code; :>> priority = WorkPriority::p0; :>> owner = "claudeFable5"; :>> estimatedPoints = 2;
    }

    action def DeliveryRunS452 {
        action storyDocCountsReconciled;
        verification storyDocCountsReconciledDoD : Test { :>> id = "266c6036-19ac-4fcd-afb0-e9ea9eaef969"; :>> method = VerificationMethod::test; :>> procedureText = "DELIVERED: dcDocCountsReconciled (resolves issue246, LOW by severity and named independently by FOUR of the nine panel lenses, which is why it is here). THE DEFECT: CLAUDE.md said 'all 45 forward guards' and .engine/docs/guards.md said 'runs **45** forward guards' while 48 were enforced - and guards.md's very next sentence said that `keel version` reports the split computed from the enforced set 'so the number has one home'. It stated a number while declaring the number should not live there. The same class was live in a shipped contract: activation.toml directed readers to .engine/contracts/process-units.toml, a file D0141 DELETED, and keel init copied that ghost into every new project. And the brief that DIAGNOSED report-vs-truth drift committed the class twice itself (30 skills where there are 37; GitHub issues cited as #1-#6 where the channel is #2-#7), which is what made a control non-optional under D0047 - manual vigilance had already demonstrably failed, including mine. THE FIX IS DELETION, NOT RECONCILIATION: syncing 45 to 48 fixes today and drifts again on guard 49, because the defect is the DUPLICATION and not the value (D0105, one canonical home). Both claims are removed - CLAUDE.md now points at `keel version`, guards.md says 'runs the enforced forward guards' - and the new hard guard doc-guard-count (GUARD_NAMES 48 -> 49) fails a commit that reintroduces a hardcoded total, naming the file, line, claim and computed value. The ghost reference is swept from activation.toml and from the ACTIVATION_HEADER that init writes. NARROW BY CONSTRUCTION, and this is the part I got wrong first: an 'all N guards' branch was implemented and then REMOVED after probing it against the real corpus, where it fired on guards.md legitimately narrating history ('passed validate and all 37 guards') - a TRUE statement about the past. A guard that fires on true prose gets bypassed, which would have made it worse than no guard, so historical narration and ordinal references ('Guard 37 checks...') are deliberately untouched. VERIFIED both directions with a freshness-checked binary: the cleaned corpus PASSES (4 files scanned, 0 violations); reintroducing 'all 45 forward guards' FAILS at exit 1 naming CLAUDE.md:179 and the computed 49; 253 lib tests pass; clippy clean; validate + all 49 guards + check-engine + rules green. Reflexively, guards.md may no longer state its own total, so the count 49 lives in D0215 and in `keel version` rather than in the catalogue."; }
        part storyDocCountsReconciledDoDR1 : TestResult { :>> id = "0790f6c9-844a-4140-b57c-5e0e345a79d3"; :>> outcome = VerdictKind::pass; :>> judgedAgainst = "766343d54c7f883b457b38f5b23f08fd66f560de"; :>> judgedAt = "2026-08-24"; :>> judgedBy = "claudeFable5"; }
    }

    verification docCountsReconciledRefineGate : Test { :>> id = "030c8946-db91-41a0-8c6b-54af4c273583"; :>> title = "Sprint 452 refine gate (DoR)"; :>> createdAt = "2026-08-24"; :>> createdBy = "claudeFable5"; :>> method = VerificationMethod::inspect; :>> procedureText = "DoR. Resolves issue246 (LOW severity, four-lens convergence). Scope: remove the two live claims, sweep the deleted-file reference, and add the control that stops the class recurring. D0047 makes the control mandatory rather than optional because the defect had already recurred in the review artifact itself. 2 points."; }
    part docCountsReconciledRefineGateR1 : TestResult { :>> id = "1cfe1b1b-8c76-478a-9d56-72e31eecf06d"; :>> outcome = VerdictKind::pass; :>> judgedAgainst = "766343d54c7f883b457b38f5b23f08fd66f560de"; :>> judgedAt = "2026-08-24"; :>> judgedBy = "claudeFable5"; }
    verification docCountsReconciledStandupGate : Test { :>> id = "354d71fa-765f-4dfd-a937-2b9fe0beb136"; :>> title = "Sprint 452 standup gate"; :>> createdAt = "2026-08-24"; :>> createdBy = "claudeFable5"; :>> method = VerificationMethod::inspect; :>> procedureText = "Approach: delete rather than sync, because the value is not the defect - the duplication is. Make the guard HARD, since a false number in the AI's own governing document is dishonest state and D0098 forbids gating completeness but says nothing against gating honesty. Keep the matcher to the canonical current-total phrasing so true historical prose survives. guards.rs is on the frozen enforcement surface, so D0215 co-commits as the marked Decision. No blockers."; }
    part docCountsReconciledStandupGateR1 : TestResult { :>> id = "82e0487f-00ef-4636-9b32-e4bba6ba1e57"; :>> outcome = VerdictKind::pass; :>> judgedAgainst = "766343d54c7f883b457b38f5b23f08fd66f560de"; :>> judgedAt = "2026-08-24"; :>> judgedBy = "claudeFable5"; }
    verification docCountsReconciledImplementGate : Test { :>> id = "d501aa20-447b-44a8-ac57-5d0819e73ffc"; :>> title = "Sprint 452 implement gate"; :>> createdAt = "2026-08-24"; :>> createdBy = "claudeFable5"; :>> method = VerificationMethod::test; :>> procedureText = "Verified by running the freshness-checked binary in both directions: keel guard doc-guard-count PASSES on the cleaned corpus (4 scanned, 0 violations) and FAILS at exit 1 when 'all 45 forward guards' is reintroduced, naming CLAUDE.md:179, the claim and the computed 49. The first matcher version was rejected by its own probe (false positive on historical narration) and narrowed. cargo test --lib -> 253 passed; cargo clippy --workspace --all-targets -D warnings clean after fixing an orphaned-doc-comment placement and two consecutive-replace lints; validate 503 + all 49 guards + check-engine + rules green."; }
    part docCountsReconciledImplementGateR1 : TestResult { :>> id = "43d10198-9f40-4d36-82c8-fa281cff7875"; :>> outcome = VerdictKind::pass; :>> judgedAgainst = "766343d54c7f883b457b38f5b23f08fd66f560de"; :>> judgedAt = "2026-08-24"; :>> judgedBy = "claudeFable5"; }
    verification docCountsReconciledReviewGate : Test { :>> id = "417fae10-f137-468b-b484-274f2c88bb64"; :>> title = "Sprint 452 review gate — three passes per D0172"; :>> createdAt = "2026-08-24"; :>> createdBy = "claudeFable5"; :>> method = VerificationMethod::inspect; :>> procedureText = "PASS 1, CLAIMS: both guard verdicts, the violation text and the computed count are quoted read-backs from the built binary. PASS 2, BOUNDARY: (i) the guard covers CLAUDE.md and .engine/docs/*.md only - a count typed into a .sysml procedureText or a README elsewhere is not caught, which is deliberate scope rather than completeness, and stated; (ii) it checks the GUARD total only, not other computable counts (processes, viewpoints, skills) - the table is extensible and starting with the one that actually drifted twice is the honest increment; (iii) 'all N guards' is NOT checked, by decision, and the catalogue row records why so the next author does not re-add it. PASS 3, OWN DIFF: two self-inflicted findings. First, my initial matcher produced a FALSE POSITIVE on true prose and I only found it by probing the real corpus rather than a toy case - the same lesson as the palette dry-run, and the reason the branch is now gone. Second, a `git checkout CLAUDE.md` during the negative probe silently REVERTED my own uncommitted fix; the new guard caught it on the very next run, which is the most direct possible demonstration that the control works and that the pre-control state was invisible. WHAT A REVIEWER SHOULD ATTACK: whether deletion loses genuine reader value - someone skimming guards.md can no longer see the scale at a glance, and the counter-argument is that a wrong number is worth less than one command."; }
    part docCountsReconciledReviewGateR1 : TestResult { :>> id = "86b0bad5-8aa7-497d-910d-47f4ad8f032f"; :>> outcome = VerdictKind::pass; :>> judgedAgainst = "766343d54c7f883b457b38f5b23f08fd66f560de"; :>> judgedAt = "2026-08-24"; :>> judgedBy = "claudeFable5"; }
    verification docCountsReconciledCloseOutGate : Test { :>> id = "ea1a8cf2-9840-4ac2-be54-2a8f0c9116e5"; :>> title = "Sprint 452 closeOut gate (autonomous, D0049)"; :>> createdAt = "2026-08-24"; :>> createdBy = "claudeFable5"; :>> method = VerificationMethod::inspect; :>> procedureText = "Autonomous closeOut (D0049). issue246 resolved: both claims deleted, the ghost reference swept, the control landed hard and probed both ways, and the catalogue row records the rejected branch. Also closed the verification-trace warning this work surfaced - the requirement authored in sprint450 now carries its #Verify edge, so the requirement is verified rather than only the work. One panel finding remains: issue245."; }
    part docCountsReconciledCloseOutGateR1 : TestResult { :>> id = "2e63cd73-0eac-4068-bb25-fb74e3aca4f7"; :>> outcome = VerdictKind::pass; :>> judgedAgainst = "766343d54c7f883b457b38f5b23f08fd66f560de"; :>> judgedAt = "2026-08-24"; :>> judgedBy = "claudeFable5"; }
    verification docCountsReconciledRetroGate : Test { :>> id = "6ffc5445-7782-4412-a778-89e7a4d90071"; :>> title = "Sprint 452 retro gate (autonomous, D0049)"; :>> createdAt = "2026-08-24"; :>> createdBy = "claudeFable5"; :>> method = VerificationMethod::analyze; :>> procedureText = "Autonomous retro (D0049). AVOIDABLE-ISSUE SCAN under rcRecurrence: (1) the nested-heredoc escaping class recurred for the THIRD time this session, in the same session whose previous retro had written 'ANY content with backslashes or quotes goes through the editor, no exceptions' - so the rule was recorded and then violated within the hour. That is now evidence that a retro lesson is not a control; the durable fix would be to stop generating Rust through shell heredocs at all. (2) A control's first version must be probed against the REAL corpus, not a constructed case: my matcher looked correct and was wrong on true prose. WELL: the guard caught my own accidental revert within one run, which is the cleanest possible evidence that the class was previously invisible; and the fix is subtractive - a number was removed from two documents rather than a synchroniser added between them. Estimate 2 pts, delivered 2."; }
    part docCountsReconciledRetroGateR1 : TestResult { :>> id = "2c33d3de-a954-4ca5-8278-1e9cfb839b51"; :>> outcome = VerdictKind::pass; :>> judgedAgainst = "766343d54c7f883b457b38f5b23f08fd66f560de"; :>> judgedAt = "2026-08-24"; :>> judgedBy = "claudeFable5"; }
}
