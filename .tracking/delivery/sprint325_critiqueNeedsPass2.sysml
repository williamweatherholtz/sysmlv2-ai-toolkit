// ProjectDeliveryS325 — Sprint 325: critique backfill pass 2 — five more human-authored Needs. EXECUTE. 3 pts.
package ProjectDeliveryS325 {
    private import EngineElement::*;
    private import EngineWork::*;
    private import EngineVerification::*;
    private import EngineRelationships::*;

    #CharteredBy dependency from critPass2Story to d0080;

    part critPass2Story : Story {
        :>> id = "0d800400-0814-6400-9b3e-000000300400";
        :>> title = "Sprint 325: critique pass 2 — 5 Needs x Core-3, 11 fail / 4 pass (3 pts)";
        :>> createdAt = "2026-08-17"; :>> createdBy = "claudeOpus5"; :>> kind = WorkKind::modeling; :>> priority = WorkPriority::p0; :>> owner = "claudeOpus5"; :>> estimatedPoints = 3;
    }

    action def DeliveryRunS325 {
        action storyCritPass2;
        verification storyCritPass2DoD : Test { :>> id = "0d800401-0814-6401-9b3e-000000300401"; :>> method = VerificationMethod::analyze; :>> procedureText = "Pass 2: nServeLaunchDefinedOnly, nServeReuseModel, nServeValidatedOutput, nViewerBaselineCompare, nViewerChangeImpact — all wweatherholtz-authored, so the judge is independent under critique-policy.toml. 11 fail, 4 pass. THE SHARPEST FINDING IS A LIVE SELF-CONTRADICTION: nServeReuseModel forbids 'a separately-maintained list that can drift', and guards.rs holds VIEW_SUBCOMMANDS — a hardcoded array of known keel commands that the viewpoint-renderer guard validates every declared renderer against. Its own comment records the drift it caused: 'authority-queue — real since D0129 sync work; never added here, so the first viewpoint naming it failed'. A real command was rejected because the hand-maintained list had not caught up, inside a guard, which is the failure mode the Need exists to prevent. SECOND: nViewerChangeImpact scopes blast radius to typed edges, and this session supplies three counter-examples where the consequential dependency was NOT a typed edge — a hardcoded file path (issue139), the engine/project schema union (issue129), and a commit SHA resolving (D0129/issue071). A change-impact view built exactly to that Need would have reported zero dependents for all three, confidently. THIRD: nServeLaunchDefinedOnly forbids at the boundary the exact case CLAUDE.md section 3 requires — defining a new process when a request maps to none — with no stated path between them. READ BACK: Need coverage 8 -> 13 of 39. validate 353 clean; 34 guards ALL PASS."; }
        part storyCritPass2DoDR1 : TestResult { :>> id = "0d800402-0814-6402-9b3e-000000300402"; :>> outcome = VerdictKind::pass; :>> judgedAgainst = "ee5a7a3"; :>> judgedAt = "2026-08-17"; :>> judgedBy = "claudeOpus5"; }
    }

    verification c2RefineGate : Test { :>> id = "0d800403-0814-6403-9b3e-000000300403"; :>> title = "Sprint 325 refine gate (DoR)"; :>> createdAt = "2026-08-17"; :>> createdBy = "claudeOpus5"; :>> method = VerificationMethod::inspect; :>> procedureText = "DoR. THE TARGET SELECTION WAS NEARLY WRONG AND A TOOL DEFECT CAUGHT IT LATE: my target-picking helper reported all 31 remaining uncovered Needs as critiquable with 0 blocked, which contradicted the measurement taken one sprint earlier (20 wweatherholtz, 16 claudeOpus5). Two bugs in the same lookup: the createdBy pattern was anchored to end-of-line and several files put createdAt and createdBy on ONE line, and the record was pre-seeded with createdBy '?' so the fill loop's not-in-record test skipped it forever. Fixed, and the honest number came back: 15 critiquable, 16 blocked. I checked the first target's file by hand before writing anything, which is what exposed it. estimatedPoints=3."; }
    part c2RefineGateR1 : TestResult { :>> id = "0d800404-0814-6404-9b3e-000000300404"; :>> outcome = VerdictKind::pass; :>> judgedAgainst = "ee5a7a3"; :>> judgedAt = "2026-08-17"; :>> judgedBy = "claudeOpus5"; }

    verification c2StandupGate : Test { :>> id = "0d800405-0814-6405-9b3e-000000300405"; :>> title = "Sprint 325 standup gate"; :>> createdAt = "2026-08-17"; :>> createdBy = "claudeOpus5"; :>> method = VerificationMethod::inspect; :>> procedureText = "Approach: move the batch writer into a reusable script that refuses a procedureText containing a double quote (which would silently truncate the attribute) and refuses to append if critiques.sysml does not end in a closing brace, so a malformed append cannot corrupt the file. Batch content authored as JSON rather than inline in a shell heredoc, which is the fourth-time-recorded remedy for quoting failures. No blockers."; }
    part c2StandupGateR1 : TestResult { :>> id = "0d800406-0814-6406-9b3e-000000300406"; :>> outcome = VerdictKind::pass; :>> judgedAgainst = "ee5a7a3"; :>> judgedAt = "2026-08-17"; :>> judgedBy = "claudeOpus5"; }

    verification c2ImplementGate : Test { :>> id = "0d800407-0814-6407-9b3e-000000300407"; :>> title = "Sprint 325 implement gate"; :>> createdAt = "2026-08-17"; :>> createdBy = "claudeOpus5"; :>> method = VerificationMethod::analyze; :>> procedureText = "FOUR LENSES PASSED, up from one last pass, and the shift is informative rather than a softening: the serve-discipline Needs are mechanically precise where the viewer Needs are aspirational. nServeReuseModel's testability passes because the property is a genuine set equivalence with an obvious falsifier — add a process to the model and it must appear with no code change — and that same test, had it been written against VIEW_SUBCOMMANDS as well as the launchable set, would have caught the defect its own correctness lens found. That is the most useful thing a critique pass produced today: a Need whose test exists in principle, was never written, and whose absence is exactly why the violation survived. WHERE A PASS IS NARROWER THAN THE WORDS I said so in the record: nServeLaunchDefinedOnly's testability passes for the SELECTION boundary, while its strong claim that 'invalid actions are unrepresentable' quantifies over everything a spawned agent might do and is untestable in that reading."; }
    part c2ImplementGateR1 : TestResult { :>> id = "0d800408-0814-6408-9b3e-000000300408"; :>> outcome = VerdictKind::pass; :>> judgedAgainst = "ee5a7a3"; :>> judgedAt = "2026-08-17"; :>> judgedBy = "claudeOpus5"; }

    verification c2ReviewGate : Test { :>> id = "0d800409-0814-6409-9b3e-000000300409"; :>> title = "Sprint 325 review gate"; :>> createdAt = "2026-08-17"; :>> createdBy = "claudeOpus5"; :>> method = VerificationMethod::inspect; :>> procedureText = "Reviewed. NO ISSUE WAS RAISED FOR THE VIEW_SUBCOMMANDS DRIFT, and the reasoning is worth stating because it is a close call: the hardcoded list is a real violation of a must-priority Need, which argues for tracking it. Against that — the list is the viewpoint-renderer guard's own vocabulary of valid keel commands, and deriving it from the model is circular (the model's renderers are what it validates), so the correct source is the BINARY's own subcommand table, which is a real refactor and not a defect fix. Recording it as an Issue would put a design change on the frontier under the guise of a bug. It is recorded where it belongs: in a failing critique against the Need it violates, with the evidence quoted, which is what makes it findable when someone builds the launchable-set reader that Need actually asks for. Same reasoning as pass 1 — a failing critique IS the finding, and duplicating it as an Issue is dual truth."; }
    part c2ReviewGateR1 : TestResult { :>> id = "0d80040a-0814-640a-9b3e-00000030040a"; :>> outcome = VerdictKind::pass; :>> judgedAgainst = "ee5a7a3"; :>> judgedAt = "2026-08-17"; :>> judgedBy = "claudeOpus5"; }

    verification c2CloseOutGate : Test { :>> id = "0d80040b-0814-640b-9b3e-00000030040b"; :>> title = "Sprint 325 closeOut gate (autonomous, D0049)"; :>> createdAt = "2026-08-17"; :>> createdBy = "claudeOpus5"; :>> method = VerificationMethod::inspect; :>> procedureText = "Autonomous closeOut (D0049). Need coverage 8 -> 13 of 39. Remaining critiquable: 10 Needs, 25 SystemRequirements, 22 Decisions; 87 elements stay blocked on a critic who is not claudeOpus5. Zero open issues; ready frontier empty; D0159 queued. validate 353 clean; check-engine clean; 34 guards ALL PASS; no code changed."; }
    part c2CloseOutGateR1 : TestResult { :>> id = "0d80040c-0814-640c-9b3e-00000030040c"; :>> outcome = VerdictKind::pass; :>> judgedAgainst = "ee5a7a3"; :>> judgedAt = "2026-08-17"; :>> judgedBy = "claudeOpus5"; }

    verification c2RetroGate : Test { :>> id = "0d80040d-0814-640d-9b3e-00000030040d"; :>> title = "Sprint 325 retro gate (autonomous, D0049)"; :>> createdAt = "2026-08-17"; :>> createdBy = "claudeOpus5"; :>> method = VerificationMethod::analyze; :>> procedureText = "Autonomous retro (D0049) under D0131's retroTrack. WELL: (1) I noticed my own tool's number contradicted the previous sprint's measurement and checked the source file by hand instead of trusting the newer answer — the newer answer was the wrong one, and taking it would have spent a whole pass on 15 critiques the policy discards; (2) the batch writer now REFUSES a text containing a double quote and refuses to append to a file that does not end in a closing brace, so the two ways this write could corrupt the model are checked rather than remembered; (3) the near-miss on VVIEW_SUBCOMMANDS was recorded as a critique with quoted evidence rather than promoted to an Issue, and the reasoning for that call is in the review gate where someone can disagree with it. AVOIDABLE-ISSUE: the helper's two-bug author lookup. Both bugs made the same false claim — that everything is critiquable — and the shape is the session's most common one AGAIN: a check narrower or wider than its subject, reported with confidence. The control that caught it was cross-checking against a number measured a different way one sprint earlier, which is the only thing that catches a confidently-wrong measurement. NO NEW ITEM: the helper is a scratch tool outside the model, not a committed control. Estimate 3 pts, delivered."; }
    part c2RetroGateR1 : TestResult { :>> id = "0d80040e-0814-640e-9b3e-00000030040e"; :>> outcome = VerdictKind::pass; :>> judgedAgainst = "ee5a7a3"; :>> judgedAt = "2026-08-17"; :>> judgedBy = "claudeOpus5"; }
}
