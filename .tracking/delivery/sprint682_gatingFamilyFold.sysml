// ProjectDeliveryS682 — Sprint 682: The gating family joins keel gate and keel audit. Under D0452 (accepted on the human's own words 2026-09-12, brief copy-out) the ten gating verbs that are not already routers - validate, check, check-engine, guard, rules, assured, adoption-check, audit-history, audit-adherence, audit-ci-runs - leave the top-level dispatch and become sub-verbs of `keel gate` (validate, check, check-engine, guard, rules, assured, adoption-check) and `keel audit` (history, adherence, ci-runs), each keeping its word and its arguments, in the sprint 512 shape (D0273): a committed transform rewrites every call site in the same commit as the removal, no alias window, and the pre-fold binary is held byte-equal to the post-fold binary on stdout, stderr and exit code over a green tree, a red tree and a workspace root, because a gate's exit code is its answer. The hooks under .githooks and the workflows under .github/workflows are rewritten in the same commit and exercised by it. Delivers the fourth of the five folds dcRemainingCliFamilies names; the dispatch count hardening reads drops 49 to 39. CHANGE.. EXECUTE. 8 pts.
package ProjectDeliveryS682 {
    private import EngineElement::*;
    private import EngineWork::*;
    private import EngineVerification::*;
    private import EngineRelationships::*;

    #CharteredBy dependency from gatingFamilyFoldStory to d0452;

    part gatingFamilyFoldStory : Story {
        :>> id = "a229c6e1-e1dd-4c67-9fad-17e5c7cc85aa";
        :>> title = "Sprint 682: The gating family joins keel gate and keel audit. Under D0452 (accepted on the human's own words 2026-09-12, brief copy-out) the ten gating verbs that are not already routers - validate, check, check-engine, guard, rules, assured, adoption-check, audit-history, audit-adherence, audit-ci-runs - leave the top-level dispatch and become sub-verbs of `keel gate` (validate, check, check-engine, guard, rules, assured, adoption-check) and `keel audit` (history, adherence, ci-runs), each keeping its word and its arguments, in the sprint 512 shape (D0273): a committed transform rewrites every call site in the same commit as the removal, no alias window, and the pre-fold binary is held byte-equal to the post-fold binary on stdout, stderr and exit code over a green tree, a red tree and a workspace root, because a gate's exit code is its answer. The hooks under .githooks and the workflows under .github/workflows are rewritten in the same commit and exercised by it. Delivers the fourth of the five folds dcRemainingCliFamilies names; the dispatch count hardening reads drops 49 to 39. CHANGE. (8 pts)";
        :>> createdAt = "2026-09-12"; :>> createdBy = "claudeFable5"; :>> kind = WorkKind::code; :>> priority = WorkPriority::p0; :>> owner = "claudeFable5"; :>> estimatedPoints = 8;
    }

    action def DeliveryRunS682 {
        action storyGatingFamilyFold;
        verification storyGatingFamilyFoldDoD : Test { :>> id = "8b7da7fe-386c-4531-a46e-3a29dbd55aef"; :>> method = VerificationMethod::test; :>> procedureText = "DELIVERED: `keel gate <sub-verb> ...` answers for validate, check, check-engine, guard, rules, assured and adoption-check and `keel audit history|adherence|ci-runs ...` for the three audits, arguments unchanged; `keel gate` bare, --fast and --workspace keep their meaning and the router resolves a reserved sub-verb before it reads a positional as a root; `keel audit [ROOT]` keeps its meaning bare. The ten top-level arms are gone from main.rs and COMMAND_NAMES (48 to 38); the ten CliCommand facts are removed from both homes and the gate and audit facts' invocations name their sub-verbs (99 facts to 89, cli-surface-declared equal). Every call site under .githooks, .github/workflows, .engine, CLAUDE.md, README.md, docs, scripts, keel-cli/assets and the Rust prose is rewritten by .engine/tools/migrations/2026-09-12-gating-family-fold.py (dry-run default, per-verb per-file conservation, re-plan 0); the Rust argv sites by a hand list each asserted to hit once; .claude regenerated by keel sync-claude. The pre-fold binary keel-prefold682.exe (build fc89e6a) and the post-fold binary agree on every case of the three-tree comparison - a green tree, a red tree and a workspace root - on stdout, stderr and exit code on every verdict-bearing case (red validate 1/1, gate --fast 1/1, workspace refusals 2/2); the differences are exactly five classes and each is read from the logs, not assumed: a usage or refusal line that names the command (`keel gate validate: --read looks like a flag`); the routers' own usage text, which now lists the sub-verbs; the --help surface, ten entries shorter; the build stamp; and the pre-fold binary's cli-surface-declared violations against the post-fold facts, the same skew that makes the post-fold binary judge pre-fold commits red under audit history (issue504). The gating-workflow-history guard's needles follow the new spellings and are probed. The control structure's keel_commands_in reads a routed sub-verb so a hook's data names `gate validate`, not `gate`. hardening reads dispatched 39/39. The commit passes its own rewritten pre-commit hook and its own rewritten CI. Decisions and .tracking are not rewritten; ledger ids validate, check-engine and guard are kept as ids."; }
        // RAN: compare682.py three trees (cmp_green.log SAME 13 DIFF 10, cmp_red.log SAME 12 DIFF 10, cmp_ws.log SAME 4 DIFF 14, every DIFF in one of the five DoD classes, verdict exits equal); keel show hardening . 39/39; COMMAND_NAMES 48 to 38 and CLI_FACTS 99 to 89 counted at fc89e6a vs the tree; cargo test --release --test gating_workflow_history_reads_routed_spelling 3 passed, --test capability_refusal_bites 8 passed, --test unknown_flag_is_refused 4 passed; keel suite --touched 792/0 (touched-receipt.toml at 1789207539); the rewritten pre-commit hook runs at the commit; the rewritten CI is read back by conclusion after the push
        part storyGatingFamilyFoldDoDR1 : TestResult { :>> id = "22822061-81eb-46fc-bf88-eeec5ee1aa83"; :>> outcome = VerdictKind::pass; :>> judgedAgainst = "6821b5c"; :>> judgedAt = "2026-09-12"; :>> judgedBy = "claudeFable5"; }
    }

    verification gatingFamilyFoldRefineGate : Test { :>> id = "1c92ddad-5437-4fe1-bca4-8f982b8c0cbd"; :>> title = "Sprint 682 refine gate (DoR)"; :>> createdAt = "2026-09-12"; :>> createdBy = "claudeFable5"; :>> method = VerificationMethod::inspect; :>> procedureText = "Chartered by D0452, accepted by the human on the brief copy-out 2026-09-12 (d0452AcceptR1). Eight points, as D0452 sized it: ten dispatch arms move under two routers with their bodies untouched, two routers gain sub-verb resolution ahead of their positional root, one constant array shrinks, ten facts leave two homes and two facts grow, one Python transform over prose in six roots plus the hooks and workflows and the python list shape scripts use, some eighty Rust argv sites by hand list, one guard's needle list, one view reader, and a three-tree comparison where the exit code is the answer. The largest of the five folds because the verbs sit on the enforcement surface: a wrong hook line blocks every commit including the fix. NOT A PROCESS CHANGE beyond what D0452 states - the fold is the Decision's own text; the co-committed marker Decision is D0452's enumerated step under D0396. NOT A FORK - the fork was d0399 and is decided."; }
    // RAN: keel show authority-queue . at 6821b5c: d0452 absent from decisionAcceptance (accepted by the human, d0452AcceptR1, brief copy-out 2026-09-12); keel show whats-next .: dcRemainingCliFamilies at the head of the ready list; #CharteredBy edge from gatingFamilyFoldStory to d0452 validates; estimatedPoints 8 as D0452 sized it
    part gatingFamilyFoldRefineGateR1 : TestResult { :>> id = "25947dd1-eeeb-4599-9aa2-932cf6925c7e"; :>> outcome = VerdictKind::proposed; :>> judgedAgainst = "6821b5c"; :>> judgedAt = "2026-09-12"; :>> judgedBy = "claudeFable5"; }
    verification gatingFamilyFoldStandupGate : Test { :>> id = "0e89b93a-66af-4ac2-b2ce-8c7e9bd7959d"; :>> title = "Sprint 682 standup gate"; :>> createdAt = "2026-09-12"; :>> createdBy = "claudeFable5"; :>> method = VerificationMethod::inspect; :>> procedureText = "Order, taken from the 678-680 retros: preserve the pre-fold binary FIRST as keel-prefold682.exe from the landed fc89e6a build; remove the ten arms from main() and route them from cmd_gate and cmd_audit, each old line asserted unique; shrink COMMAND_NAMES and remove the ten facts from both homes while growing gate and audit in one script so cli-surface-declared stays equal; sweep every control bound to a verb's spelling before the transform runs (the 680 retro's class: K7 read one token) - guards.rs gating-workflow-history needles, control_structure.rs keel_commands_in, hardening.rs help assertions; rewrite Rust argv sites by a hand list each asserted to hit once; run the transform dry then apply; sync-claude; rebuild; compare old against new on three trees; read hardening back. Blocker met at refine: D0452's acceptance landed in 6821b5c, one commit before the change it authorises, so the keystone lock (D0209 cl.2) sees no staged marked Decision - resolved by D0396: a marker Decision recorded with plan d0452 and the step D0452's consequences enumerate is accepted at record time under the human's own signature on the plan."; }
    // RAN: cp target/release/keel.exe target/release/keel-prefold682.exe before any edit (keel-prefold682.exe version reads fc89e6a); census.py over main.rs: ten arms each found once; the keystone lock read at refine - guards.rs staged_marked_decision (line 1220) requires a changed .engine/decisions/*.sysml carrying a line-anchored #ProspectiveChange/#SafetyChange in the same commit as the hook edits, and d0452 landed in 6821b5c - resolved by d0455 recorded with marker safety-change plan d0452 (accepted at record time under D0396)
    part gatingFamilyFoldStandupGateR1 : TestResult { :>> id = "2547c7d1-b897-4213-aed0-023809ab57c0"; :>> outcome = VerdictKind::proposed; :>> judgedAgainst = "6821b5c"; :>> judgedAt = "2026-09-12"; :>> judgedBy = "claudeFable5"; }
    verification gatingFamilyFoldImplementGate : Test { :>> id = "4279d1d2-a8f2-434d-a938-fd366fec2f19"; :>> title = "Sprint 682 implement gate"; :>> createdAt = "2026-09-12"; :>> createdBy = "claudeFable5"; :>> method = VerificationMethod::test; :>> procedureText = "DELIVERED: main.rs ten arms removed, dispatch_arms reads 39; cmd_gate and cmd_audit resolve a reserved sub-verb ahead of the positional root and hand the untouched functions their remaining argv; print_gate_usage names the seven sub-verbs and the two tiers; COMMAND_NAMES 38; cli_facts.rs and commands.sysml lose ten facts and the gate and audit invocations name their sub-verbs (89 facts, the audit fact's own `[ROOT]` moved to the trailing alternative because the sub-verb reader cancels on a non-verb opener - issue506); the guards.rs gating-workflow-history needles read `keel gate` and `keel audit` with a D0388 pair in tests/gating_workflow_history_reads_routed_spelling.rs (3/3); control_structure.rs keel_commands_in emits `gate validate` for a routed sub-verb; adoption_check.rs, migrate.rs and the test argv sites rewritten by a hand list each asserted to hit once; the transform .engine/tools/migrations/2026-09-12-gating-family-fold.py applied 302 sites across 91 files with per-verb per-file conservation and re-plan 0; scripts/exec_brief/facts.py counts the three routers as the gating invocations; README.md's command table and .engine/docs/guards.md swept by hand for bare verbs the `keel <verb>` rule could not see (issue505); keel sync-claude regenerated .claude; d0455 recorded as the plan-covered marker Decision (D0396) with a #DependsOn edge to d0452."; }
    // RAN: python .engine/tools/migrations/2026-09-12-gating-family-fold.py --dry-run then --apply: 302 sites / 91 files, conservation reconciled per verb per file, re-plan 0; fold682_rust.py hand list each anchor asserted once; cargo build --release -p keel-cli after [CliFact; 99] -> 89; keel show hardening .: dispatched 39 namedInHelp 39; keel sync-claude . then --check clean; cargo test --release --test capability_refusal_bites 8 passed (the_gate_and_audit_sub_verbs_match_their_facts after the audit [ROOT] moved to the trailing alternative); --test gating_workflow_history_reads_routed_spelling 3 passed; keel gate validate . 781 clean; keel gate check-engine . clean after d0455
    part gatingFamilyFoldImplementGateR1 : TestResult { :>> id = "f4c8e082-579a-46aa-82d8-ce24c0605e45"; :>> outcome = VerdictKind::pass; :>> judgedAgainst = "6821b5c"; :>> judgedAt = "2026-09-12"; :>> judgedBy = "claudeFable5"; }
    verification gatingFamilyFoldReviewGate : Test { :>> id = "8be6a3e1-438a-4b71-b3df-a195a249c859"; :>> title = "Sprint 682 review gate — three passes per D0172"; :>> createdAt = "2026-09-12"; :>> createdBy = "claudeFable5"; :>> method = VerificationMethod::inspect; :>> procedureText = "DELIVERED: three-tree comparison (compare682.py, 23 pairs) - green SAME 13 DIFF 10, red SAME 12 DIFF 10, workspace SAME 4 DIFF 14; every DIFF read and placed in one of the five classes the DoD names; the red tree's injected violation (an unresolved import and type in .tracking/red.sysml, after a duplicate part name and an unknown actor both validated clean) is refused 1/1 by both binaries. hardening dispatched 39 namedInHelp 39 read back from keel show hardening. D0388 pairs: guard needles 3/3 (a shallow workflow running `keel gate validate` and one running `keel audit history` are violations naming ci.yml; the full checkout is scanned and clean), keel_commands_in unit test, capability_refusal_bites 8/8 including the_gate_and_audit_sub_verbs_match_their_facts. clippy clean. Findings carried to the retro: issue504 (audit history skew), issue505 (README table), issue506 (sub-verb reader)."; }
    // RAN: compare682.py (23 pairs, keel-prefold682.exe fc89e6a vs keel-serve.exe 6821b5c+dirty) logs cmp_green.log SAME 13 DIFF 10, cmp_red.log SAME 12 DIFF 10, cmp_ws.log SAME 4 DIFF 14; every DIFF read and classified into the five DoD classes; verdict exits equal (red validate 1/1, gate --fast 1/1, workspace refusals 2/2, audit-history 0/0 with the skew visible as FAIL rows - issue504); cargo clippy --release -p keel-cli -- -D warnings clean; subverb_census.py: only audit and render differ between the strict and relaxed readers (issue506)
    part gatingFamilyFoldReviewGateR1 : TestResult { :>> id = "5c7d6709-1cb0-4f86-88fb-32aa3115262e"; :>> outcome = VerdictKind::proposed; :>> judgedAgainst = "6821b5c"; :>> judgedAt = "2026-09-12"; :>> judgedBy = "claudeFable5"; }
    verification gatingFamilyFoldCloseOutGate : Test { :>> id = "b6151472-403f-475a-b702-cae9e1d0c5dd"; :>> title = "Sprint 682 closeOut gate (autonomous, D0049)"; :>> createdAt = "2026-09-12"; :>> createdBy = "claudeFable5"; :>> method = VerificationMethod::inspect; :>> procedureText = "DELIVERED: closes on the three-tree comparison, the hardening read-back, gate validate (781 clean), gate check-engine, gate guard --no-receipt, sync-claude --check, clippy, the surface and refusal tests and the touched suite run by the VERIFIER (D0425/D0438), receipt in the closeOut result. The co-committed marker Decision is d0455 (plan-covered by d0452, D0396). dcRemainingCliFamilies stays open: one fold remains, D0453 (sprint 683), whose comparison must re-run the audit-history row against issue504's fix or read the skew."; }
    // RAN: VERIFIER receipts verifier_receipt.md and verifier_receipt2.md (haiku, skill test-verify, D0425/D0438): keel suite --touched . first run outcome fail 790/2 (unknown_flag_is_refused: keel gate gate --read from the hand list; the new probe asserting a count by substring), both fixed, second run touched-receipt.toml outcome pass passed 792 failed 0 at 1789207539 head 6821b5c stems 28; keel gate validate . 781 clean; keel gate check-engine . clean; keel gate guard --no-receipt . ALL PASS 316 warnings 0 violations; keel sync-claude --check . clean; keel gate rules --enforce . pass; cargo clippy -D warnings clean; keel show hardening . dispatched 39 namedInHelp 39
    part gatingFamilyFoldCloseOutGateR1 : TestResult { :>> id = "246db568-f344-4ac9-b888-15b1bcc4a0c4"; :>> outcome = VerdictKind::proposed; :>> judgedAgainst = "6821b5c"; :>> judgedAt = "2026-09-12"; :>> judgedBy = "claudeFable5"; }
    verification gatingFamilyFoldRetroGate : Test { :>> id = "309a2864-15b7-49b8-94d1-6c58be9d44c5"; :>> title = "Sprint 682 retro gate (autonomous, D0049)"; :>> createdAt = "2026-09-12"; :>> createdBy = "claudeFable5"; :>> method = VerificationMethod::analyze; :>> procedureText = "AVOIDABLE-ISSUE SCAN, three findings, three tracked items (D0131): (1) audit history with the post-fold binary judged all three pre-fold commits FAIL on cli-surface-declared, a skew of the binary against a tree it was not built from, not a verdict about the commit - issue504, resolver dcAuditHistoryLabelsTheBinarysSkew (SKEW label, D0388 pair); (2) README.md's command table named `orient` and `whats-next` bare through three folds because the transform rule reads `keel <verb>` and no guard reads documents - issue505, resolver dcScriptCallersOfTheCliAreHeldToTheSurface extended to the document surface; (3) the sub-verb reader cancels on a non-verb opener so the audit fact's `[ROOT]` had to trail, and relaxing it would misread render - issue506, resolver dcSubVerbEffectIsDeclared extended to declare the list. Caught by existing controls, so no new item: the VERIFIER touched suite (D0432) failed 2 of 792 - the hand list had rewritten unknown_flag_is_refused.rs by prepending the router to BOTH the verb list and the argv builder, producing `keel gate gate --read`, and the new probe asserted a non-zero scanned count by substring, which the no_test_asserts_a_count_by_substring meta-test refuses; both fixed and re-run 4/4 and 3/3, the touched suite re-run by a second VERIFIER. Not tracked, and why: the compare script's ten-minute timeout on the workspace tree was the scratch harness's, not the engine's; the duplicate-part-name and unknown-actor probes that validated clean are already dcAnEditCannotNestAnItemByAccident's class (validate is a resolution check, not a census). What went right: preserving the pre-fold binary FIRST and sweeping spelling-bound controls BEFORE the transform (the 678-680 retros' order) meant the guard needles moved with the verbs and the pair caught the scaffold's second workflow in its scanned count rather than a silent zero."; }
    // RAN: keel record issue x3 (issue504 Medium, issue505 Low, issue506 Low, each with a #Resolves edge at record time); keel record task dcAuditHistoryLabelsTheBinarysSkew; textpatch replace on the DoDs of dcScriptCallersOfTheCliAreHeldToTheSurface and dcSubVerbEffectIsDeclared; keel gate guard issues . PASS 515 scanned after the resolver DoD named issue504 (the guard refused the unnamed edge first)
    part gatingFamilyFoldRetroGateR1 : TestResult { :>> id = "5e91c9f4-e870-45fa-ae74-044d07fcaab3"; :>> outcome = VerdictKind::proposed; :>> judgedAgainst = "6821b5c"; :>> judgedAt = "2026-09-12"; :>> judgedBy = "claudeFable5"; }
}
