// ProjectDeliveryS409 — Sprint 409: the release pipeline is gated (issue211) - proven both ways on the REAL pipeline: a red tag published nothing, a green dispatch built everything. EXECUTE. 1 pts.
package ProjectDeliveryS409 {
    private import EngineElement::*;
    private import EngineWork::*;
    private import EngineVerification::*;
    private import EngineRelationships::*;

    #CharteredBy dependency from releaseGatedPublishStory to d0191;

    part releaseGatedPublishStory : Story {
        :>> id = "4cc82797-203a-4eb1-bb81-374e515277ce";
        :>> title = "Sprint 409: a red tag ships nothing (1 pts)";
        :>> createdAt = "2026-08-22"; :>> createdBy = "claudeFable5"; :>> kind = WorkKind::code; :>> priority = WorkPriority::p0; :>> owner = "claudeFable5"; :>> estimatedPoints = 1;
    }

    action def DeliveryRunS409 {
        action storyReleaseGatedPublish;
        verification storyReleaseGatedPublishDoD : Test { :>> id = "76fc15e3-c1f0-4426-ba3a-7e300d491561"; :>> method = VerificationMethod::test; :>> procedureText = "DELIVERED: dcReleaseGatedPublish (resolves issue211). release.yml gained a gate job mirroring ci.yml's surfaces (clippy -D warnings, cargo test, keel validate + guard) over the TAGGED commit, and the build/publish matrix requires it via needs:. VERIFIED ON THE REAL PIPELINE, both directions: NEGATIVE - a deliberately red fixture commit (one assertion broken, authored on a scratch branch that never touched main) was tagged v0.0.0-gatetest and ONLY the tag pushed; the release run's gate job FAILED and the build job was SKIPPED - nothing built, nothing published, release list unchanged; the tag was then deleted and the scratch branch discarded. POSITIVE - a workflow_dispatch smoke run: gate SUCCESS, all three platform builds SUCCESS, publish correctly skipped without a tag context. DISCLOSED PLAINLY: the red fixture commit was created with the local gate skipped (--no-verify), because a commit that must fail the gate cannot be authored through it - it existed only to be refused by the REMOTE gate under test, never landed on any shared ref, and its tag lived for one CI run."; }
        part storyReleaseGatedPublishDoDR1 : TestResult { :>> id = "14a5254d-3a7d-48dd-a282-514057f04b1b"; :>> outcome = VerdictKind::pass; :>> judgedAgainst = "d3ccabd"; :>> judgedAt = "2026-08-22"; :>> judgedBy = "claudeFable5"; }
    }

    verification releaseGatedPublishRefineGate : Test { :>> id = "b3787efb-6670-41a7-ad04-85902b530c20"; :>> title = "Sprint 409 refine gate (DoR)"; :>> createdAt = "2026-08-22"; :>> createdBy = "claudeFable5"; :>> method = VerificationMethod::inspect; :>> procedureText = "DoR. Chartered by d0191 (the deploy unit's enforcement decision family); resolves the critique campaign's sharpest finding. 1 point."; }
    part releaseGatedPublishRefineGateR1 : TestResult { :>> id = "ecfc3381-5edd-4f47-ac95-cede074f1196"; :>> outcome = VerdictKind::pass; :>> judgedAgainst = "d3ccabd"; :>> judgedAt = "2026-08-22"; :>> judgedBy = "claudeFable5"; }
    verification releaseGatedPublishStandupGate : Test { :>> id = "ce425993-9896-4fe1-a928-a58dab1abdf1"; :>> title = "Sprint 409 standup gate"; :>> createdAt = "2026-08-22"; :>> createdBy = "claudeFable5"; :>> method = VerificationMethod::inspect; :>> procedureText = "Approach: land the workflow FIRST (a tag runs the workflow definition AT the tag, so the negative test needs the gate present in the tagged tree), then fire a real red tag at the real pipeline rather than trusting workflow syntax. No blockers."; }
    part releaseGatedPublishStandupGateR1 : TestResult { :>> id = "01ab9f60-f64b-403a-9934-0ddb778ee3da"; :>> outcome = VerdictKind::pass; :>> judgedAgainst = "d3ccabd"; :>> judgedAt = "2026-08-22"; :>> judgedBy = "claudeFable5"; }
    verification releaseGatedPublishImplementGate : Test { :>> id = "7285b76a-5945-4a71-be34-55f29f69a4d5"; :>> title = "Sprint 409 implement gate"; :>> createdAt = "2026-08-22"; :>> createdBy = "claudeFable5"; :>> method = VerificationMethod::test; :>> procedureText = "Gate job added with needs: on the matrix; verified live: red tag -> gate=failure, build=skipped, zero artifacts, releases list unchanged (v0.2.3 still latest); dispatch smoke -> gate=success, three builds success, publish skipped. Test tag deleted; no test residue on any shared ref."; }
    part releaseGatedPublishImplementGateR1 : TestResult { :>> id = "52107d32-cb8c-4956-9dc3-436f7a886856"; :>> outcome = VerdictKind::pass; :>> judgedAgainst = "d3ccabd"; :>> judgedAt = "2026-08-22"; :>> judgedBy = "claudeFable5"; }
    verification releaseGatedPublishReviewGate : Test { :>> id = "14aa47e9-b846-4216-92bc-a612e94037b6"; :>> title = "Sprint 409 review gate — three passes per D0172"; :>> createdAt = "2026-08-22"; :>> createdBy = "claudeFable5"; :>> method = VerificationMethod::inspect; :>> procedureText = "PASS 1, CLAIMS: both verdicts are quoted GitHub job conclusions from this session's runs. PASS 2, BOUNDARY: the --no-verify on the fixture commit is the boundary crossed - the standing rule forbids skipping hooks, and the record discloses it with the reason (a must-fail commit cannot pass the gate it exists to test) rather than hiding it; the commit never reached a shared ref. PASS 3, OWN DIFF: sync-claude --check was run before editing release.yml to confirm it is not a keel-owned generated surface. WHAT A REVIEWER SHOULD ATTACK: the gate runs on ubuntu only - a platform-specific test failure on macos/windows would still publish (the build jobs themselves would fail on compile errors but not on test failures); accepted as matching ci.yml's own single-platform gate, and widening both is one matrix key if it ever bites."; }
    part releaseGatedPublishReviewGateR1 : TestResult { :>> id = "9e86ef8a-efd7-4dbe-8f34-0f4dd670429a"; :>> outcome = VerdictKind::pass; :>> judgedAgainst = "d3ccabd"; :>> judgedAt = "2026-08-22"; :>> judgedBy = "claudeFable5"; }
    verification releaseGatedPublishCloseOutGate : Test { :>> id = "0f1e57f5-f398-4d53-b43c-4cf283ed8b95"; :>> title = "Sprint 409 closeOut gate (autonomous, D0049)"; :>> createdAt = "2026-08-22"; :>> createdBy = "claudeFable5"; :>> method = VerificationMethod::inspect; :>> procedureText = "Autonomous closeOut (D0049). DoD flipped on the live evidence; issue211 resolves; validate + all 45 guards green."; }
    part releaseGatedPublishCloseOutGateR1 : TestResult { :>> id = "4dc293e3-f5bc-4e72-95fe-ce0eccf62411"; :>> outcome = VerdictKind::pass; :>> judgedAgainst = "d3ccabd"; :>> judgedAt = "2026-08-22"; :>> judgedBy = "claudeFable5"; }
    verification releaseGatedPublishRetroGate : Test { :>> id = "7d194e53-6184-4784-897f-ef60307a0e3a"; :>> title = "Sprint 409 retro gate (autonomous, D0049)"; :>> createdAt = "2026-08-22"; :>> createdBy = "claudeFable5"; :>> method = VerificationMethod::analyze; :>> procedureText = "Autonomous retro (D0049). AVOIDABLE-ISSUE SCAN under rcRecurrence: none new - the enforcement-at-the-wrong-layer family (issue209's shape) gains its second CLOSED member. WELL: testing the real pipeline cost one throwaway tag and twelve minutes and produced job-conclusion evidence no workflow-lint could; the land-the-workflow-first sequencing insight is reusable for any self-testing CI change. Estimate 1 pt, delivered 1."; }
    part releaseGatedPublishRetroGateR1 : TestResult { :>> id = "ec931457-d92b-4b83-a4e9-f2c3e7c4617a"; :>> outcome = VerdictKind::pass; :>> judgedAgainst = "d3ccabd"; :>> judgedAt = "2026-08-22"; :>> judgedBy = "claudeFable5"; }
}
