// ProjectDeliveryS200 — Sprint 200: researchSpikeCharterRule (D0111/issue055) — the enforceable slice of
// research-spike routing. A declared WARNING-level rule: a WorkKind::research spike must charter to a
// legitimate governing source (Decision/Need/SystemRequirement/Issue), via a new whereKind scope +
// charterTargetType predicate. This is PART 2 of proveProcessDeployment (issue061); part 1 (dogfooding the
// business-architecture skill on a real design session) remains, so issue061 stays OPEN. CHANGE (rule/
// control) — governed by d0111. 2 pt. AUTONOMOUS (D0049).
package ProjectDeliveryS200 {
    private import EngineElement::*;
    private import EngineWork::*;
    private import EngineVerification::*;
    private import EngineRequirements::*;
    private import EngineRelationships::*;

    #CharteredBy dependency from researchSpikeCharterRuleStory to d0111;

    part researchSpikeCharterRuleStory : Story {
        :>> id = "63940516-2c7d-4e8f-c200-51627384c001";
        :>> title = "Sprint 200: researchSpikeCharterRule (2 pt) - declared warning-level control on research-spike charter (D0111/issue055)";
        :>> createdAt = "2026-07-09"; :>> createdBy = "wweatherholtz"; :>> kind = WorkKind::code; :>> priority = WorkPriority::p2; :>> owner = "claudeOpus"; :>> estimatedPoints = 2;
    }

    action def DeliveryRunS200 {
        action storyResearchSpikeCharter;
        verification storyResearchSpikeCharterDoD : Test { :>> id = "63940516-2c7d-4e8f-c200-51627384c002"; :>> method = VerificationMethod::test; :>> procedureText = "Delivers D0111 (issue055 fix (3); PART 2 of proveProcessDeployment/issue061): convert engine-triage item-8's research-spike routing CONVENTION into a declared control on the structurally-visible side. (1) view.rs: add whereKind(v) scope to subject_in_scope (mirrors whereStatus; reads the WorkKind member) + a charterTargetType(T1,...) ElementRule predicate term (every outgoing #CharteredBy edge targets an allow-listed type; vacuously true when unchartered — charterRule owns existence). (2) researchSpikeCharterRule (.engine/rules): ElementRule, subjectType Story, appliesWhen whereKind(research), predicate charterTargetType(Issue,Decision,Need,SystemRequirement) — the exact union guards.rs:376 sanctions (D0068/issue055); WARNING-level (non-gating, D0102 precedent); #JustifiedBy d0111. (3) D0047 control: unit test element_rule_flags_research_spike_bad_charter (a spike chartered to a Story IS flagged; Decision/Need/SR/Issue pass; non-research out of scope). ALLOW-LIST widened mid-implement: the first cut (Issue|Decision) spuriously flagged sr19SpikeStory (a legit SystemRequirement charter) — corrected to D0068. doc-sync: CLAUDE.md Sec 5 (declarative-controls paragraph) + engine-triage SKILL item 8 (0.5.0->0.6.0). SCOPE HONESTY: this is the artifact-side slice; the 'did substantial analysis skip the spike?' judgment is un-gatable at commit (reminder-enforced, exactly as issue059 left D0106's parse-first) -> issue061 stays OPEN (part 1 = a real design session), not overclaimed. Guard count UNCHANGED (15 — not a new blocking guard). VERIFY: clippy -D warnings clean; cargo test (view unit tests, incl. the new one) green; keel validate + guard all (15) green; `keel rules` shows researchSpikeCharterRule evaluated=true, 0 violations on the live repo."; }
        part storyResearchSpikeCharterDoDR1 : TestResult { :>> id = "63940516-2c7d-4e8f-c200-51627384c003"; :>> outcome = VerdictKind::pass; :>> judgedAgainst = "633b689"; :>> judgedAt = "2026-07-09"; :>> judgedBy = "claudeOpus"; }
    }

    verification rscRefineGate : Test { :>> id = "63940516-2c7d-4e8f-c200-51627384c004"; :>> title = "Sprint 200 refine gate (DoR)"; :>> createdAt = "2026-07-09"; :>> createdBy = "claudeOpus"; :>> method = VerificationMethod::inspect; :>> procedureText = "DoR: d0111 accepted (human-judged 2026-07-09, wweatherholtz); the rule shape is issue055 fix (3) (declared EdgeRule/ElementRule, not a bespoke guard); warning-level chosen. estimatedPoints=2. #CharteredBy d0111. DoR met."; }
    part rscRefineGateR1 : TestResult { :>> id = "63940516-2c7d-4e8f-c200-51627384c005"; :>> outcome = VerdictKind::pass; :>> judgedAgainst = "633b689"; :>> judgedAt = "2026-07-09"; :>> judgedBy = "claudeOpus"; }
    verification rscStandupGate : Test { :>> id = "63940516-2c7d-4e8f-c200-51627384c006"; :>> title = "Sprint 200 standup gate"; :>> createdAt = "2026-07-09"; :>> createdBy = "claudeOpus"; :>> method = VerificationMethod::inspect; :>> procedureText = "Approach: whereKind scope + charterTargetType predicate (view.rs) -> declare researchSpikeCharterRule (warning) -> unit test the catch path -> doc-sync. No blockers."; }
    part rscStandupGateR1 : TestResult { :>> id = "63940516-2c7d-4e8f-c200-51627384c007"; :>> outcome = VerdictKind::pass; :>> judgedAgainst = "633b689"; :>> judgedAt = "2026-07-09"; :>> judgedBy = "claudeOpus"; }
    verification rscImplementGate : Test { :>> id = "63940516-2c7d-4e8f-c200-51627384c008"; :>> title = "Sprint 200 implement gate"; :>> createdAt = "2026-07-09"; :>> createdBy = "claudeOpus"; :>> method = VerificationMethod::test; :>> procedureText = "whereKind + charterTargetType + researchSpikeCharterRule + the unit test landed. Allow-list corrected to D0068 after it flagged sr19SpikeStory. clippy -D clean; cargo test green; keel rules -> researchSpikeCharterRule evaluated=true, 0 live violations; keel validate + guard green."; }
    part rscImplementGateR1 : TestResult { :>> id = "63940516-2c7d-4e8f-c200-51627384c009"; :>> outcome = VerdictKind::pass; :>> judgedAgainst = "633b689"; :>> judgedAt = "2026-07-09"; :>> judgedBy = "claudeOpus"; }
    verification rscReviewGate : Test { :>> id = "63940516-2c7d-4e8f-c200-51627384c00a"; :>> title = "Sprint 200 review gate"; :>> createdAt = "2026-07-09"; :>> createdBy = "claudeOpus"; :>> method = VerificationMethod::inspect; :>> procedureText = "Reviewed. The change does exactly what the honest scope allows: it locks the STRUCTURALLY-VISIBLE half of research-spike routing (a spike's charter must be a legitimate governing source) as a declared warning rule, reusing the D0105/D0107 declared-rules substrate (whereKind + charterTargetType are general, not one-offs). It correctly did NOT overclaim issue061 (part 1 needs a real design session) and did NOT force the un-gatable conversational half into a false control. The mid-implement allow-list widening (Issue|Decision -> the D0068 union) shows the rule earning its keep by catching a real edge case (sr19SpikeStory) during dogfood. Warning-first is the right trust posture. Clean."; }
    part rscReviewGateR1 : TestResult { :>> id = "63940516-2c7d-4e8f-c200-51627384c00b"; :>> outcome = VerdictKind::pass; :>> judgedAgainst = "633b689"; :>> judgedAt = "2026-07-09"; :>> judgedBy = "claudeOpus"; }
    verification rscCloseOutGate : Test { :>> id = "63940516-2c7d-4e8f-c200-51627384c00c"; :>> title = "Sprint 200 closeOut gate (autonomous, D0049)"; :>> createdAt = "2026-07-09"; :>> createdBy = "claudeOpus"; :>> method = VerificationMethod::inspect; :>> procedureText = "Autonomous closeOut (D0049): DoD pass; researchSpikeCharterRule is live in keel rules (warning, 0 violations); D0111 recorded + human-accepted. clippy + cargo test + keel validate + guard (15) green. Self-evidencing (D0051). issue061 remains OPEN (part 1 pending — honest). NEXT: proveProcessDeployment part 1 awaits a real design/scoping request to dogfood the business-architecture skill."; }
    part rscCloseOutGateR1 : TestResult { :>> id = "63940516-2c7d-4e8f-c200-51627384c00d"; :>> outcome = VerdictKind::pass; :>> judgedAgainst = "633b689"; :>> judgedAt = "2026-07-09"; :>> judgedBy = "claudeOpus"; }
    verification rscRetroGate : Test { :>> id = "63940516-2c7d-4e8f-c200-51627384c00e"; :>> title = "Sprint 200 retro gate (autonomous, D0049)"; :>> createdAt = "2026-07-09"; :>> createdBy = "claudeOpus"; :>> method = VerificationMethod::analyze; :>> procedureText = "Autonomous retro (D0049). WELL: the enforceable half of research-spike routing is now a declared control (not just triage vigilance), built on reusable scope/predicate primitives (whereKind, charterTargetType) that grow the declared-rules vocabulary for future migrations. Dogfooding the rule against the live repo caught a real allow-list gap BEFORE commit (sr19SpikeStory) — the rule earned trust immediately. AVOIDABLE-ISSUE SCAN: the first-cut allow-list was too narrow because I anchored on issue055's headline (Issue/proposed-Decision) rather than the guards.rs charter message's full union — LESSON: derive an allow-list from the authoritative predicate (the guard message), not an issue's summary. No defect escaped (caught in implement). Estimate 2 pt held. NEXT: part 1 of issue061 (real-design dogfood); a possible follow-on is promoting researchSpikeCharterRule from warning to a hard guard once a run of clean commits proves it low-noise (the D0102 path)."; }
    part rscRetroGateR1 : TestResult { :>> id = "63940516-2c7d-4e8f-c200-51627384c00f"; :>> outcome = VerdictKind::pass; :>> judgedAgainst = "633b689"; :>> judgedAt = "2026-07-09"; :>> judgedBy = "claudeOpus"; }
}
