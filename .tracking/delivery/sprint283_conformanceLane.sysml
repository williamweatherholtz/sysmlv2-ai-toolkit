// ProjectDeliveryS283 — Sprint 283: the conformance lane, and the dangling-edge guard it found
// (dcKernelConformanceGate, issue097/issue109). EXECUTE. 8 pts.
package ProjectDeliveryS283 {
    private import EngineElement::*;
    private import EngineWork::*;
    private import EngineVerification::*;
    private import EngineRelationships::*;

    #CharteredBy dependency from conformanceLaneStory to d0144;

    part conformanceLaneStory : Story {
        :>> id = "0d80015d-0814-615d-9b3e-00000030015d";
        :>> title = "Sprint 283: measure SysML v2 conformance; the lane finds what no Rust check could (8 pts)";
        :>> createdAt = "2026-08-14"; :>> createdBy = "claudeOpus5"; :>> kind = WorkKind::code; :>> priority = WorkPriority::p0; :>> owner = "claudeOpus5"; :>> estimatedPoints = 8;
    }

    action def DeliveryRunS283 {
        action storyConformanceLane;
        verification storyConformanceLaneDoD : Test { :>> id = "0d80015e-0814-615e-9b3e-00000030015e"; :>> method = VerificationMethod::demo; :>> procedureText = "Delivers dcKernelConformanceGate; resolves issue097 and issue109. `keel validate`/`check` are the ENGINE's semantic authority and NOT a SysML v2 conformance check, but nothing said so, so 'validate is green' read as 'this is valid SysML v2' — which is how a non-conformant construct reached an accepted Decision as a migration target (D0139 clause E). The human's goal is a model that opens in a standard viewer, so conformance is the property that matters and it was unmeasured. DELIVERED (a) the LANE: `.engine/tools/validate/conformance_lane.py` sweeps every instance file through the OMG pilot kernel, reports the rejected CONSTRUCT, and never blocks — exit 0 even on findings, because D0132 demoted the per-file validator for failing correct files and forcing an all-or-nothing bypass that disabled every other layer (issue081). RESULT: 470/470 instance files, NO construct rejected. (b) the PRE-ADOPTION check: `--construct FILE` kernel-checks one snippet, making the rule 'never adopt a base construct on the Rust parser alone' runnable rather than remembered. (c) the ORACLE BOUNDARY stated in CLAUDE.md §5 where `validate` is documented as the authority. (d) `conformanceIndicator`, method=PULLED and not computed — the Rust binary cannot compute this number, since the validation path is kernel-free by D0048, and a `computed` indicator here would be the Rust parser grading its own homework. First measurement 100.0% at 1cb73e4. THE 40% THAT WASN'T: the lane's first run reported 190/470 and every diagnostic was 'Couldn't resolve reference to d0094' — an artifact of loading one file per cell in iteration order, not a conformance result. Publishing it would have been a false finding of exactly the kind this sprint exists to prevent, so the lane now classifies unresolved-name diagnostics into ordering artifacts (279, excluded and reported as such) versus genuinely undeclared names (1, which became issue109). clippy clean; 172 tests; validate 305 clean; 29 guards green."; }
        part storyConformanceLaneDoDR1 : TestResult { :>> id = "0d80015f-0814-615f-9b3e-00000030015f"; :>> outcome = VerdictKind::pass; :>> judgedAgainst = "0bd61be"; :>> judgedAt = "2026-08-14"; :>> judgedBy = "claudeOpus5"; }
    }

    verification clRefineGate : Test { :>> id = "0d800160-0814-6160-9b3e-000000300160"; :>> title = "Sprint 283 refine gate (DoR)"; :>> createdAt = "2026-08-14"; :>> createdBy = "claudeOpus5"; :>> method = VerificationMethod::inspect; :>> procedureText = "DoR. CONSUMER CHECK (dorConsumer, D0144): the lane's consumer is a HUMAN reading a number, and the number's consumer is the indicator layer. That second consumer settled the method — `computed` indicators source from the Rust `metric_value`, which is kernel-free by D0048 and therefore cannot produce this figure, so the indicator had to be `pulled`. Checking it first avoided declaring a computed indicator whose metric key nothing could ever compute. estimatedPoints=8. DoR met."; }
    part clRefineGateR1 : TestResult { :>> id = "0d800161-0814-6161-9b3e-000000300161"; :>> outcome = VerdictKind::pass; :>> judgedAgainst = "0bd61be"; :>> judgedAt = "2026-08-14"; :>> judgedBy = "claudeOpus5"; }

    verification clStandupGate : Test { :>> id = "0d800162-0814-6162-9b3e-000000300162"; :>> title = "Sprint 283 standup gate"; :>> createdAt = "2026-08-14"; :>> createdBy = "claudeOpus5"; :>> method = VerificationMethod::inspect; :>> procedureText = "Approach: build the lane, run it, and READ the output rather than the exit code — the lesson issue107 recorded one sprint earlier, where a warning-only guard had been reporting a real defect for four sprints while I reported `guard exit=0`. That is precisely what paid off here: the lane exits 0 by design, so its findings exist only in its message. No blockers. Tooling note: the PowerShell path returned exit 1 with NO output twice, leaving three stale JVMs; switched to bash with a redirect rather than re-issuing the same form, which is the shell-adaptation rule (issue065) applied instead of recorded."; }
    part clStandupGateR1 : TestResult { :>> id = "0d800163-0814-6163-9b3e-000000300163"; :>> outcome = VerdictKind::pass; :>> judgedAgainst = "0bd61be"; :>> judgedAt = "2026-08-14"; :>> judgedBy = "claudeOpus5"; }

    verification clImplementGate : Test { :>> id = "0d800164-0814-6164-9b3e-000000300164"; :>> title = "Sprint 283 implement gate"; :>> createdAt = "2026-08-14"; :>> createdBy = "claudeOpus5"; :>> method = VerificationMethod::test; :>> procedureText = "THE LANE JUSTIFIED ITSELF ON ITS FIRST REAL RUN by finding a defect class no Rust check could see: a typed edge whose endpoint is declared NOWHERE. Two live instances — `#Resolves ... from declarativeControlsRoiOrRescope` (its DoD and a PASSING result sat in the backlog with no `action` line above them, so issue060 read as triaged by a resolver that did not exist) and `#CharteredBy ... to postReleaseBurndown` (declared in no commit, so a Story read as chartered by an origin that never existed). Both passed validate, check-engine and all 28 guards, because `issues` and `charter` each check that the EDGE is PRESENT and none resolved an endpoint. A dangling edge is strictly worse than a missing one: a missing edge shows as a gap, a dangling edge is counted as satisfied by the very guard meant to find the gap. FIXED ASYMMETRICALLY, on purpose: the first was RESTORED (its DoD and result are committed records of what it was), the second REMOVED rather than repointed, because inventing a charter target to satisfy a guard would fabricate provenance to pass a check."; }
    part clImplementGateR1 : TestResult { :>> id = "0d800165-0814-6165-9b3e-000000300165"; :>> outcome = VerdictKind::pass; :>> judgedAgainst = "0bd61be"; :>> judgedAt = "2026-08-14"; :>> judgedBy = "claudeOpus5"; }

    verification clReviewGate : Test { :>> id = "0d800166-0814-6166-9b3e-000000300166"; :>> title = "Sprint 283 review gate"; :>> createdAt = "2026-08-14"; :>> createdBy = "claudeOpus5"; :>> method = VerificationMethod::inspect; :>> procedureText = "Reviewed. The `edge-endpoints` guard is AST-based, and that is load-bearing rather than stylistic: a text scan for the same thing reports two extra hits from D0133's own prose ABOUT edges (`#Verify dependency from a to b;` inside a description), the identical self-referential-corpus trap that inflated the marker census in issue099 — third occurrence of that trap in this pass, and the first one the design was immune to by construction. The guard also fired initially on `.engine/docs/tracking-template.sysml`, an authoring EXAMPLE whose placeholder names are undeclared on purpose; fixed by scoping it to the directories `Model::build` actually ingests, now a shared `model_dirs` so the two cannot drift. Four violations against a file the model never loads is how a new guard teaches its reader to ignore it."; }
    part clReviewGateR1 : TestResult { :>> id = "0d800167-0814-6167-9b3e-000000300167"; :>> outcome = VerdictKind::pass; :>> judgedAgainst = "0bd61be"; :>> judgedAt = "2026-08-14"; :>> judgedBy = "claudeOpus5"; }

    verification clCloseOutGate : Test { :>> id = "0d800168-0814-6168-9b3e-000000300168"; :>> title = "Sprint 283 closeOut gate (autonomous, D0049)"; :>> createdAt = "2026-08-14"; :>> createdBy = "claudeOpus5"; :>> method = VerificationMethod::inspect; :>> procedureText = "Autonomous closeOut (D0049). dcKernelConformanceGate carries a passing DoD TestResult; issue097 and issue109 resolve. Guards 28 -> 29 (20 hard-blocking), `edge-endpoints` verified live by negative test — reintroducing a dangling edge fails it, removing it passes — and starting at zero with no grandfathering, which issue068 does not warrant here because the work was not correct when written, only undetected. Doc-sync rides this commit: CLAUDE.md §5 gains the oracle boundary and the pre-adoption command, guards.md gains the new guard and the corrected counts. clippy clean; 172 tests; validate 305 clean; check-engine clean; 29 guards green; JVMs swept. No gate bypassed."; }
    part clCloseOutGateR1 : TestResult { :>> id = "0d800169-0814-6169-9b3e-000000300169"; :>> outcome = VerdictKind::pass; :>> judgedAgainst = "0bd61be"; :>> judgedAt = "2026-08-14"; :>> judgedBy = "claudeOpus5"; }

    verification clRetroGate : Test { :>> id = "0d80016a-0814-616a-9b3e-00000030016a"; :>> title = "Sprint 283 retro gate (autonomous, D0049)"; :>> createdAt = "2026-08-14"; :>> createdBy = "claudeOpus5"; :>> method = VerificationMethod::analyze; :>> procedureText = "Autonomous retro (D0049) under D0131's retroTrack. WELL: (1) the 190/470 first result was interrogated instead of published — it looked like a dramatic finding and was entirely the lane's own artifact, and a sprint whose purpose is measuring honesty publishing a false 40% would have been the worst possible outcome; (2) the lane paid for itself immediately by finding a defect class every Rust check was blind to, which is a stronger argument for it than any of the reasoning in its charter; (3) the guard that followed is immune BY CONSTRUCTION to the prose-in-strings trap rather than defended against it. AVOIDABLE-ISSUE 1: a `str.replace(old, new, 1)` in a fix-up script hit an EXISTING indicator's line instead of my new one and rewrote its immutable UUID — §1.3's one true invariant. Caught by `duplicate-identity` before commit, restored verbatim from git, and the diff verified to be pure insertions. This is the SECOND time this pass that a replace-by-count landed on the wrong occurrence; sprint 273's rule was 'never patch by a pattern you have not confirmed is unique', and here I knew the pattern was NOT unique and used a count anyway. NO NEW ITEM, reason stated: issue094 tracks the class and dcShellAdaptationGate is its declared resolver, still unbuilt and now three sprints old. AVOIDABLE-ISSUE 2: two PowerShell invocations returned exit 1 with no output and leaked three JVMs before I switched tools — the shell-adaptation rule says switch rather than re-issue, and I re-issued once first. Same tracked class. Estimate 8 pts, delivered."; }
    part clRetroGateR1 : TestResult { :>> id = "0d80016b-0814-616b-9b3e-00000030016b"; :>> outcome = VerdictKind::pass; :>> judgedAgainst = "0bd61be"; :>> judgedAt = "2026-08-14"; :>> judgedBy = "claudeOpus5"; }
}
