// ProjectDeliveryS242 — Sprint 242: create a new item of any declared type in-canvas (the CREATE half of
// srViewerAuthoringSurface, D0126) — POST /api/item + the viewer's generative New-item dialog. The EDIT
// half is split to viewerEditItem. EXECUTE. 3 pts.
package ProjectDeliveryS242 {
    private import EngineElement::*;
    private import EngineWork::*;
    private import EngineVerification::*;
    private import EngineRelationships::*;

    #CharteredBy dependency from viewerCreateItemStory to d0126;

    part viewerCreateItemStory : Story {
        :>> id = "63940516-2c7d-4e8f-c242-51627384c001";
        :>> title = "Sprint 242: viewerCreateItem (3 pts) - create a new item of any declared type in-canvas (POST /api/item + generative New-item dialog)";
        :>> createdAt = "2026-07-16"; :>> createdBy = "wweatherholtz"; :>> kind = WorkKind::code; :>> priority = WorkPriority::p2; :>> owner = "claudeOpus"; :>> estimatedPoints = 3;
    }

    action def DeliveryRunS242 {
        action storyViewerCreateItem;
        verification storyViewerCreateItemDoD : Test { :>> id = "63940516-2c7d-4e8f-c242-51627384c002"; :>> method = VerificationMethod::demo; :>> procedureText = "Delivers the CREATE half of srViewerAuthoringSurface (D0126) — 'make new items', the headline of the human's 'not just new decision'. KEEL (v1.14.0, cea5150): write::create_item + NewItem author a new part of a declared type into .tracking/authored.sysml with a generated UUID + provenance, string attrs (quoted, sanitized) + enum attrs (EnumType::member); the SysML keyword is DERIVED from the type's meta-kind (requirement / use case / verification / part) so create is generative + conformant. POST /api/item, advertised in /api/version writeEndpoints; additive only, never auto-commits. VIEWER (8738af4): the ＋ in Find opens a generative New-item dialog — a 91-type picker (from /api/schema) + fields generated per type (String -> text/textarea, enum -> member select), provenance stamped by keel; submits via POST /api/item, runs /api/check inline (guard-rejection surfaced), refreshes the index, focuses the new item; Decision routes to its dedicated proposal flow. VERIFY (demo, live): created an Issue (part) + a Need (requirement, enum priority) via the dialog end-to-end; model validates clean; the untriaged Issue is correctly flagged by /api/check ('would REJECT — untriaged') — honest inline feedback, not committed. clippy + validate + guard + check-engine green. HONEST: v1 covers String + enum attrs (Boolean/Integer deferred); the EDIT path (attribute change / supersede) is split to viewerEditItem."; }
        part storyViewerCreateItemDoDR1 : TestResult { :>> id = "63940516-2c7d-4e8f-c242-51627384c003"; :>> outcome = VerdictKind::pass; :>> judgedAgainst = "cea5150"; :>> judgedAt = "2026-07-16"; :>> judgedBy = "claudeOpus"; }
    }

    verification ciRefineGate : Test { :>> id = "63940516-2c7d-4e8f-c242-51627384c004"; :>> title = "Sprint 242 refine gate (DoR)"; :>> createdAt = "2026-07-16"; :>> createdBy = "claudeOpus"; :>> method = VerificationMethod::inspect; :>> procedureText = "DoR: viewerAuthoringEndpoints ready on the frontier; scope this sprint to CREATE (POST /api/item + viewer New-item dialog), split EDIT to viewerEditItem. #CharteredBy d0126. estimatedPoints=3. DoR met."; }
    part ciRefineGateR1 : TestResult { :>> id = "63940516-2c7d-4e8f-c242-51627384c005"; :>> outcome = VerdictKind::pass; :>> judgedAgainst = "cea5150"; :>> judgedAt = "2026-07-16"; :>> judgedBy = "claudeOpus"; }
    verification ciStandupGate : Test { :>> id = "63940516-2c7d-4e8f-c242-51627384c006"; :>> title = "Sprint 242 standup gate"; :>> createdAt = "2026-07-16"; :>> createdBy = "claudeOpus"; :>> method = VerificationMethod::inspect; :>> procedureText = "Approach: write::create_item (keyword-by-meta-kind, string+enum literals, provenance, authored.sysml) + POST /api/item; viewer generative New-item dialog from /api/schema + /api/check inline. No blockers."; }
    part ciStandupGateR1 : TestResult { :>> id = "63940516-2c7d-4e8f-c242-51627384c007"; :>> outcome = VerdictKind::pass; :>> judgedAgainst = "cea5150"; :>> judgedAt = "2026-07-16"; :>> judgedBy = "claudeOpus"; }
    verification ciImplementGate : Test { :>> id = "63940516-2c7d-4e8f-c242-51627384c008"; :>> title = "Sprint 242 implement gate"; :>> createdAt = "2026-07-16"; :>> createdBy = "claudeOpus"; :>> method = VerificationMethod::demo; :>> procedureText = "Implemented (keel@cea5150, viewer@8738af4). Live-verified: New-item dialog (91 types, generative enum/string fields); created an Issue + Need end-to-end; validates clean; /api/check flags the untriaged Issue. clippy + validate + guard + check-engine green."; }
    part ciImplementGateR1 : TestResult { :>> id = "63940516-2c7d-4e8f-c242-51627384c009"; :>> outcome = VerdictKind::pass; :>> judgedAgainst = "cea5150"; :>> judgedAt = "2026-07-16"; :>> judgedBy = "claudeOpus"; }
    verification ciReviewGate : Test { :>> id = "63940516-2c7d-4e8f-c242-51627384c00a"; :>> title = "Sprint 242 review gate"; :>> createdAt = "2026-07-16"; :>> createdBy = "claudeOpus"; :>> method = VerificationMethod::inspect; :>> procedureText = "Reviewed. Create is fully process-bound: generative from schema, keyword-conformant, provenance-stamped, guarded, never auto-committed — and the untriaged-Issue case proves /api/check honestly gates completeness at commit (D0098) rather than the endpoint faking a clean create. Scope split (create now, edit as viewerEditItem) is honest, not a silent drop. Clean."; }
    part ciReviewGateR1 : TestResult { :>> id = "63940516-2c7d-4e8f-c242-51627384c00b"; :>> outcome = VerdictKind::pass; :>> judgedAgainst = "cea5150"; :>> judgedAt = "2026-07-16"; :>> judgedBy = "claudeOpus"; }
    verification ciCloseOutGate : Test { :>> id = "63940516-2c7d-4e8f-c242-51627384c00c"; :>> title = "Sprint 242 closeOut gate (autonomous, D0049)"; :>> createdAt = "2026-07-16"; :>> createdBy = "claudeOpus"; :>> method = VerificationMethod::inspect; :>> procedureText = "Autonomous closeOut (D0049): CREATE delivered + verified (POST /api/item + New-item dialog); viewerAuthoringEndpoints marked done for create. Self-evidencing. NEXT: viewerEditItem (the edit/attribute-change path)."; }
    part ciCloseOutGateR1 : TestResult { :>> id = "63940516-2c7d-4e8f-c242-51627384c00d"; :>> outcome = VerdictKind::pass; :>> judgedAgainst = "cea5150"; :>> judgedAt = "2026-07-16"; :>> judgedBy = "claudeOpus"; }
    verification ciRetroGate : Test { :>> id = "63940516-2c7d-4e8f-c242-51627384c00e"; :>> title = "Sprint 242 retro gate (autonomous, D0049)"; :>> createdAt = "2026-07-16"; :>> createdBy = "claudeOpus"; :>> method = VerificationMethod::analyze; :>> procedureText = "Autonomous retro (D0049). WELL: derived the SysML keyword from the type meta-kind so create is generative across all 91 types (not a hardcoded subset); leaned on /api/check so a created-but-incomplete item (untriaged Issue) is surfaced honestly instead of blocked-at-create or faked. Split create/edit rather than half-doing both. AVOIDABLE-ISSUE: the static file server dropped mid-session and needed a restart — minor; not tracked. LESSON: for a create endpoint, correctness = right keyword + provenance + let the existing guards gate completeness at commit. Estimate 3 pts. NEXT: viewerEditItem."; }
    part ciRetroGateR1 : TestResult { :>> id = "63940516-2c7d-4e8f-c242-51627384c00f"; :>> outcome = VerdictKind::pass; :>> judgedAgainst = "cea5150"; :>> judgedAt = "2026-07-16"; :>> judgedBy = "claudeOpus"; }
}
