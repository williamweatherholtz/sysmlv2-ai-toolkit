// ProjectDeliveryS147 — Sprint 147: tierSatisfaction (D0098, completes issue047/requirementRootednessGuard)
// — the DOWNWARD integrity burndown + the always-visible orient surfacing. `keel tier-satisfaction`
// computes per-tier structural satisfaction (Needs decomposed into SRs; SRs verified by Tests) as a
// leading indicator of insufficient implementation; orient now carries a compact non-blocking burndown
// block. With S146 (rootedness) + D0098 (requirement-first support), requirementRootednessGuard is
// complete -> issue047 resolved. EXECUTE under D0098 (computed/non-blocking; no new Decision). 4 pts. AUTONOMOUS (D0049).
package ProjectDeliveryS147 {
    private import EngineElement::*;
    private import EngineWork::*;
    private import EngineVerification::*;
    private import EngineRelationships::*;

    #CharteredBy dependency from tierSatisfactionStory to d0098;

    part tierSatisfactionStory : Story {
        :>> id = "63940516-2c7d-4e8f-c147-51627384c001";
        :>> title = "Sprint 147: tierSatisfaction (4 pts) — downward tier-satisfaction burndown + orient surfacing; completes requirementRootednessGuard (D0098/issue047)";
        :>> createdAt = "2026-06-24"; :>> createdBy = "wweatherholtz"; :>> kind = WorkKind::code; :>> priority = WorkPriority::p2; :>> owner = "claudeOpus"; :>> estimatedPoints = 4;
    }

    action def DeliveryRunS147 {
        action storyTierSatisfaction;
        verification storyTierSatisfactionDoD : Test { :>> id = "63940516-2c7d-4e8f-c147-51627384c002"; :>> method = VerificationMethod::test; :>> procedureText = "The DOWNWARD half of requirement integrity (human insight, D0098): is each tier cleanly + comprehensively satisfied by its downstream items? FIX: `keel tier-satisfaction` computes the STRUCTURAL satisfaction floor per tier — a Need is decomposed iff some SystemRequirement `satisfy`-traces to it; a SystemRequirement is verified iff a Test `#Verify`-links to it — plus the gap set + a per-tier pct (the leading indicator; thin downstream => predicted under-implementation; the deeper 'do the SRs fully discharge the Need' is the future AI white-box layer, SR-3c). orient now carries a compact NON-BLOCKING `burndown` block (D0098) — tier-satisfaction pcts + unrooted-capabilities + orphan-stories + a detail pointer — so incompleteness is ALWAYS visible (the chart you can't refuse to draw), cheap (graph-only, no git). A `tier-satisfaction` Viewpoint declares the concern; VIEW_SUBCOMMANDS + README + CLAUDE.md (the computed-lenses list + orient burndown) doc-synced. VERIFIED (live): `keel tier-satisfaction` = Need 14/14 (100%), SystemRequirement 14/14 (100%); `keel orient` burndown block present (need 100 / sr 100 / unrooted_caps 0 / orphan_stories 38); unit tests capability_must_derive_a_need + tier_satisfaction_counts_decomposition_and_verification pass. clippy -D warnings + cargo test 53 lib + keel validate 160 + guard all (12) green. This + S146 (rootedness) + D0098 (requirement-first support) completes requirementRootednessGuard -> issue047 resolved."; }
        part storyTierSatisfactionDoDR1 : TestResult { :>> id = "63940516-2c7d-4e8f-c147-51627384c003"; :>> outcome = VerdictKind::pass; :>> judgedAgainst = "c6664cc"; :>> judgedAt = "2026-06-24"; :>> judgedBy = "claudeOpus"; }
    }

    verification tierSatisfactionRefineGate : Test { :>> id = "63940516-2c7d-4e8f-c147-51627384c004"; :>> title = "Sprint 147 refine gate (DoR)"; :>> createdAt = "2026-06-24"; :>> createdBy = "claudeOpus"; :>> method = VerificationMethod::inspect; :>> procedureText = "DoR: D0098 + the human's tier-comprehensiveness insight authorize the downward burndown + orient surfacing (the remaining pieces of requirementRootednessGuard after S146 rootedness). Computed/non-blocking, so EXECUTE under D0098 (no new Decision). estimatedPoints=4. #CharteredBy d0098. DoR met."; }
    part tierSatisfactionRefineGateR1 : TestResult { :>> id = "63940516-2c7d-4e8f-c147-51627384c005"; :>> outcome = VerdictKind::pass; :>> judgedAgainst = "c6664cc"; :>> judgedAt = "2026-06-24"; :>> judgedBy = "claudeOpus"; }
    verification tierSatisfactionStandupGate : Test { :>> id = "63940516-2c7d-4e8f-c147-51627384c006"; :>> title = "Sprint 147 standup gate"; :>> createdAt = "2026-06-24"; :>> createdBy = "claudeOpus"; :>> method = VerificationMethod::inspect; :>> procedureText = "Approach: compute_tier_satisfaction (satisfy/verify edge presence per tier) + `keel tier-satisfaction` view; a cheap burndown_summary_json embedded into orient (graph-only, no git, no orient recursion); tier-satisfaction Viewpoint + doc-sync; unit tests. No blockers."; }
    part tierSatisfactionStandupGateR1 : TestResult { :>> id = "63940516-2c7d-4e8f-c147-51627384c007"; :>> outcome = VerdictKind::pass; :>> judgedAgainst = "c6664cc"; :>> judgedAt = "2026-06-24"; :>> judgedBy = "claudeOpus"; }
    verification tierSatisfactionImplementGate : Test { :>> id = "63940516-2c7d-4e8f-c147-51627384c008"; :>> title = "Sprint 147 implement gate"; :>> createdAt = "2026-06-24"; :>> createdBy = "claudeOpus"; :>> method = VerificationMethod::test; :>> procedureText = "Added compute_tier_satisfaction + `keel tier-satisfaction` + burndown_summary_json + orient burndown field/emit + tier-satisfaction Viewpoint + VIEW_SUBCOMMANDS + doc-sync + 2 unit tests. VERIFIED: tier-satisfaction Need 14/14 + SR 14/14; orient burndown block present; guard 12 ALL PASS; clippy green; validate 160; 53 lib tests pass."; }
    part tierSatisfactionImplementGateR1 : TestResult { :>> id = "63940516-2c7d-4e8f-c147-51627384c009"; :>> outcome = VerdictKind::pass; :>> judgedAgainst = "c6664cc"; :>> judgedAt = "2026-06-24"; :>> judgedBy = "claudeOpus"; }
    verification tierSatisfactionReviewGate : Test { :>> id = "63940516-2c7d-4e8f-c147-51627384c00a"; :>> title = "Sprint 147 review gate"; :>> createdAt = "2026-06-24"; :>> createdBy = "claudeOpus"; :>> method = VerificationMethod::inspect; :>> procedureText = "Diff reviewed. tier-satisfaction is the honest STRUCTURAL floor (decomposed/verified presence) — explicitly NOT claiming the deeper 'comprehensively discharges' judgment, which is correctly deferred to the AI white-box layer (SR-3c). orient's burndown is compact + cheap (graph-only) so it stays fast while making incompleteness always-visible (D0098 'chart you can't refuse to draw'). Non-blocking throughout — consistent with the honest-state doctrine. Completes the upward+downward+requirement-first triad of issue047. Clean."; }
    part tierSatisfactionReviewGateR1 : TestResult { :>> id = "63940516-2c7d-4e8f-c147-51627384c00b"; :>> outcome = VerdictKind::pass; :>> judgedAgainst = "c6664cc"; :>> judgedAt = "2026-06-24"; :>> judgedBy = "claudeOpus"; }
    verification tierSatisfactionCloseOutGate : Test { :>> id = "63940516-2c7d-4e8f-c147-51627384c00c"; :>> title = "Sprint 147 closeOut gate (autonomous, D0049)"; :>> createdAt = "2026-06-24"; :>> createdBy = "claudeOpus"; :>> method = VerificationMethod::inspect; :>> procedureText = "Autonomous closeOut (D0049): DoD pass; downward tier-satisfaction burndown + orient surfacing live + tested. guard 12 ALL PASS; clippy + 53 lib tests + validate 160 + kernel validate_instances (pre-commit) green. Self-evidencing (D0051). requirementRootednessGuard now complete (rootedness S146 + tier-satisfaction S147 + requirement-first D0098) -> issue047 resolved. Next: serveRequirementsTrace (unblocked; will mark d0094 #Capability + author serve Needs)."; }
    part tierSatisfactionCloseOutGateR1 : TestResult { :>> id = "63940516-2c7d-4e8f-c147-51627384c00d"; :>> outcome = VerdictKind::pass; :>> judgedAgainst = "c6664cc"; :>> judgedAt = "2026-06-24"; :>> judgedBy = "claudeOpus"; }
    verification tierSatisfactionRetroGate : Test { :>> id = "63940516-2c7d-4e8f-c147-51627384c00e"; :>> title = "Sprint 147 retro gate (autonomous, D0049)"; :>> createdAt = "2026-06-24"; :>> createdBy = "claudeOpus"; :>> method = VerificationMethod::analyze; :>> procedureText = "Autonomous retro (D0049). WELL: the upward (rootedness) + downward (tier-satisfaction) split cleanly realizes the human's integrity insight, and both ship as NON-BLOCKING burndowns (honest-state doctrine) so they inform without gating. Surfacing the burndown in orient makes incompleteness un-ignorable without a hard gate — exactly the burndown-not-block principle. AVOIDABLE-ISSUE SCAN: kept orient fast by making the burndown graph-only (no git, no orient recursion); guarded the new computations with 2 unit tests. LESSON: a leading indicator belongs where it's seen every day (orient), but must be cheap enough not to tax the hot path. NON-blocking: the DEEPER comprehensiveness judgment (do the SRs fully discharge the Need) is the AI white-box layer (SR-3c), the natural next capability. serveRequirementsTrace is the immediate next step. Estimate 4 pts held."; }
    part tierSatisfactionRetroGateR1 : TestResult { :>> id = "63940516-2c7d-4e8f-c147-51627384c00f"; :>> outcome = VerdictKind::pass; :>> judgedAgainst = "c6664cc"; :>> judgedAt = "2026-06-24"; :>> judgedBy = "claudeOpus"; }
}
