// ProjectDeliveryS492 — Sprint 492: the library read side: ambient availability that governs nothing. EXECUTE. 5 pts.
package ProjectDeliveryS492 {
    private import EngineElement::*;
    private import EngineWork::*;
    private import EngineVerification::*;
    private import EngineRelationships::*;

    #CharteredBy dependency from libraryReadSideStory to d0250;

    part libraryReadSideStory : Story {
        :>> id = "35c9adef-4f48-4730-b322-54683867f879";
        :>> title = "Sprint 492: keel library init/sync/list + import --from-library - the cache that governs nothing (5 pts)";
        :>> createdAt = "2026-08-29"; :>> createdBy = "claudeOpus5"; :>> kind = WorkKind::code; :>> priority = WorkPriority::p0; :>> owner = "claudeOpus5"; :>> estimatedPoints = 5;
    }

    action def DeliveryRunS492 {
        action storyLibraryReadSide;
        verification storyLibraryReadSideDoD : Test { :>> id = "1b8a85ec-15a4-470f-be92-8442d11b60ba"; :>> method = VerificationMethod::test; :>> procedureText = "Discharges dcLibraryReadSide (increment 3, D0250 clauses A/B/C/F; srLibraryAvailableWithoutInstall + srAvailabilityIsNotActivation). keel library init clones the author's repository to <home>/.keel/library - machine-local, beside the console registry, DISCOVERED not declared (the clone IS the state; its origin IS the remote; no config file to drift). sync is fetch + fast-forward ONLY: up-to-date and AHEAD (unpushed publishes) are quiet successes, DIVERGED refuses naming the defect, an unreachable remote is a STATED staleness serving the last-good cache. list enumerates units from the cache. process import --from-library resolves the cache and delegates to the ONE existing import path. VERIFY: six Gherkin scenarios in library_read_side.rs, RED first (0/6), now 6/6 - including THE DIFFERENTIAL: a project's guard run is byte-identical (verdict and output) with the library present and absent.: DELIVERED BACKLOG ITEMS: <items>. <what done means, verified how>."; }
        // RAN: // RAN: library_read_side.rs RED 0/6 -> GREEN 6/6 (incl. the byte-identical differential); clippy -D warnings clean; cargo test --workspace --release 20 suites 0 FAILED; two meta-controls fired on the new module (git-spawn counter, help coverage) and were honoured, not exempted
        part storyLibraryReadSideDoDR1 : TestResult { :>> id = "41b2a5f2-f010-4a83-a142-f7b631e6b929"; :>> outcome = VerdictKind::pass; :>> judgedAgainst = "a901722"; :>> judgedAt = "2026-08-29"; :>> judgedBy = "claudeOpus5"; }
    }

    verification libraryReadSideRefineGate : Test { :>> id = "53eb117c-519a-4875-8715-d71e9544ccf4"; :>> title = "Sprint 492 refine gate (DoR)"; :>> createdAt = "2026-08-29"; :>> createdBy = "claudeOpus5"; :>> method = VerificationMethod::inspect; :>> procedureText = "READY: chartered by accepted D0250, thresholds from the accepted requirement layer. Every scenario isolates HOME/USERPROFILE to a fixture, so the machine's real .keel state is never touched - the hook-probe isolation discipline."; }
    verification libraryReadSideStandupGate : Test { :>> id = "9c7de61d-0033-4325-b50f-979ec59044b4"; :>> title = "Sprint 492 standup gate"; :>> createdAt = "2026-08-29"; :>> createdBy = "claudeOpus5"; :>> method = VerificationMethod::inspect; :>> procedureText = "No blocker. The differential scenario was STRENGTHENED after its first failure: it demanded a green fixture gate, which coupled it to every guard's fixture appetite - rewritten to compare verdict AND output identically whatever the color, which is the stronger form of srAvailabilityIsNotActivation."; }
    verification libraryReadSideImplementGate : Test { :>> id = "c67d943d-0d0d-4c8e-95da-039b11cc7b3f"; :>> title = "Sprint 492 implement gate"; :>> createdAt = "2026-08-29"; :>> createdBy = "claudeOpus5"; :>> method = VerificationMethod::test; :>> procedureText = "RAN: library_read_side.rs RED 0/6 (commands absent) -> GREEN 6/6; clippy -D warnings clean after four pedantic rounds; cargo test --workspace --release 20 suites 0 FAILED. DESIGN NOTES: no library config file - the D0245 discovered-not-declared rule, a second place to keep the remote true is a second place for it to be false; AHEAD-tolerance is what lets increment 4's publish commit locally without sync screaming; import --from-library substitutes the DIRECTORY and nothing else, so the library cannot fork the import semantics."; }
    verification libraryReadSideReviewGate : Test { :>> id = "8ed09896-c5f0-489f-9a64-91e665a5e8e9"; :>> title = "Sprint 492 review gate — three passes per D0172"; :>> createdAt = "2026-08-29"; :>> createdBy = "claudeOpus5"; :>> method = VerificationMethod::inspect; :>> procedureText = "THREE PASSES. (1) THE DIFFERENTIAL IS THE HEADLINE PROPERTY and it is byte-level: same exit status, same every-byte output, library present vs absent - the property that makes silent sync safe, held by test rather than argument. (2) DIVERGENCE HANDLING derives from D0250 clause B verbatim: read-only downstream means a non-ff is evidence of an unsanctioned write, and the message says what to inspect and that a cache is disposable. (3) OFFLINE IS EXIT 0: an unreachable remote must not fail scripts that embed sync; the staleness is stated on stdout with the last-good commit stamp."; }
    verification libraryReadSideCloseOutGate : Test { :>> id = "72fb70dc-2b4a-4060-a6fd-9210c94e38fe"; :>> title = "Sprint 492 closeOut gate (autonomous, D0049)"; :>> createdAt = "2026-08-29"; :>> createdBy = "claudeOpus5"; :>> method = VerificationMethod::inspect; :>> procedureText = "CLOSED. Increment 3 of 5. RESIDUALS, named: (a) list reads only TOP-LEVEL unit dirs - a nested layout would list nothing, loudly visible in list's count; (b) sync fetches origin HEAD, so a library repo whose default branch moves needs a re-init - acceptable for a single-author library, revisit if it ever grows contributors; (c) the unit.toml version shown by list is the PUBLISHED version, which until increment 4 lands is whatever the export wrote."; }
    verification libraryReadSideRetroGate : Test { :>> id = "4e8a431c-3db6-43c8-a705-2775e8db2112"; :>> title = "Sprint 492 retro gate (autonomous, D0049)"; :>> createdAt = "2026-08-29"; :>> createdBy = "claudeOpus5"; :>> method = VerificationMethod::analyze; :>> procedureText = "FINDING: the differential test failed first for demanding MORE than the property (a green gate) - the same over-assertion shape as the reverify probe's vacuous fixture, from the opposite side. The propriety lens vocabulary is becoming the working critique language: over-assertion couples a test to incidentals (changeRobustness), under-assertion lets it pass vacuously (the pf-class), and the discipline is to assert exactly the property. SECOND: four clippy-pedantic rounds on a new module suggests drafting against the lint profile rather than fixing after - cheap to internalise, no control needed."; }
    // The #Verify edges these DoDs EARNED and never carried (found by the rigor audit,
    // 2026-08-30): the work was verified, the REQUIREMENT was not (issue082).
    #Verify dependency from storyLibraryReadSideDoD to srAvailabilityIsNotActivation;
    #Verify dependency from storyLibraryReadSideDoD to srLibraryAvailableWithoutInstall;
}
