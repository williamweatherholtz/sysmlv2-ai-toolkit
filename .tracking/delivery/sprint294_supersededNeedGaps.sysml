// ProjectDeliveryS294 — Sprint 294: a DESCOPED Need stops being counted as an undecomposed gap
// (dcSupersededNeedGaps, issue088). EXECUTE. 3 pts.
package ProjectDeliveryS294 {
    private import EngineElement::*;
    private import EngineWork::*;
    private import EngineVerification::*;
    private import EngineRelationships::*;

    #CharteredBy dependency from supersededGapsStory to d0144;

    part supersededGapsStory : Story {
        :>> id = "0d80020d-0814-620d-9b3e-00000030020d";
        :>> title = "Sprint 294: descoped Needs leave the gap set, and stay visible (3 pts)";
        :>> createdAt = "2026-08-15"; :>> createdBy = "claudeOpus5"; :>> kind = WorkKind::code; :>> priority = WorkPriority::p0; :>> owner = "claudeOpus5"; :>> estimatedPoints = 3;
    }

    action def DeliveryRunS294 {
        action storySupersededGaps;
        verification storySupersededGapsDoD : Test { :>> id = "0d80020e-0814-620e-9b3e-00000030020e"; :>> method = VerificationMethod::test; :>> procedureText = "Delivers dcSupersededNeedGaps; resolves issue088. `tier-satisfaction` counted a SUPERSEDED Need as an undecomposed gap. §2.4 makes a superseding Decision the engine's own scope mechanism, so demanding decomposition of descoped work both understates completeness AND — the worse half — invites a future contributor to 'fix' the gap by authoring SystemRequirements for work that was explicitly cut. The metric was actively pointing at wrong work. FIXED: a Need or SystemRequirement carrying an incoming `#Supersede` edge leaves the tier's DENOMINATOR and gap set, and is reported separately as `supersededExcluded` + the names — an excluded item must not become an invisible one, or the metric starts flattering itself. MEASURED: Need tier 47/53 (88%) -> 47/48 (97%), with the 5 descoped viewer Needs named, and `nViewerPersistedViewpoints` — genuinely undecomposed, no supersede edge — correctly REMAINING a gap. THE DoD ALSO ASKED WHETHER SIBLING VIEWS SHARE THE BLIND SPOT, and one does: the `coverage` view listed all 5 descoped Needs as uncovered assurance targets. Fixed in the same place its own comment already excludes non-accepted Decisions 'because including them would report false gaps' — the identical reasoning, one type over. MEASURED: assured coverage_gaps 71 -> 66. `rootedness` does NOT share it (it measures charter over Stories, not decomposition) and its single orphan is genuinely uncharted. clippy clean; 137 lib tests; validate 316 clean; 31 guards green."; }
        part storySupersededGapsDoDR1 : TestResult { :>> id = "0d80020f-0814-620f-9b3e-00000030020f"; :>> outcome = VerdictKind::pass; :>> judgedAgainst = "cc9acb3"; :>> judgedAt = "2026-08-15"; :>> judgedBy = "claudeOpus5"; }
    }

    verification sgRefineGate : Test { :>> id = "0d800210-0814-6210-9b3e-000000300210"; :>> title = "Sprint 294 refine gate (DoR)"; :>> createdAt = "2026-08-15"; :>> createdBy = "claudeOpus5"; :>> method = VerificationMethod::inspect; :>> procedureText = "DoR. CONSUMER CHECK (dorConsumer, D0144): the consumers of the tier numbers are `assured`, the burndown block in `orient`, and a human reading a percentage — so the change had to keep the descoping VISIBLE, not merely remove it from the denominator. A silently smaller denominator is a better-looking number with less information in it. estimatedPoints=3. DoR met."; }
    part sgRefineGateR1 : TestResult { :>> id = "0d800211-0814-6211-9b3e-000000300211"; :>> outcome = VerdictKind::pass; :>> judgedAgainst = "cc9acb3"; :>> judgedAt = "2026-08-15"; :>> judgedBy = "claudeOpus5"; }

    verification sgStandupGate : Test { :>> id = "0d800212-0814-6212-9b3e-000000300212"; :>> title = "Sprint 294 standup gate"; :>> createdAt = "2026-08-15"; :>> createdBy = "claudeOpus5"; :>> method = VerificationMethod::inspect; :>> procedureText = "Approach: fix tier-satisfaction, then actually RUN the sibling views against the five known descoped names rather than reading their code for the assumption. Reading would have been faster and would have missed it — `coverage`'s own comment already articulates the correct rule for Decisions, so it reads as if it handles this. Only running it showed the five names present. No blockers."; }
    part sgStandupGateR1 : TestResult { :>> id = "0d800213-0814-6213-9b3e-000000300213"; :>> outcome = VerdictKind::pass; :>> judgedAgainst = "cc9acb3"; :>> judgedAt = "2026-08-15"; :>> judgedBy = "claudeOpus5"; }

    verification sgImplementGate : Test { :>> id = "0d800214-0814-6214-9b3e-000000300214"; :>> title = "Sprint 294 implement gate"; :>> createdAt = "2026-08-15"; :>> createdBy = "claudeOpus5"; :>> method = VerificationMethod::test; :>> procedureText = "The load-bearing choice is that the descoped items leave the DENOMINATOR, not just the gap list. Removing them from `gaps` alone would leave 47/53 with 1 gap — a number that adds up to nothing and invites the reader to hunt for five missing items. Removing them from both, and reporting the count and the NAMES alongside, is what makes 47/48 both true and checkable. The test asserts the denominator specifically, because that is the assertion that would silently pass if someone later 'simplified' the exclusion into a gap filter."; }
    part sgImplementGateR1 : TestResult { :>> id = "0d800215-0814-6215-9b3e-000000300215"; :>> outcome = VerdictKind::pass; :>> judgedAgainst = "cc9acb3"; :>> judgedAt = "2026-08-15"; :>> judgedBy = "claudeOpus5"; }

    verification sgReviewGate : Test { :>> id = "0d800216-0814-6216-9b3e-000000300216"; :>> title = "Sprint 294 review gate"; :>> createdAt = "2026-08-15"; :>> createdBy = "claudeOpus5"; :>> method = VerificationMethod::inspect; :>> procedureText = "Reviewed. A small correction to the item's own text, recorded rather than quietly matched: it predicted 47/48 = 98%, and the view reports 97% because `pct` floors and 47/48 is 97.9%. The computation is right and the prediction was rounded; stating the number the tool actually prints matters more here than agreeing with the backlog. Separately, `rootedness` now reports exactly one orphan — `postReleaseBurndownStory`, whose false `#CharteredBy` edge sprint 283 REMOVED. That is the removal working: the story genuinely has no charter, and it says so instead of pointing at an origin that never existed."; }
    part sgReviewGateR1 : TestResult { :>> id = "0d800217-0814-6217-9b3e-000000300217"; :>> outcome = VerdictKind::pass; :>> judgedAgainst = "cc9acb3"; :>> judgedAt = "2026-08-15"; :>> judgedBy = "claudeOpus5"; }

    verification sgCloseOutGate : Test { :>> id = "0d800218-0814-6218-9b3e-000000300218"; :>> title = "Sprint 294 closeOut gate (autonomous, D0049)"; :>> createdAt = "2026-08-15"; :>> createdBy = "claudeOpus5"; :>> method = VerificationMethod::inspect; :>> procedureText = "Autonomous closeOut (D0049). dcSupersededNeedGaps carries a passing DoD TestResult; issue088 resolves. Both affected views corrected and measured; the unaffected one checked and stated as unaffected with the reason. clippy clean; 137 lib tests; validate 316 clean; check-engine clean; 31 guards green. No gate bypassed."; }
    part sgCloseOutGateR1 : TestResult { :>> id = "0d800219-0814-6219-9b3e-000000300219"; :>> outcome = VerdictKind::pass; :>> judgedAgainst = "cc9acb3"; :>> judgedAt = "2026-08-15"; :>> judgedBy = "claudeOpus5"; }

    verification sgRetroGate : Test { :>> id = "0d80021a-0814-621a-9b3e-00000030021a"; :>> title = "Sprint 294 retro gate (autonomous, D0049)"; :>> createdAt = "2026-08-15"; :>> createdBy = "claudeOpus5"; :>> method = VerificationMethod::analyze; :>> procedureText = "Autonomous retro (D0049) under D0131's retroTrack. WELL: (1) the sibling views were RUN against the five known names rather than read for the assumption, and that is the only reason the coverage half was found — `coverage`'s own comment states the correct rule for Decisions, so reading it gives every impression the case is handled; (2) descoped items leave the denominator AND stay named, so the better number carries more information rather than less; (3) the item's predicted 98% is reported as the tool's actual 97%, because matching the backlog's rounding would have been the small dishonesty that makes every other number in the record slightly less trustworthy. AVOIDABLE-ISSUE 1: none. The finding was well-specified, the fix was in one place per view, and the only surprise — coverage sharing the blind spot — was something the item explicitly told me to go and check. Recording that plainly rather than manufacturing a finding. Estimate 3 pts, delivered."; }
    part sgRetroGateR1 : TestResult { :>> id = "0d80021b-0814-621b-9b3e-00000030021b"; :>> outcome = VerdictKind::pass; :>> judgedAgainst = "cc9acb3"; :>> judgedAt = "2026-08-15"; :>> judgedBy = "claudeOpus5"; }
}
