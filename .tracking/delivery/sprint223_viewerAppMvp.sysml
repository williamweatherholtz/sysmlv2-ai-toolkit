// ProjectDeliveryS223 — Sprint 223: viewerAppMvp — BUILD the keel-viewer app MVP (shape B / D0114,
// generative / D0117). A buildless static SPA over keel's committed API that GENERATES its UI from the
// declared model (types/attributes/actions) — nothing per-type hardcoded. Committed to the sysmlv2-viewer
// repo (5f55952); verified end-to-end in a browser against a live keel serve. Satisfies srViewerGenerativeUi
// + srViewerGraphExpand. Recorded per D0118. EXECUTE. 5 pts.
package ProjectDeliveryS223 {
    private import EngineElement::*;
    private import EngineWork::*;
    private import EngineVerification::*;
    private import EngineRequirements::*;
    private import EngineRelationships::*;

    #CharteredBy dependency from viewerAppMvpStory to d0117;

    part viewerAppMvpStory : Story {
        :>> id = "63940516-2c7d-4e8f-c223-51627384c001";
        :>> title = "Sprint 223: viewerAppMvp (5 pts) - build the generative viewer SPA over the keel API (shape B)";
        :>> createdAt = "2026-07-15"; :>> createdBy = "wweatherholtz"; :>> kind = WorkKind::code; :>> priority = WorkPriority::p1; :>> owner = "claudeOpus"; :>> estimatedPoints = 5;
    }

    // the MVP realises these viewer requirements (satisfy <requirement> by <satisfier>)
    satisfy srViewerGenerativeUi by viewerAppMvpStory;
    satisfy srViewerGraphExpand by viewerAppMvpStory;

    action def DeliveryRunS223 {
        action storyViewerAppMvp;
        verification storyViewerAppMvpDoD : Test { :>> id = "63940516-2c7d-4e8f-c223-51627384c002"; :>> method = VerificationMethod::demo; :>> procedureText = "Satisfies srViewerGenerativeUi + srViewerGraphExpand (shape B / D0114, generative / D0117; recorded per D0118). BUILT (sysmlv2-viewer repo, commit 5f55952): a BUILDLESS static SPA (app/index.html + app.js + styles.css + vendored cytoscape; no CDN/toolchain) that consumes keel's committed API and GENERATES its UI from the declared model — (1) discovers the API from GET /api/version (read+write endpoint contract); (2) a schema browser from GET /api/schema (every declared type + its attribute fields — 92 types, nothing hardcoded); (3) an explorable cytoscape graph from GET /api/slice (seed + depth/direction; click=detail, dbl-click=expand neighbours; generative per-type colour palette); (4) generative element detail from GET /api/item/:name (attributes ordered by the type's declared schema + typed edges, click-through); (5) a propose-a-Decision form generated from the Decision type's attributes, POSTing to /api/decision (status=proposed via keel's record process; acceptance stays a separate human gate). VERIFY (demo): live browser run (Playwright) against `keel serve .` — connected + API v1.5.0 discovered (18 read / 4 write); 92 types listed with attributes; slices for d0117 and nViewerGenerativeUi rendered as a graph; generative detail shown (Need/Decision attributes from schema); +Decision enabled via write-endpoint discovery. 0 console errors after the empty-overlay fix. POST /api/decision separately verified against a throwaway root (returns status=proposed) — not clicked live to avoid writing a stray Decision into this repo."; }
        part storyViewerAppMvpDoDR1 : TestResult { :>> id = "63940516-2c7d-4e8f-c223-51627384c003"; :>> outcome = VerdictKind::pass; :>> judgedAgainst = "33beb77"; :>> judgedAt = "2026-07-15"; :>> judgedBy = "claudeOpus"; :>> notes = "viewer code at sysmlv2-viewer@5f55952; verified against keel@33beb77 serve."; }
    }

    verification vamRefineGate : Test { :>> id = "63940516-2c7d-4e8f-c223-51627384c004"; :>> title = "Sprint 223 refine gate (DoR)"; :>> createdAt = "2026-07-15"; :>> createdBy = "claudeOpus"; :>> method = VerificationMethod::inspect; :>> procedureText = "DoR: user directed 'build the viewer app'. keel-side substrate ready (/api/schema S220, /api/decision + write discovery S221, CORS S222). Scope: the generative SPA MVP (connect, schema browser, graph explorer, generative detail, propose-Decision). estimatedPoints=5. #CharteredBy d0117. DoR met."; }
    part vamRefineGateR1 : TestResult { :>> id = "63940516-2c7d-4e8f-c223-51627384c005"; :>> outcome = VerdictKind::pass; :>> judgedAgainst = "33beb77"; :>> judgedAt = "2026-07-15"; :>> judgedBy = "claudeOpus"; }
    verification vamStandupGate : Test { :>> id = "63940516-2c7d-4e8f-c223-51627384c006"; :>> title = "Sprint 223 standup gate"; :>> createdAt = "2026-07-15"; :>> createdBy = "claudeOpus"; :>> method = VerificationMethod::inspect; :>> procedureText = "Approach: buildless SPA (reuse keel's vendored cytoscape), match the real API response shapes (slice: items/edges; item: attrs/outgoing/incoming; schema: types/attributes), generative rendering throughout. Serve statically + drive with Playwright against live keel serve. No blockers."; }
    part vamStandupGateR1 : TestResult { :>> id = "63940516-2c7d-4e8f-c223-51627384c007"; :>> outcome = VerdictKind::pass; :>> judgedAgainst = "33beb77"; :>> judgedAt = "2026-07-15"; :>> judgedBy = "claudeOpus"; }
    verification vamImplementGate : Test { :>> id = "63940516-2c7d-4e8f-c223-51627384c008"; :>> title = "Sprint 223 implement gate"; :>> createdAt = "2026-07-15"; :>> createdBy = "claudeOpus"; :>> method = VerificationMethod::demo; :>> procedureText = "SPA implemented + committed (sysmlv2-viewer@5f55952). Live browser verification passed: connect/discover, 92-type schema browser, graph slice + expand, generative detail, write-discovery. Empty-overlay CSS bug found + fixed (display:flex overrode [hidden]); re-verified 0 console errors."; }
    part vamImplementGateR1 : TestResult { :>> id = "63940516-2c7d-4e8f-c223-51627384c009"; :>> outcome = VerdictKind::pass; :>> judgedAgainst = "33beb77"; :>> judgedAt = "2026-07-15"; :>> judgedBy = "claudeOpus"; }
    verification vamReviewGate : Test { :>> id = "63940516-2c7d-4e8f-c223-51627384c00a"; :>> title = "Sprint 223 review gate"; :>> createdAt = "2026-07-15"; :>> createdBy = "claudeOpus"; :>> method = VerificationMethod::inspect; :>> procedureText = "Reviewed. The MVP proves the generative thesis (D0117) concretely: the entire type browser, node palette, detail forms, and write form are derived from /api/schema + /api/version at runtime — add a type/attribute/process to the model and it appears with no viewer code change. Cleanly shape B (separate app, own repo) consuming the committed, CORS-enabled API. Honest scope: the write path was verified by endpoint, not clicked live (avoids polluting this repo); node-label overlap + saved viewpoints + temporal state remain follow-ups. Clean."; }
    part vamReviewGateR1 : TestResult { :>> id = "63940516-2c7d-4e8f-c223-51627384c00b"; :>> outcome = VerdictKind::pass; :>> judgedAgainst = "33beb77"; :>> judgedAt = "2026-07-15"; :>> judgedBy = "claudeOpus"; }
    verification vamCloseOutGate : Test { :>> id = "63940516-2c7d-4e8f-c223-51627384c00c"; :>> title = "Sprint 223 closeOut gate (autonomous, D0049)"; :>> createdAt = "2026-07-15"; :>> createdBy = "claudeOpus"; :>> method = VerificationMethod::inspect; :>> procedureText = "Autonomous closeOut (D0049): DoD pass; the generative viewer MVP is built, browser-verified, and committed (sysmlv2-viewer@5f55952), and now RECORDED via governance (D0118 + this sprint) — closing the 'built but unrecorded' gap the user flagged. NEXT: SysML v2 standard-notation research (in flight) → then the axis-to-graphical-encoding viewpoint feature (color/position/swimlanes/nesting)."; }
    part vamCloseOutGateR1 : TestResult { :>> id = "63940516-2c7d-4e8f-c223-51627384c00d"; :>> outcome = VerdictKind::pass; :>> judgedAgainst = "33beb77"; :>> judgedAt = "2026-07-15"; :>> judgedBy = "claudeOpus"; }
    verification vamRetroGate : Test { :>> id = "63940516-2c7d-4e8f-c223-51627384c00e"; :>> title = "Sprint 223 retro gate (autonomous, D0049)"; :>> createdAt = "2026-07-15"; :>> createdBy = "claudeOpus"; :>> method = VerificationMethod::analyze; :>> procedureText = "Autonomous retro (D0049). WELL: delivered a genuinely generative MVP (not a hardcoded viewer) and verified it in a real browser, not just by asserting endpoints. AVOIDABLE-ISSUE (the user's correction, now a banked lesson + memory): I built + committed the app but had NOT recorded it via governance — recording is PART of the task, not a later step. Fixed by authoring D0118 + this sprint in the SAME effort going forward. Also: [hidden] is overridden by an explicit CSS display — set display:none in the [hidden] rule. LESSON: for every deliverable, author its Decision + delivery sprint + satisfy edges as it is produced; unrecorded work is not done. Estimate 5 pts. NEXT: notation research → axis-encoding viewpoints."; }
    part vamRetroGateR1 : TestResult { :>> id = "63940516-2c7d-4e8f-c223-51627384c00f"; :>> outcome = VerdictKind::pass; :>> judgedAgainst = "33beb77"; :>> judgedAt = "2026-07-15"; :>> judgedBy = "claudeOpus"; }
}
