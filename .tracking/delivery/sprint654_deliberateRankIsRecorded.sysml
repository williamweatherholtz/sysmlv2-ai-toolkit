// ProjectDeliveryS654 — Sprint 654: Deliver dcDeliberateRankIsRecorded (issue345): the priority-inversion guard's 'if that is deliberate say so' gets a home the guard can read. A #PrioritizedBy dependency edge from a ready item to the Statement or Decision that ranks it is the record; the guard does not warn on an item carrying one, keel show priority lists the citation, and an edge to any other type is a violation. D0429 (proposed, process-change) is the co-committed record of the process and schema change.. EXECUTE. 3 pts.
package ProjectDeliveryS654 {
    private import EngineElement::*;
    private import EngineWork::*;
    private import EngineVerification::*;
    private import EngineRelationships::*;

    #CharteredBy dependency from deliberateRankIsRecordedStory to d0429;

    part deliberateRankIsRecordedStory : Story {
        :>> id = "a2d73a6a-8a26-4799-a26b-4950854eae67";
        :>> title = "Sprint 654: Deliver dcDeliberateRankIsRecorded (issue345): the priority-inversion guard's 'if that is deliberate say so' gets a home the guard can read. A #PrioritizedBy dependency edge from a ready item to the Statement or Decision that ranks it is the record; the guard does not warn on an item carrying one, keel show priority lists the citation, and an edge to any other type is a violation. D0429 (proposed, process-change) is the co-committed record of the process and schema change. (3 pts)";
        :>> createdAt = "2026-09-10"; :>> createdBy = "claudeOpus5"; :>> kind = WorkKind::code; :>> priority = WorkPriority::p0; :>> owner = "claudeOpus5"; :>> estimatedPoints = 3;
    }

    action def DeliveryRunS654 {
        action storyDeliberateRankIsRecorded;
        verification storyDeliberateRankIsRecordedDoD : Test { :>> id = "18f5fcd9-941c-4e76-97e1-ec57df10749e"; :>> method = VerificationMethod::test; :>> procedureText = "metadata def PrioritizedBy in schema/core/relationships.sysml; view::priority_records reads the edges and classes each as a record (Statement or Decision target) or a violation; inversion_pairs takes the recorded set and exempts the outranking item; PrioritySignal carries ranked_by and show priority carries rankedBy per row plus recorded and recordViolations; the guard prints the remaining inversions naming the edge to author, and reports each ill-typed edge as a violation. VERIFY (the DoD's three clauses, probed live against the HEAD-order backlog): with the edge from dcDeliberateRankIsRecorded to st066 the guard's 27 warnings became 26 and show priority listed the record; removing the edge restored 27; an edge to issue345 produced one violation naming the type. Unit tests cover the same three cases against a fixture. refineAssessPriority names the edge in place of the block comment; guards.md row updated; clippy clean."; }
        // RAN: verifier receipt (D0425): lib 466/0 incl. the 3 priority tests; clippy 0; validate 745 clean; check-engine clean; guard ALL PASS exit 0 with priority-inversion 0 scanned; show priority inversions 0 with rankedBy on every row
        part storyDeliberateRankIsRecordedDoDR1 : TestResult { :>> id = "851f991a-3e6e-458a-a32b-381d647964b9"; :>> outcome = VerdictKind::pass; :>> judgedAgainst = "1961ab34e9783f9533a21891d175f4989d372e69"; :>> judgedAt = "2026-09-10T14:07:05Z"; :>> judgedBy = "claudeOpus5"; }
    }

    verification deliberateRankIsRecordedRefineGate : Test { :>> id = "0ddf539e-e1c8-41d9-9d50-b3e6e426622c"; :>> title = "Sprint 654 refine gate (DoR)"; :>> createdAt = "2026-09-10"; :>> createdBy = "claudeOpus5"; :>> method = VerificationMethod::inspect; :>> procedureText = "One ready item, 3 points: a frozen-schema marker (CR via D0429), a view change, a guard change with tests, a process-text change and doc-sync. Ready: issue345 names the mechanism and its measurement, the guard and the view are one function each, and the DoD names its checks. The two items the DoD's VERIFY names (st066's control-structure work) are done, so the live probe ran against today's 27-warning inversion set instead and is recorded as such."; }
    // RAN: verifier receipt (D0425): validate 745 clean; check-engine clean; whats-next head dcIdIsAUuid then dcDeliberateRankIsRecorded
    part deliberateRankIsRecordedRefineGateR1 : TestResult { :>> id = "5e4e7c9a-1b51-42b3-937e-3915c0c6b3af"; :>> outcome = VerdictKind::pass; :>> judgedAgainst = "1961ab34e9783f9533a21891d175f4989d372e69"; :>> judgedAt = "2026-09-10T14:07:05Z"; :>> judgedBy = "claudeOpus5"; }
    verification deliberateRankIsRecordedStandupGate : Test { :>> id = "5331265c-c12d-4516-9596-62902fcd5659"; :>> title = "Sprint 654 standup gate"; :>> createdAt = "2026-09-10"; :>> createdBy = "claudeOpus5"; :>> method = VerificationMethod::inspect; :>> procedureText = "No blocker. One finding on the live tree: the 27 standing warnings had no recorded reason - no Statement or Decision ranks the 27 items above dcIdIsAUuid (High, issue454) - so the honest discharge was D0052's own: dcIdIsAUuid moved to the head of the ready block, zero inversions, no edge authored. The record mechanism was exercised live only as a transient probe, never committed, because no fact justified a permanent edge."; }
    // RAN: verifier receipt (D0425): show priority inversions 0, recorded [], recordViolations [], rankedBy on every row; guard priority-inversion PASS 0 scanned
    part deliberateRankIsRecordedStandupGateR1 : TestResult { :>> id = "a213a912-b2a1-4104-bfca-71522ba18b9d"; :>> outcome = VerdictKind::pass; :>> judgedAgainst = "1961ab34e9783f9533a21891d175f4989d372e69"; :>> judgedAt = "2026-09-10T14:07:05Z"; :>> judgedBy = "claudeOpus5"; }
    verification deliberateRankIsRecordedImplementGate : Test { :>> id = "8b9d1c84-8c5f-438e-8b0e-70727f62db4a"; :>> title = "Sprint 654 implement gate"; :>> createdAt = "2026-09-10"; :>> createdBy = "claudeOpus5"; :>> method = VerificationMethod::test; :>> procedureText = "keel-cli/src/view/mod.rs: priority_records(model) -> (item -> citation, violations); PriorityInversions { pairs, recorded, violations }; inversions_of(signals, violations); inversion_pairs(ready, recorded); PrioritySignal.ranked_by; priority() emits rankedBy, recorded, recordViolations; priority_inversions() returns the struct. keel-cli/src/guards.rs: priority_inversion reads the struct, the warning names the edge to author, violations carry through. .engine/schema/core/relationships.sysml: metadata def PrioritizedBy. .engine/processes/agile-workflow.sysml refineAssessPriority: RECORD as the edge, not the block comment. .engine/docs/guards.md: the row. .tracking/backlog.sysml: dcIdIsAUuid reordered to the head. Tests: inversion_pairs_flags_lower_severity_work_ranked_above_high gains the recorded/removed pair; priority_records_read_the_edge_and_refuse_a_target_that_is_not_a_word_or_a_judgment covers Statement, Decision, Issue and an unresolved target end to end through inversions_of."; }
    // RAN: verifier receipt (D0425): cargo test --lib inversion_pairs priority_records 3 passed 0 failed; cargo test --lib 466 passed 0 failed; clippy 0; metadata def PrioritizedBy = 1 in relationships.sysml
    part deliberateRankIsRecordedImplementGateR1 : TestResult { :>> id = "e4413977-ee5e-4648-b629-df03f1163c08"; :>> outcome = VerdictKind::pass; :>> judgedAgainst = "1961ab34e9783f9533a21891d175f4989d372e69"; :>> judgedAt = "2026-09-10T14:07:05Z"; :>> judgedBy = "claudeOpus5"; }
    verification deliberateRankIsRecordedReviewGate : Test { :>> id = "8829ee0a-e6ce-474b-adfa-969572859043"; :>> title = "Sprint 654 review gate — three passes per D0172"; :>> createdAt = "2026-09-10"; :>> createdBy = "claudeOpus5"; :>> method = VerificationMethod::inspect; :>> procedureText = "Live probe against HEAD order (git stash of the reorder): 27 warnings -> 26 with the edge to st066, show priority recorded = [dcDeliberateRankIsRecorded -> st066], rankedBy on the row; edge removed -> 27; edge to issue345 -> FAIL 1 violation 'the target is of type Issue, not a Statement or Decision'. Reordered tree: 0 scanned, 0 warnings. Unit tests 3/3 on the priority functions; clippy clean after one into_iter-on-singleton fix. guard --no-receipt ALL PASS with the Decision staged (process-change 2 scanned, marker-vocabulary 3456 scanned, doc-sync 2 scanned)."; }
    // RAN: verifier receipt (D0425): guard --no-receipt ALL PASS exit 0 - process-change 2 scanned, marker-vocabulary 3457 scanned, doc-sync 2 scanned; PrioritizedBy named in agile-workflow.sysml and guards.md
    part deliberateRankIsRecordedReviewGateR1 : TestResult { :>> id = "da0fa5bd-b12a-447d-92b6-80b20d72bb9f"; :>> outcome = VerdictKind::pass; :>> judgedAgainst = "1961ab34e9783f9533a21891d175f4989d372e69"; :>> judgedAt = "2026-09-10T14:07:05Z"; :>> judgedBy = "claudeOpus5"; }
    verification deliberateRankIsRecordedCloseOutGate : Test { :>> id = "28e2011b-5644-44a8-8687-8a014d7666e6"; :>> title = "Sprint 654 closeOut gate (autonomous, D0049)"; :>> createdAt = "2026-09-10"; :>> createdBy = "claudeOpus5"; :>> method = VerificationMethod::inspect; :>> procedureText = "Delivered: the record, the guard reading it, the lens listing it, the schema marker, the process text, and a backlog with zero inversions by reorder. D0429 stays proposed for the human (D0337); the code lands with it because the lock checks the marker's presence. Not delivered: no permanent #PrioritizedBy edge exists yet, because no recorded word ranks any current inversion - the first real edge is the human's to cause."; }
    // RAN: verifier receipt (D0425): validate 745 clean; check-engine clean; guard ALL PASS exit 0
    part deliberateRankIsRecordedCloseOutGateR1 : TestResult { :>> id = "7ee904ea-9d46-4b9f-9d1f-28645c625bd5"; :>> outcome = VerdictKind::pass; :>> judgedAgainst = "1961ab34e9783f9533a21891d175f4989d372e69"; :>> judgedAt = "2026-09-10T14:07:05Z"; :>> judgedBy = "claudeOpus5"; }
    verification deliberateRankIsRecordedRetroGate : Test { :>> id = "c7f20847-d993-4f6a-abfe-863c39de2109"; :>> title = "Sprint 654 retro gate (autonomous, D0049)"; :>> createdAt = "2026-09-10"; :>> createdBy = "claudeOpus5"; :>> method = VerificationMethod::analyze; :>> procedureText = "Autonomous retro (D0049). AVOIDABLE-ISSUE SCAN: no avoidable issue and no new item. Finding 1, not avoidable: the DoD's VERIFY named two items that were done by the time the work was reached, so the clause could not run as written; the probe ran against the live inversion set with the same three cases and the sprint record says so. A DoD that names a live item as its fixture ages with the frontier; the probe-first rule d0388 already covers the remedy - name the cases, not the items - and the existing item dcGuardPoolDispatchesLongestFirst (sprint 653) carries a DoD written that way, so the finding is already tracked there and no item is added. Finding 2, not avoidable: the harness denied two heredocs carrying a backslash (D0309) and each was rewritten through the Write tool; the control fired as designed, twice, on the agent's act."; }
    // RAN: verifier receipt (D0425): guard retro-backlog PASS 1 scanned 0 violations after the retro named dcGuardPoolDispatchesLongestFirst
    part deliberateRankIsRecordedRetroGateR1 : TestResult { :>> id = "b58cbe82-e3fd-4155-b759-74a22896bd9c"; :>> outcome = VerdictKind::pass; :>> judgedAgainst = "1961ab34e9783f9533a21891d175f4989d372e69"; :>> judgedAt = "2026-09-10T14:07:05Z"; :>> judgedBy = "claudeOpus5"; }
}
