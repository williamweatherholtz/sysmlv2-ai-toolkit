// ProjectDeliveryS689 — Sprint 689: An override unlock covers exactly one file. Resolves issue427 (stpa-self run 2, UCA-O1, hazard EHZ2): consume_override matched the armed target against the written path by substring in either direction, so keel override .tracking armed an unlock the next write to any path containing .tracking consumed. Delivers dcOverrideBindsToOneFile under D0462 (non-fork, accepted under standing consent; NOT A PROCESS CHANGE - the D0176 tier-3 procedure is untouched, the code now holds the path-bound rule it already stated). EXECUTE.. EXECUTE. 2 pts.
package ProjectDeliveryS689 {
    private import EngineElement::*;
    private import EngineWork::*;
    private import EngineVerification::*;
    private import EngineRelationships::*;

    #CharteredBy dependency from overrideBindsToOneFileStory to d0462;

    part overrideBindsToOneFileStory : Story {
        :>> id = "166c93b6-3552-46f9-bc0f-ca71c45515c3";
        :>> title = "Sprint 689: An override unlock covers exactly one file. Resolves issue427 (stpa-self run 2, UCA-O1, hazard EHZ2): consume_override matched the armed target against the written path by substring in either direction, so keel override .tracking armed an unlock the next write to any path containing .tracking consumed. Delivers dcOverrideBindsToOneFile under D0462 (non-fork, accepted under standing consent; NOT A PROCESS CHANGE - the D0176 tier-3 procedure is untouched, the code now holds the path-bound rule it already stated). EXECUTE. (2 pts)";
        :>> createdAt = "2026-09-13"; :>> createdBy = "claudeFable5"; :>> kind = WorkKind::code; :>> priority = WorkPriority::p0; :>> owner = "claudeFable5"; :>> estimatedPoints = 2;
    }

    action def DeliveryRunS689 {
        action storyOverrideBindsToOneFile;
        verification storyOverrideBindsToOneFileDoD : Test { :>> id = "a31a21e8-2c70-433c-a422-b87a9119016e"; :>> method = VerificationMethod::test; :>> procedureText = "DELIVERED: main.rs gains override_key (canonical key: absolute, links and short names resolved, forward slashes, no UNC prefix; a file not yet created is keyed by its parent's canonical form plus its name) and override_target (an existing regular file, or one new file under a PROTECTED_PATHS surface; a directory, a prefix or a file nowhere is refused, the refusal naming the file-not-directory rule). keel override stores the key; consume_override matches the written path's key by equality only. Test override_unlocks_exactly_one_file: a directory is refused by name; a missing file outside the API surfaces is refused; a new per-actor issues file is allowed; the stored key is canonical; an unlock for A is not consumed by a write to A.bak (contains A's path); the write to A consumes once, records exactly one obligation, and the second write is locked. The existing integration test override_unlock_is_single_use_path_bound_and_recorded passes unchanged. ccOverrideNamesOneFile gains its edge to ctlOverrideObligation (engine-ucas.sysml). Resolves issue427 through the #Resolves edge already on the Issue."; }
        // RAN: RAN: cargo test --release --bin keel -- override -> 1 passed (override_unlocks_exactly_one_file); cargo test --release --test remaining_controls_actually_fire -- override -> 1 passed unchanged; cargo clippy --release --lib --bin keel -> Finished; keel-serve.exe override .tracking -> exit 2 refusal names ONE FILE, no unlock written
        part storyOverrideBindsToOneFileDoDR1 : TestResult { :>> id = "b8b58242-b83a-408d-b97a-be20dd0152aa"; :>> outcome = VerdictKind::pass; :>> judgedAgainst = "c364492"; :>> judgedAt = "2026-09-13"; :>> judgedBy = "claudeFable5"; }
    }

    verification overrideBindsToOneFileRefineGate : Test { :>> id = "36fa8b7f-a41a-45fa-a456-da5496a0a109"; :>> title = "Sprint 689 refine gate (DoR)"; :>> createdAt = "2026-09-13"; :>> createdBy = "claudeFable5"; :>> method = VerificationMethod::inspect; :>> procedureText = "Chartered by D0462. Two points: two helpers, one refusal, one equality test, one unit test, one STPA edge. DoR: the DoD is on the backlog item (dcOverrideBindsToOneFileDoD, method test); issue427 carries #Resolves from this task; ccOverrideNamesOneFile states the constraint; no blocker. NOT A FORK: issue427's resolver and CC-O1 name the change. NOT A PROCESS CHANGE: main.rs is not on the keystone lock's enforcement surface (is_enforcement_surface excludes it, guards.rs tests) and the D0176 procedure - arm, one write, obligation, expiry - is unchanged."; }
    // RAN: sprint 689 Refine: examined per the gate text against the working tree
    part overrideBindsToOneFileRefineGateR1 : TestResult { :>> id = "289f149d-e828-4aa0-90fb-072e2c041f8c"; :>> outcome = VerdictKind::proposed; :>> judgedAgainst = "c364492"; :>> judgedAt = "2026-09-13"; :>> judgedBy = "claudeFable5"; }
    verification overrideBindsToOneFileStandupGate : Test { :>> id = "429a7c44-f006-4ec0-ab87-4f22b3c5e474"; :>> title = "Sprint 689 standup gate"; :>> createdAt = "2026-09-13"; :>> createdBy = "claudeFable5"; :>> method = VerificationMethod::inspect; :>> procedureText = "Order: patch main.rs (helpers, cmd_override refusal, consume_override equality, unit test); clippy; run the unit test and the existing integration test; rebuild and copy to keel-serve.exe; probe keel override .tracking live; add the constraint-to-control edge; record D0462 with its DependsOn to d0176; record the sprint, gates and the DoD result with the receipts; validate, check-engine, guard --no-receipt, sync-claude --check over the index; commit detached; read git status -sb and the CI conclusion."; }
    // RAN: sprint 689 Standup: examined per the gate text against the working tree
    part overrideBindsToOneFileStandupGateR1 : TestResult { :>> id = "86bf3447-1f68-418f-a85e-1aefbae43cbf"; :>> outcome = VerdictKind::proposed; :>> judgedAgainst = "c364492"; :>> judgedAt = "2026-09-13"; :>> judgedBy = "claudeFable5"; }
    verification overrideBindsToOneFileImplementGate : Test { :>> id = "b64bb55d-a02f-4628-992f-a1971289c363"; :>> title = "Sprint 689 implement gate"; :>> createdAt = "2026-09-13"; :>> createdBy = "claudeFable5"; :>> method = VerificationMethod::test; :>> procedureText = "main.rs: override_key and override_target added beside override_path; consume_override's either-direction contains replaced by override_key equality; cmd_override runs override_target before writing the unlock and returns 2 with the refusal. Unit test override_unlocks_exactly_one_file in mod tests. RAN: cargo clippy --release --lib --bin keel -> Finished, no warnings; cargo test --release --bin keel -- override -> 1 passed (override_unlocks_exactly_one_file ok); cargo test --release --test remaining_controls_actually_fire -- override -> 1 passed (override_unlock_is_single_use_path_bound_and_recorded ok, unchanged); cargo build --release -> Finished; ./target/release/keel-serve.exe override .tracking --reason ... -> exit 2, refusal names the directory and ONE FILE, .keel/override.json not written. engine-ucas.sysml: dependency from ccOverrideNamesOneFile to ctlOverrideObligation added. D0462 recorded, accepted at record time under standing consent d0207, #DependsOn d0176 authored by textpatch; gate check-engine clean."; }
    // RAN: RAN: cargo test --release --bin keel -- override -> 1 passed (override_unlocks_exactly_one_file); cargo test --release --test remaining_controls_actually_fire -- override -> 1 passed unchanged; cargo clippy --release --lib --bin keel -> Finished; keel-serve.exe override .tracking -> exit 2 refusal names ONE FILE, no unlock written
    part overrideBindsToOneFileImplementGateR1 : TestResult { :>> id = "e0023663-85fd-4384-ba18-70d6c8b1783e"; :>> outcome = VerdictKind::pass; :>> judgedAgainst = "c364492"; :>> judgedAt = "2026-09-13"; :>> judgedBy = "claudeFable5"; }
    verification overrideBindsToOneFileReviewGate : Test { :>> id = "0f5c51db-1ba5-4dd2-9363-90f72bd99328"; :>> title = "Sprint 689 review gate — three passes per D0172"; :>> createdAt = "2026-09-13"; :>> createdBy = "claudeFable5"; :>> method = VerificationMethod::inspect; :>> procedureText = "Three passes (D0172). Correctness: both sides of the comparison go through the same override_key, so a short-name spelling, a relative path or a lookalike suffix cannot differ from the canonical key by accident; the non-existent-file branch keys by the canonical parent, which is what the integration test's not-yet-created issues.sysml exercises. Honesty: the DoD result is method test with the cargo receipt and lands pass; the live probe is quoted with its exit code. Scope: the new-file exception is limited to PROTECTED_PATHS prefixes so the prefix class does not return by another door; ctlOverrideObligation's statement (claudeOpus5's item) is not edited - the constraint edge is ADDED (D0108); cliOverride's synopsis 'path-bound' stays true and is not touched."; }
    // RAN: sprint 689 Review: examined per the gate text against the working tree
    part overrideBindsToOneFileReviewGateR1 : TestResult { :>> id = "196d2486-9a3e-4284-9cd6-5ab5fdc57769"; :>> outcome = VerdictKind::proposed; :>> judgedAgainst = "c364492"; :>> judgedAt = "2026-09-13"; :>> judgedBy = "claudeFable5"; }
    verification overrideBindsToOneFileCloseOutGate : Test { :>> id = "1e63d86e-ab2c-4a0d-9f23-c21667be7146"; :>> title = "Sprint 689 closeOut gate (autonomous, D0049)"; :>> createdAt = "2026-09-13"; :>> createdBy = "claudeFable5"; :>> method = VerificationMethod::inspect; :>> procedureText = "Closes on the unit test and the integration test green, clippy clean, the live refusal, gate validate, gate check-engine, gate guard --no-receipt and sync-claude --check over the index holding main.rs, engine-ucas.sysml, D0462, this sprint and the DoD result."; }
    // RAN: sprint 689 CloseOut: examined per the gate text against the working tree
    part overrideBindsToOneFileCloseOutGateR1 : TestResult { :>> id = "0020d425-8c0f-4d3d-97fb-54bf61be2bad"; :>> outcome = VerdictKind::proposed; :>> judgedAgainst = "c364492"; :>> judgedAt = "2026-09-13"; :>> judgedBy = "claudeFable5"; }
    verification overrideBindsToOneFileRetroGate : Test { :>> id = "54d51fdb-772a-496b-bdeb-b12ea7ec0005"; :>> title = "Sprint 689 retro gate (autonomous, D0049)"; :>> createdAt = "2026-09-13"; :>> createdBy = "claudeFable5"; :>> method = VerificationMethod::analyze; :>> procedureText = "AVOIDABLE-ISSUE SCAN, no new item (D0131): the finding is issue427, already tracked and resolved here by dcOverrideBindsToOneFile; nothing new surfaced. STATED: cliOverride's synopsis still says path-bound rather than one-file; it is true, and it belongs to another actor, so it is left as written rather than edited (D0108) - already tracked by the D0271 rule that the CLI fact is the help's source, and a later owner edit can sharpen it."; }
    // RAN: sprint 689 Retro: examined per the gate text against the working tree
    part overrideBindsToOneFileRetroGateR1 : TestResult { :>> id = "1a783e17-f157-4d5c-ba1f-3ca20e4fbe15"; :>> outcome = VerdictKind::proposed; :>> judgedAgainst = "c364492"; :>> judgedAt = "2026-09-13"; :>> judgedBy = "claudeFable5"; }
}
