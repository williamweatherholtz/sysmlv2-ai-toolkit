// ProjectDeliveryS621 — Sprint 621: Sprint 621 makes recalled facts that arrive after the cap useful instead of discarded (recallCapFate, D0390 option A, the human's word 2026-09-09): the user-prompt hook pushes them LATE with the latency named and counts the fire recall-slow, and keel enforcement-report counts slow beside the pre-D0390 skipped.. EXECUTE. 2 pts.
package ProjectDeliveryS621 {
    private import EngineElement::*;
    private import EngineWork::*;
    private import EngineVerification::*;
    private import EngineRelationships::*;

    #CharteredBy dependency from recallCapFateStory to d0390;

    part recallCapFateStory : Story {
        :>> id = "dcb558fe-3bb5-449b-8d17-be0345bf790d";
        :>> title = "Sprint 621: Sprint 621 makes recalled facts that arrive after the cap useful instead of discarded (recallCapFate, D0390 option A, the human's word 2026-09-09): the user-prompt hook pushes them LATE with the latency named and counts the fire recall-slow, and keel enforcement-report counts slow beside the pre-D0390 skipped. (2 pts)";
        :>> createdAt = "2026-09-09"; :>> createdBy = "claudeOpus5"; :>> kind = WorkKind::code; :>> priority = WorkPriority::p0; :>> owner = "claudeOpus5"; :>> estimatedPoints = 2;
    }

    action def DeliveryRunS621 {
        action storyRecallCapFate;
        verification storyRecallCapFateDoD : Test { :>> id = "49258da4-26a8-4f79-9be0-f8d1531b1bd7"; :>> method = VerificationMethod::test; :>> procedureText = "DONE MEANS: recalled facts that arrive after the 2,500 ms cap are pushed to the turn instead of dropped, because the cap is read after the walk and a drop saves nothing. Implements D0390 option A. DO: recalled_facts pushes past the cap with the ms named in its header and emits a recall-slow ledger event (recall-skipped no longer fires, staying in the ledger as pre-D0390 history); enforcement-report's recall section counts slow with its rate and named turns beside skipped; CLAUDE.md's recall line says facts past the cap are pushed late, not dropped. VERIFY: a pm test that a recall-slow ledger line is counted as slow with its rate and named turn, beside a recall-skipped counted as skipped; the live enforcement-report carries slow and skipped; recalled_facts returns the facts (not a SKIPPED line) past the cap."; }
        // RAN: recalled_facts pushes late + emits recall-slow; enforcement-report counts slow beside skipped; pm test recall_slow; CLAUDE.md updated; D0390 option A
        part storyRecallCapFateDoDR1 : TestResult { :>> id = "74894d38-8770-493e-b765-987529bd9b3e"; :>> outcome = VerdictKind::pass; :>> judgedAgainst = "996f8bbead9ddd49def96a4938c742d3911d1ce3"; :>> judgedAt = "2026-09-09"; :>> judgedBy = "claudeOpus5"; }
    }

    verification recallCapFateRefineGate : Test { :>> id = "5fcceb75-e0a8-455a-9cef-4ea34627c516"; :>> title = "Sprint 621 refine gate (DoR)"; :>> createdAt = "2026-09-09"; :>> createdBy = "claudeOpus5"; :>> method = VerificationMethod::inspect; :>> procedureText = "Scope: keel-cli/src/main.rs recalled_facts (the over-cap branch pushes late + emits recall-slow); keel-cli/src/pm.rs (collect recall-slow, recall_degradation reports slow beside skipped, a recall_turns helper, a test); CLAUDE.md the recall paragraph. D0390 is the accepted direction (option A, human word 2026-09-09). Out of scope: raising RECALL_CAP_MS (option B, not chosen) and removing the cap entirely; the cap stays as the reporting threshold that decides slow-vs-fast. Estimate 2 points: a hook branch, a report extension with a test, a doc line. DoR: points set, charter d0390, scope clear, no blocking dependency, DoD authored."; }
    // RAN: DoR: 2 points, charter d0390, scope in refine text, DoD authored, no blocking dependency
    part recallCapFateRefineGateR1 : TestResult { :>> id = "ca0617f3-4b82-4000-9260-6f6c8d5aa0ea"; :>> outcome = VerdictKind::pass; :>> judgedAgainst = "996f8bbead9ddd49def96a4938c742d3911d1ce3"; :>> judgedAt = "2026-09-09"; :>> judgedBy = "claudeOpus5"; }
    verification recallCapFateStandupGate : Test { :>> id = "1a2f3379-c498-45a9-ade9-9c53d62fa34d"; :>> title = "Sprint 621 standup gate"; :>> createdAt = "2026-09-09"; :>> createdBy = "claudeOpus5"; :>> method = VerificationMethod::inspect; :>> procedureText = "Plan: (1) recalled_facts: past the cap, ledger_emit recall-slow and return the facts with a header naming the ms and the cap, rather than emitting recall-skipped and returning a SKIPPED line; (2) pm.rs: collect recall-slow into its own vec, recall_degradation reports slow / slowRatePct / slowTurns beside skipped / skipRatePct / skippedTurns via a shared recall_turns helper, note updated; (3) a pm test with one recall-slow and one recall-skipped line asserting each is counted apart with its rate and turn; (4) CLAUDE.md says facts past the cap are pushed late; (5) sync-claude, gates."; }
    // RAN: plan of five steps in the standup text; all five executed in this commit
    part recallCapFateStandupGateR1 : TestResult { :>> id = "59035fd8-a918-4ed9-86b1-8f233d933366"; :>> outcome = VerdictKind::pass; :>> judgedAgainst = "996f8bbead9ddd49def96a4938c742d3911d1ce3"; :>> judgedAt = "2026-09-09"; :>> judgedBy = "claudeOpus5"; }
    verification recallCapFateImplementGate : Test { :>> id = "dd940baa-a7b2-489b-b90f-c219653e46d3"; :>> title = "Sprint 621 implement gate"; :>> createdAt = "2026-09-09"; :>> createdBy = "claudeOpus5"; :>> method = VerificationMethod::test; :>> procedureText = "RAN: cargo build --release clean; cargo clippy --release --all-targets -D warnings exit 0; cargo test --release --lib pm:: 5 passed 0 failed (incl. recall_slow_is_counted_beside_the_pre_d0390_skipped); keel enforcement-report . recall carries slow/skipped both 0 on this fresh-since-build ledger with the D0390 note; keel sync-claude; keel validate . 706 clean; keel guard exit 0; keel guard doc-sync PASS."; }
    // RAN: cargo build --release clean; cargo clippy --release --all-targets -D warnings exit 0; cargo test --release --lib pm:: 5 passed 0 failed incl recall_slow_is_counted_beside_the_pre_d0390_skipped; enforcement-report recall carries slow/skipped with the D0390 note; sync-claude; keel validate . 706 clean; keel guard exit 0; doc-sync PASS
    part recallCapFateImplementGateR1 : TestResult { :>> id = "7ebc3c54-eb92-4013-8d5e-5d64ef44f937"; :>> outcome = VerdictKind::pass; :>> judgedAgainst = "996f8bbead9ddd49def96a4938c742d3911d1ce3"; :>> judgedAt = "2026-09-09"; :>> judgedBy = "claudeOpus5"; }
    verification recallCapFateReviewGate : Test { :>> id = "94161b51-e684-444f-83b9-0e5714f30816"; :>> title = "Sprint 621 review gate — three passes per D0172"; :>> createdAt = "2026-09-09"; :>> createdBy = "claudeOpus5"; :>> method = VerificationMethod::inspect; :>> procedureText = "Reviewed against the DoD: recalled_facts past the cap emits recall-slow and returns the facts with the latency named, not a SKIPPED line (main.rs); the report counts slow beside skipped, each with rate and named turns (pm test, live report); CLAUDE.md's recall line says late-not-dropped; recall-skipped is preserved as history."; }
    // RAN: reviewed vs DoD: recalled_facts past the cap emits recall-slow and returns facts with the ms named not a SKIPPED line; report counts slow beside skipped with rate and named turns; CLAUDE.md says late-not-dropped; recall-skipped kept as history
    part recallCapFateReviewGateR1 : TestResult { :>> id = "5640436c-bc30-4c80-9895-b5e3e3a1dcce"; :>> outcome = VerdictKind::pass; :>> judgedAgainst = "996f8bbead9ddd49def96a4938c742d3911d1ce3"; :>> judgedAt = "2026-09-09"; :>> judgedBy = "claudeOpus5"; }
    verification recallCapFateCloseOutGate : Test { :>> id = "c0f57af8-f6d8-4a5f-9abb-8dda3adcb5e9"; :>> title = "Sprint 621 closeOut gate (autonomous, D0049)"; :>> createdAt = "2026-09-09"; :>> createdBy = "claudeOpus5"; :>> method = VerificationMethod::inspect; :>> procedureText = "Sprint 621 closes when recallCapFateDoD carries a pass at the commit that carries the hook branch, the report extension and the doc line, and CI is green."; }
    // RAN: DoD pass on storyRecallCapFateDoD at this SHA; CI verified on the push
    part recallCapFateCloseOutGateR1 : TestResult { :>> id = "41b4014c-982f-4aa3-942f-94b4c856142d"; :>> outcome = VerdictKind::pass; :>> judgedAgainst = "996f8bbead9ddd49def96a4938c742d3911d1ce3"; :>> judgedAt = "2026-09-09"; :>> judgedBy = "claudeOpus5"; }
    verification recallCapFateRetroGate : Test { :>> id = "ac64ef40-3850-4651-9842-efd84cf1995a"; :>> title = "Sprint 621 retro gate (autonomous, D0049)"; :>> createdAt = "2026-09-09"; :>> createdBy = "claudeOpus5"; :>> method = VerificationMethod::analyze; :>> procedureText = "Retro held; avoidable-issue scan: no new item - this sprint implements the accepted d0390 exactly and surfaced no defect, so there is nothing beyond d0390 to track. Process improvement: the cap remains as a threshold that classifies rather than discards, so the memory channel is least available never means unavailable - the busiest turns now keep their facts, late, and the lateness is a counted rate."; }
    // RAN: retro held; follows accepted D0390 with no new defect; no new Issue
    part recallCapFateRetroGateR1 : TestResult { :>> id = "defd0d69-2198-4ae4-8e7e-c12cd142cc69"; :>> outcome = VerdictKind::pass; :>> judgedAgainst = "996f8bbead9ddd49def96a4938c742d3911d1ce3"; :>> judgedAt = "2026-09-09"; :>> judgedBy = "claudeOpus5"; }
}
