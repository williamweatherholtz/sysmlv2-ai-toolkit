// ProjectDeliveryS354 — Sprint 354: the first deck review comes back. 4 acceptances, 19 dispositions,
// 34 sprints accepted, and a delegation that weakens an attestation control. CHANGE (§3a). 5 pts.
package ProjectDeliveryS354 {
    private import EngineElement::*;
    private import EngineWork::*;
    private import EngineVerification::*;
    private import EngineRelationships::*;

    #CharteredBy dependency from deckIntakeStory to d0165;

    part deckIntakeStory : Story {
        :>> id = "0d8005d0-0814-65d0-9b3e-0000003005d0";
        :>> title = "Sprint 354: deck review intake — the queue clears, and finding disposition is delegated (D0165, 5 pts)";
        :>> createdAt = "2026-08-20"; :>> createdBy = "claudeOpus5"; :>> kind = WorkKind::decision; :>> priority = WorkPriority::p0; :>> owner = "claudeOpus5"; :>> estimatedPoints = 5;
    }

    action def DeliveryRunS354 {
        action storyDeckIntake;
        verification storyDeckIntakeDoD : Test { :>> id = "0d8005d1-0814-65d1-9b3e-0000003005d1"; :>> method = VerificationMethod::test; :>> procedureText = "Delivered by dcDeckReviewIntake. THE DECK CAME BACK WITH 24 JUDGMENTS AND AN INSTRUCTION, and the whole queue cleared: pendingAcceptances 4 to 0, undispositioned 23 to 0 of 116, sittings due 34 to 0. RECORDED AS THEIRS: four Decision acceptances through `keel accept` (d0161-d0164, which also resolves d0164 having been applied-but-unaccepted); nineteen finding dispositions carrying each per-item note VERBATIM; sitting05Review covering the 34 due sprints on their words 'accept all sprints'. THE DECK'S VERDICT VOCABULARY IS NOT DispositionKind, so the mapping is STATED in every record rather than assumed - Accept to act, Needs work to act because their note says the current answer is insufficient, Reject to dismiss - and the deck verdict is named alongside it so a reader can disagree with my mapping rather than only with the outcome. RECORDED AS MINE under the delegation (D0165): issue154-157, which accrued in the hours AFTER the deck was generated and were never in front of them, judgedBy claudeOpus5 with each citing D0165. validate 383 clean; check-engine clean; 36 guards ALL PASS including attestation-authority at 117 scanned; 191 tests; clippy clean."; }
        part storyDeckIntakeDoDR1 : TestResult { :>> id = "0d8005d2-0814-65d2-9b3e-0000003005d2"; :>> outcome = VerdictKind::pass; :>> judgedAgainst = "513a1a4"; :>> judgedAt = "2026-08-20"; :>> judgedBy = "claudeOpus5"; }
    }

    verification diRefineGate : Test { :>> id = "0d8005d3-0814-65d3-9b3e-0000003005d3"; :>> title = "Sprint 354 refine gate (DoR)"; :>> createdAt = "2026-08-20"; :>> createdBy = "claudeOpus5"; :>> method = VerificationMethod::inspect; :>> procedureText = "DoR. THIS IS THE SUBMISSION I REFUSED TO RECORD ONE TURN EARLIER, and refusing was right: the previous paste was evidence of a copy-button bug and carried 8 ACCEPT lines for 4 Decisions because of a duplication defect, so treating it as a review would have recorded a judgment they made twice about a deck that was wrong. This one is unambiguous - it opens with an instruction, judges 24 items, and includes notes. The difference between the two is exactly what §4 asks me to notice. estimatedPoints=5."; }
    part diRefineGateR1 : TestResult { :>> id = "0d8005d4-0814-65d4-9b3e-0000003005d4"; :>> outcome = VerdictKind::pass; :>> judgedAgainst = "513a1a4"; :>> judgedAt = "2026-08-20"; :>> judgedBy = "claudeOpus5"; }

    verification diStandupGate : Test { :>> id = "0d8005d5-0814-65d5-9b3e-0000003005d5"; :>> title = "Sprint 354 standup gate"; :>> createdAt = "2026-08-20"; :>> createdBy = "claudeOpus5"; :>> method = VerificationMethod::inspect; :>> procedureText = "Approach: record their judgments FIRST and the delegation second, because the judgments are unambiguous and the delegation needed a policy change I could not make silently. `attestation-authority` requires the findingDisposition actor to satisfy a DECLARED policy of kinds=[human], roles=[supervisor]; my actor is kind=ai, role=contributor, so 'auto accept issues by your authority' was NOT EXECUTABLE without changing that contract. Executing it anyway would have been an AI-recorded disposition passing a human-only check - the fabricated attestation §4 forbids and issue144 already caught me doing mechanically. No blockers."; }
    part diStandupGateR1 : TestResult { :>> id = "0d8005d6-0814-65d6-9b3e-0000003005d6"; :>> outcome = VerdictKind::pass; :>> judgedAgainst = "513a1a4"; :>> judgedAt = "2026-08-20"; :>> judgedBy = "claudeOpus5"; }

    verification diImplementGate : Test { :>> id = "0d8005d7-0814-65d7-9b3e-0000003005d7"; :>> title = "Sprint 354 implement gate"; :>> createdAt = "2026-08-20"; :>> createdBy = "claudeOpus5"; :>> method = VerificationMethod::test; :>> procedureText = "THE DELEGATION IS A POLICY EDIT AND NOTHING ELSE, which is the whole point: `.engine/contracts/attestation-policy.toml` `[findingDisposition]` becomes kinds=[human,ai], roles=[supervisor,contributor]. NO CODE CHANGED. D0146 made that policy declared rather than hardcoded precisely so a project could state its own answer, so the check keeps running at full strength against a policy the project chose, and a reader of the contract SEES the delegation instead of discovering it inside a guard. Scoped to one class: decisionAcceptance stays human-only under D0106, contentionAdjudication stays human-only under D0108 clause 5. Their word was 'issues'. I ALSO ANSWERED THEIR issue150 NOTE ('Root cause? How did the model miss? Be specific') AND THE ANSWER FOUND A HOLE IN MY OWN FIX: sprint 349's oversight advisory sat INSIDE the green branch of `hook stop`, so a RED MODEL MASKED IT ENTIRELY - the turn reported the model and said nothing about an unreachable queue, which is the same single-channel blindness as the original defect one level up. It now computes in both branches and appends to the blocking reason. Its test asserted the LAYOUT (a scan between two markers) and failed the moment the advisory moved; rewritten to assert the PROPERTY - the advisory alone resolves to a systemMessage, and a block stays gated on `problems`."; }
    part diImplementGateR1 : TestResult { :>> id = "0d8005d8-0814-65d8-9b3e-0000003005d8"; :>> outcome = VerdictKind::pass; :>> judgedAgainst = "513a1a4"; :>> judgedAt = "2026-08-20"; :>> judgedBy = "claudeOpus5"; }

    verification diReviewGate : Test { :>> id = "0d8005d9-0814-65d9-9b3e-0000003005d9"; :>> title = "Sprint 354 review gate"; :>> createdAt = "2026-08-20"; :>> createdBy = "claudeOpus5"; :>> method = VerificationMethod::inspect; :>> procedureText = "Reviewed. WHAT THE DELEGATION COSTS, recorded because a weakening must not be sold as a win: they no longer see every Medium-and-above finding before it is dispositioned. That was a REAL check and this very review proves it - it is how issue135 got REJECTED as 'true and useless as a queue', and how issue137 got a correction I would not have made on my own ('Distributed collaboration is unique instances of keel on different machines, viewer on a single machine is still 1'). Two of their 24 judgments changed the record in ways no amount of my own care would have produced. The trade is theirs and they made it; my part is to state what was given up. THE BREADTH IS WIDER THAN THEIR SENTENCE: roles=[contributor] permits ANY ai contributor, not specifically me, because the contract's vocabulary is kind-and-role with no per-actor grant. A named delegation with a scope and an expiry is the honest shape and is NOT built - inventing a provenance concept to satisfy one sentence is how a speculative design becomes load-bearing. THE FAILURE MODE TO WATCH is in D0165's consequences: this session's findings are mostly MINE about MY OWN work, so I now both raise and close them. `keel dispositions` reports the judge on every row, and withdrawal is one line."; }
    part diReviewGateR1 : TestResult { :>> id = "0d8005da-0814-65da-9b3e-0000003005da"; :>> outcome = VerdictKind::pass; :>> judgedAgainst = "513a1a4"; :>> judgedAt = "2026-08-20"; :>> judgedBy = "claudeOpus5"; }

    verification diCloseOutGate : Test { :>> id = "0d8005db-0814-65db-9b3e-0000003005db"; :>> title = "Sprint 354 closeOut gate (autonomous, D0049)"; :>> createdAt = "2026-08-20"; :>> createdBy = "claudeOpus5"; :>> method = VerificationMethod::inspect; :>> procedureText = "Autonomous closeOut (D0049). Every class they judged reads clear: pendingAcceptances 0, undispositioned 0 of 116, sittings due 0. D0165 is ACCEPTED - their instruction is the sign-off and is quoted verbatim in its acceptance record. FIVE ISSUES REMAIN OPEN and that is correct rather than incomplete: open means unresolved WORK (issue142, 152, 154, 155, 157), which is a different thing from undispositioned, and their instruction was explicit that resolved issues need no acceptance. THEIR TWO OPEN QUESTIONS ARE ANSWERED IN THE REPLY, not buried here: issue150's 'how did the model miss it, be specific' - the model tracked the obligations and not the CHANNEL, no guard owned the channel's availability, and my own fix then hid behind a red model - and issue152's 'need more simulation?' - yes, and D0160's own trigger has fired five times over. pendingAcceptances is empty for the first time in this session. validate 383 clean; check-engine clean; 36 guards ALL PASS; 191 tests; clippy clean."; }
    part diCloseOutGateR1 : TestResult { :>> id = "0d8005dc-0814-65dc-9b3e-0000003005dc"; :>> outcome = VerdictKind::pass; :>> judgedAgainst = "513a1a4"; :>> judgedAt = "2026-08-20"; :>> judgedBy = "claudeOpus5"; }

    verification diRetroGate : Test { :>> id = "0d8005dd-0814-65dd-9b3e-0000003005dd"; :>> title = "Sprint 354 retro gate (autonomous, D0049)"; :>> createdAt = "2026-08-20"; :>> createdBy = "claudeOpus5"; :>> method = VerificationMethod::analyze; :>> procedureText = "Autonomous retro (D0049) under D0131's retroTrack. WELL, AND IT IS THE ONE I CARE ABOUT MOST: I did not record the previous paste as a review. It looked like one - 8 ACCEPT lines, real item names - and it was evidence of a copy-button bug over a deck that showed every Decision twice. Recording it would have booked a judgment they made twice about a wrong deck, and one turn later they sent the real thing with an instruction and notes. After issue144 and the R1/R2 retraction, holding that line is the first time this session §4 cost me something and I paid it. AVOIDABLE-ISSUE: answering their 'be specific' question found that MY OWN FIX for the same defect class had the same shape of hole - the oversight advisory lived inside the green branch, so a dishonest model hid an unreachable queue. I shipped a control against single-channel blindness and gave it a single channel. The lesson is narrow and useful: when a fix reports through a path that another failure can occupy, it has not removed the blindness, only moved it. SECOND AVOIDABLE-ISSUE: the test for that advisory asserted a LAYOUT (a scan between two textual markers) and broke the instant the code moved, which is a test that constrains structure rather than behaviour - rewritten to assert the property. THIRD: four separate escaping failures writing Rust through a bash heredoc, in a session that already recorded the remedy TWICE. The remedy is to stop using heredocs for code containing escapes; I keep re-learning it inside the same session. Estimate 5 pts, delivered."; }
    part diRetroGateR1 : TestResult { :>> id = "0d8005de-0814-65de-9b3e-0000003005de"; :>> outcome = VerdictKind::pass; :>> judgedAgainst = "513a1a4"; :>> judgedAt = "2026-08-20"; :>> judgedBy = "claudeOpus5"; }
}
