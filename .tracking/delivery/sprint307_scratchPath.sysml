// ProjectDeliveryS307 — Sprint 307: close the heredoc-body gap in the shell-adaptation advisory.
// EXECUTE. 3 pts.
package ProjectDeliveryS307 {
    private import EngineElement::*;
    private import EngineWork::*;
    private import EngineVerification::*;
    private import EngineRelationships::*;

    #CharteredBy dependency from scratchPathStory to issue126;

    part scratchPathStory : Story {
        :>> id = "0d8002e0-0814-62e0-9b3e-0000003002e0";
        :>> title = "Sprint 307: detect an MSYS path inside a heredoc body, not just as an argument (3 pts)";
        :>> createdAt = "2026-08-15"; :>> createdBy = "claudeOpus5"; :>> kind = WorkKind::code; :>> priority = WorkPriority::p1; :>> owner = "claudeOpus5"; :>> estimatedPoints = 3;
    }

    action def DeliveryRunS307 {
        action storyScratchPath;
        verification storyScratchPathDoD : Test { :>> id = "0d8002e1-0814-62e1-9b3e-0000003002e1"; :>> method = VerificationMethod::test; :>> procedureText = "Delivers dcScratchPathControl, resolving issue126. THE INVESTIGATION CHANGED THE FIX, and that is the finding: the item assumed the pre-bash hook did not cover this class at all. It already did — `keel.exe ... > /tmp/cc.json; python ...` IS flagged today, because keel.exe is Windows-native and /tmp/cc.json is a bare MSYS argument. Verified by test before writing anything. The ACTUAL gap is narrower and is exactly what bit me twice: an MSYS path that appears ONLY INSIDE A HEREDOC BODY, as `io.open('/tmp/cc.json')`, is never a bare argument, so the whole-word check never saw it. DELIVERED: `embedded_msys_path` finds an MSYS path inside a larger token, scoped to the SEGMENT whose program is Windows-native — a heredoc body carries no shell operators, so it stays attached to the segment that consumes it, and segment scoping is what stops this firing on an unrelated bash-only /tmp use elsewhere in the same command. Deliberately only `/tmp/` and `/mnt/`, never the single-letter drive form: a `/c/` substring match would fire on any URL path and on ordinary prose, and this hook is worthless the moment it becomes noise the reader skips. Remains ADVISORY and returns 0 always (issue094 — a blocking heuristic over shell commands is the issue076/issue081 dynamic that trains its actor to disable the gate). VERIFIED: the heredoc shape is now advised on; the redirect shape still is; a pure-bash /tmp use with no Windows program stays SILENT. clippy clean; 216 tests; validate 332 clean; 33 guards green."; }
        part storyScratchPathDoDR1 : TestResult { :>> id = "0d8002e2-0814-62e2-9b3e-0000003002e2"; :>> outcome = VerdictKind::pass; :>> judgedAgainst = "c918626"; :>> judgedAt = "2026-08-15"; :>> judgedBy = "claudeOpus5"; }
    }

    verification spRefineGate : Test { :>> id = "0d8002e3-0814-62e3-9b3e-0000003002e3"; :>> title = "Sprint 307 refine gate (DoR)"; :>> createdAt = "2026-08-15"; :>> createdBy = "claudeOpus5"; :>> method = VerificationMethod::inspect; :>> procedureText = "DoR. issue126 records a defect that recurred three times in one session after its remedy was already written into a sprint 301 retro — the D0047 case where a reminder is not a control. CONSUMER CHECK (dorConsumer, D0144): the consumer is the next Bash call, so the advisory has to fire BEFORE the command runs and has to name the remedy, not just the smell. estimatedPoints=3."; }
    part spRefineGateR1 : TestResult { :>> id = "0d8002e4-0814-62e4-9b3e-0000003002e4"; :>> outcome = VerdictKind::pass; :>> judgedAgainst = "c918626"; :>> judgedAt = "2026-08-15"; :>> judgedBy = "claudeOpus5"; }

    verification spStandupGate : Test { :>> id = "0d8002e5-0814-62e5-9b3e-0000003002e5"; :>> title = "Sprint 307 standup gate"; :>> createdAt = "2026-08-15"; :>> createdBy = "claudeOpus5"; :>> method = VerificationMethod::inspect; :>> procedureText = "Approach: reproduce the failing shapes as TESTS against the existing `inspect` before changing it, so the fix is aimed at the real gap rather than the assumed one. No blockers."; }
    part spStandupGateR1 : TestResult { :>> id = "0d8002e6-0814-62e6-9b3e-0000003002e6"; :>> outcome = VerdictKind::pass; :>> judgedAgainst = "c918626"; :>> judgedAt = "2026-08-15"; :>> judgedBy = "claudeOpus5"; }

    verification spImplementGate : Test { :>> id = "0d8002e7-0814-62e7-9b3e-0000003002e7"; :>> title = "Sprint 307 implement gate"; :>> createdAt = "2026-08-15"; :>> createdBy = "claudeOpus5"; :>> method = VerificationMethod::test; :>> procedureText = "WRITING THE TESTS FIRST SAVED BUILDING THE WRONG THING. Two of the three shapes I was about to 'fix' already passed, which means the existing control covered my FIRST failure and the item's premise — that this class was unhandled — was wrong. Only the heredoc-body shape failed. Had I built to the item's description I would have added a broad any-MSYS-path-anywhere check, which would fire on every command mixing a bash /tmp use with an unrelated python call, and a noisy advisory is one the reader learns to skip. A SEPARATE COST WORTH RECORDING: probing the hook by calling `keel hook pre-bash` with the command as an ARGUMENT hung for the full ten-minute timeout, because the hook reads its JSON payload from STDIN and blocked waiting for input that never came. Ten minutes lost to a command that could not have worked. The tell generalises: before probing a hook from the shell, read how it takes input — and prefer testing the function directly, which is faster, does not hang, and leaves a regression test behind."; }
    part spImplementGateR1 : TestResult { :>> id = "0d8002e8-0814-62e8-9b3e-0000003002e8"; :>> outcome = VerdictKind::pass; :>> judgedAgainst = "c918626"; :>> judgedAt = "2026-08-15"; :>> judgedBy = "claudeOpus5"; }

    verification spReviewGate : Test { :>> id = "0d8002e9-0814-62e9-9b3e-0000003002e9"; :>> title = "Sprint 307 review gate"; :>> createdAt = "2026-08-15"; :>> createdBy = "claudeOpus5"; :>> method = VerificationMethod::inspect; :>> procedureText = "Reviewed. The silence test is the one that matters and it is asserted: a pure-bash `echo hi > /tmp/x && cat /tmp/x` produces NO advisory, because no Windows program is involved and bash reads its own /tmp perfectly well. Without that test the natural fix — flag /tmp anywhere — would have been indistinguishable from this one at review time and much worse in use. The embedded check stays narrower than the whole-word check on purpose, and the reason is written at the function rather than left to be rediscovered."; }
    part spReviewGateR1 : TestResult { :>> id = "0d8002ea-0814-62ea-9b3e-0000003002ea"; :>> outcome = VerdictKind::pass; :>> judgedAgainst = "c918626"; :>> judgedAt = "2026-08-15"; :>> judgedBy = "claudeOpus5"; }

    verification spCloseOutGate : Test { :>> id = "0d8002eb-0814-62eb-9b3e-0000003002eb"; :>> title = "Sprint 307 closeOut gate (autonomous, D0049)"; :>> createdAt = "2026-08-15"; :>> createdBy = "claudeOpus5"; :>> method = VerificationMethod::inspect; :>> procedureText = "Autonomous closeOut (D0049). issue126 resolves through dcScratchPathControl. clippy clean; 216 tests; validate 332 clean; check-engine clean; 33 guards green. The hook stays advisory and non-blocking, so nothing about this change can stop honest work."; }
    part spCloseOutGateR1 : TestResult { :>> id = "0d8002ec-0814-62ec-9b3e-0000003002ec"; :>> outcome = VerdictKind::pass; :>> judgedAgainst = "c918626"; :>> judgedAt = "2026-08-15"; :>> judgedBy = "claudeOpus5"; }

    verification spRetroGate : Test { :>> id = "0d8002ed-0814-62ed-9b3e-0000003002ed"; :>> title = "Sprint 307 retro gate (autonomous, D0049)"; :>> createdAt = "2026-08-15"; :>> createdBy = "claudeOpus5"; :>> method = VerificationMethod::analyze; :>> procedureText = "Autonomous retro (D0049) under D0131's retroTrack. WELL: (1) testing the existing behaviour BEFORE building disproved the item's own premise and shrank the change from a broad heuristic to a narrow one — the item said the class was unhandled, and two thirds of it already was; (2) the silence assertion for pure-bash /tmp use is what keeps the advisory from becoming noise, and it was written as a test rather than a promise. AVOIDABLE-ISSUE: I probed the hook by passing the command as a shell ARGUMENT when it reads a JSON payload from STDIN, and it hung for the full ten-minute timeout. NO NEW ITEM, reason stated: the remedy is already recorded in this repo's own guidance about not piping commands whose input a process holds, and the specific lesson — read how a hook takes input before invoking it, and prefer calling the function under test — is captured in the implement gate above. Adding a third item about shell-invocation care would be process theatre; the concrete control that WOULD have helped is the one this sprint just shipped. OBSERVED: dcCritiqueCoverageSupersede and dcArchRegistryPortability remain on the frontier; the first needs section 3a sign-off because it changes what a computed view counts, the second is blocked on a second project's registry that this repo does not hold. Estimate 3 pts, delivered."; }
    part spRetroGateR1 : TestResult { :>> id = "0d8002ee-0814-62ee-9b3e-0000003002ee"; :>> outcome = VerdictKind::pass; :>> judgedAgainst = "c918626"; :>> judgedAt = "2026-08-15"; :>> judgedBy = "claudeOpus5"; }
}
