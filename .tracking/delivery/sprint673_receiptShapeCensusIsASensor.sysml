// ProjectDeliveryS673 — Sprint 673: The receipt-shape rule as a sensor. D0444 measured the rule over the tree's 283 prefixed RAN receipts before any code was written: prefix admits 283, alphabet alone admits 1 false positive, alphabet plus function words admits 0. The rule is now codified in a committed sensor so that loosening it re-measures the shape first. The census script is charged to D0444 as its own deliverable (not to this sprint) but tracked here for resolution.. EXECUTE. 1 pts.
package ProjectDeliveryS673 {
    private import EngineElement::*;
    private import EngineWork::*;
    private import EngineVerification::*;
    private import EngineRelationships::*;

    #CharteredBy dependency from receiptShapeCensusIsASensorStory to d0444;

    part receiptShapeCensusIsASensorStory : Story {
        :>> id = "204490a1-150c-474c-8e4c-52dab20fa78d";
        :>> title = "Sprint 673: The receipt-shape rule as a sensor. D0444 measured the rule over the tree's 283 prefixed RAN receipts before any code was written: prefix admits 283, alphabet alone admits 1 false positive, alphabet plus function words admits 0. The rule is now codified in a committed sensor so that loosening it re-measures the shape first. The census script is charged to D0444 as its own deliverable (not to this sprint) but tracked here for resolution. (1 pts)";
        :>> createdAt = "2026-09-11"; :>> createdBy = "claudeOpus5"; :>> kind = WorkKind::code; :>> priority = WorkPriority::p0; :>> owner = "claudeOpus5"; :>> estimatedPoints = 1;
    }

    action def DeliveryRunS673 {
        action storyReceiptShapeCensusIsASensor;
        verification storyReceiptShapeCensusIsASensorDoD : Test { :>> id = "41159b5f-4380-4d10-a86c-4fd513188aea"; :>> method = VerificationMethod::test; :>> procedureText = "scripts/probes/receipt_shape_census.py: NEW, the census as a committed sensor. Reads [demo] replayable prefixes from .engine/contracts/reverify.toml and PROSE_WORDS from keel-cli/src/reverify.rs by regex (names the pairs so neither list is copied and neither drifts), applies the three layered rules (trimmed one line, declared prefix, token alphabet, no function word) exactly as reverify.rs does (is_replayable_with), includes D0388 probe pair (known-positive keel show control-structure . --svg and keel version admitted; known-negative keel suite 571 passed, 0 failed and looked at the picture rejected). Outputs plain text by default, --json for one object, --probe runs only the known cases. LF check: 0 CRLF. keel-cli/src/reverify.rs: doc comment on PROSE_WORDS (2 lines added) names the census script and that it reads the list verbatim; no code change. .engine/contracts/reverify.toml: NOT EDITED (locked per process-change guard; a comment there gates as process-change and is not worth a Decision). Tests: the probe pair is run BEFORE the tree is read (D0388), every run; live census over the tree's 907 RAN receipts with 283 prefixed, 1 alphabet false positive, 0 under full rule; demoReplayable count from keel attestation . --json is 0, equals census full-rule count."; }
        // RAN: verifier receipt batch1: receipt_shape_census.py --probe exit 0; census 283 prefixed / alphabet 1 / full rule 0 = attestation demoReplayable 0
        part storyReceiptShapeCensusIsASensorDoDR1 : TestResult { :>> id = "3f153f96-b2f9-4c88-ac69-f9d6d43f8105"; :>> outcome = VerdictKind::pass; :>> judgedAgainst = "b8fab64"; :>> judgedAt = "2026-09-11"; :>> judgedBy = "claudeOpus5"; }
    }

    verification receiptShapeCensusIsASensorRefineGate : Test { :>> id = "109bf74c-16c9-4274-b207-e18b81b0c98c"; :>> title = "Sprint 673 refine gate (DoR)"; :>> createdAt = "2026-09-11"; :>> createdBy = "claudeOpus5"; :>> method = VerificationMethod::inspect; :>> procedureText = "Chartered by D0444 (Decision, recorded proposed/HELD per D0337 for the process-change). No depends beyond D0444 itself. 1 point: one new script with probe pair, two doc-comment lines. Receipt-shape rule was measured before written (D0444 text cited 283/1/0 against a scratchpad census); this sprint makes that measurement a committed sensor. The rule's three layers are exact to reverify.rs is_replayable_with: prefix from .engine/contracts/reverify.toml (declared before measurement), token alphabet (ASCII letters/digits/underscore/slash/colon/equals/at/hyphen), no token a function word from reverify.rs (16 words, read by regex so PROSE_WORDS and the script cannot drift)."; }
    // RAN: verifier receipt batch1: chartered by d0444; 1 point; validate 766 clean exit 0
    part receiptShapeCensusIsASensorRefineGateR1 : TestResult { :>> id = "961f2b6e-c91b-4ca4-b35b-c095c4af2948"; :>> outcome = VerdictKind::proposed; :>> judgedAgainst = "b8fab64"; :>> judgedAt = "2026-09-11"; :>> judgedBy = "claudeOpus5"; }
    verification receiptShapeCensusIsASensorStandupGate : Test { :>> id = "e2424331-47fb-4d03-bc0e-48cc1a94c51e"; :>> title = "Sprint 673 standup gate"; :>> createdAt = "2026-09-11"; :>> createdBy = "claudeOpus5"; :>> method = VerificationMethod::inspect; :>> procedureText = "Order: receipt_shape_census.py (--probe known cases before read, live census on .tracking receipts, --json for the six counts), reverify.rs doc comment, attestation.rs demoReplayable from JSON, D0444 text amended with the measured rule, CI discovery simulated (D0394/D0397: scripts/probes/receipt_shape_census.py --probe found alongside artefact.py and check_templates.py; exit 0). Blocker met and avoided: .engine/contracts/reverify.toml is locked; the pointer to the census lives in reverify.rs doc comment and the script's docstring instead."; }
    // RAN: verifier receipt batch1: receipt_shape_census.py --probe exit 0; CI discovery found alongside check_templates.py; reverify.rs doc comment added
    part receiptShapeCensusIsASensorStandupGateR1 : TestResult { :>> id = "76d92e84-ff9f-4aa5-954f-03f760d51bf5"; :>> outcome = VerdictKind::proposed; :>> judgedAgainst = "b8fab64"; :>> judgedAt = "2026-09-11"; :>> judgedBy = "claudeOpus5"; }
    verification receiptShapeCensusIsASensorImplementGate : Test { :>> id = "f4fc3e9e-f5dd-4a60-b019-9e5575732bc3"; :>> title = "Sprint 673 implement gate"; :>> createdAt = "2026-09-11"; :>> createdBy = "claudeOpus5"; :>> method = VerificationMethod::test; :>> procedureText = "scripts/probes/receipt_shape_census.py: reads .tracking/ for RAN receipt lines (// RAN: prefix, ci-run id= shortcut, demo_replays form, 25 doubled receipts, 7 string mentions), executes the three rule layers (prefix, alphabet, alphabet+function-words), counts admits at each layer, counts demo latest-pass under full rule (mirroring attestation.rs demo_replays_in_text, latest result per Test), prints narrative (plain text or --json). keel-cli/src/reverify.rs: doc comment on PROSE_WORDS names the script and that it reads the list. D0444 Decision text: amended with 283 / 1 / 0 as the measured rule. .engine/contracts/reverify.toml: no edit (locked). No Sensor item authored (other probes do not carry Sensor items and instruments-declared does not scan scripts/probes/)."; }
    // RAN: verifier receipt batch1: receipt_shape_census.py --probe positive pass exit 0; negative pass exit 0; census 283 prefixed / alphabet 1 / full rule 0
    part receiptShapeCensusIsASensorImplementGateR1 : TestResult { :>> id = "8e037cd8-e2b7-44cd-b483-1ee0a3cc8a8b"; :>> outcome = VerdictKind::pass; :>> judgedAgainst = "b8fab64"; :>> judgedAt = "2026-09-11"; :>> judgedBy = "claudeOpus5"; }
    verification receiptShapeCensusIsASensorReviewGate : Test { :>> id = "c20b3cf5-73cf-4216-8e16-2447def6b8f0"; :>> title = "Sprint 673 review gate — three passes per D0172"; :>> createdAt = "2026-09-11"; :>> createdBy = "claudeOpus5"; :>> method = VerificationMethod::inspect; :>> procedureText = "Delivered: the receipt-shape rule is now a committed measurement, so the next change to the alphabet or function-word list re-runs the census (--probe pair validates the rule, live tree shows the admit counts, demoReplayable from attestation gives the count that matters) before any code changes it. Today's count: prefix 283, alphabet 1, full rule 0. Residual: 25 receipts in the 283-prefixed set carry the doubled marker (// RAN: // RAN: ...) from earlier appends, and split('// RAN:').nth(1) in the Rust yields a narrative that begins // RAN: and is not prefixed - a non-issue for this rule because those receipts are prefixed at the start, counted in the 283, and the doubled marker is only in the appended narrative. A guardless anomaly (an earlier guard run named reverify.toml as touched when this run did not; not reproduced on later runs) was noted but not explained."; }
    // RAN: verifier receipt batch1: keel attestation . --json demoReplayable 0 equals census full-rule 0 exit 0; guard exit 0
    part receiptShapeCensusIsASensorReviewGateR1 : TestResult { :>> id = "1a0a61bb-1302-4953-b6d3-a1933e1552d5"; :>> outcome = VerdictKind::proposed; :>> judgedAgainst = "b8fab64"; :>> judgedAt = "2026-09-11"; :>> judgedBy = "claudeOpus5"; }
    verification receiptShapeCensusIsASensorCloseOutGate : Test { :>> id = "78f5dca0-c910-4349-8c66-7725a4192d06"; :>> title = "Sprint 673 closeOut gate (autonomous, D0049)"; :>> createdAt = "2026-09-11"; :>> createdBy = "claudeOpus5"; :>> method = VerificationMethod::inspect; :>> procedureText = "Sprint 673 closes on the verifier's receipt only (D0425). dcReceiptShapeCensusIsASensor gets its DoD result. D0444 stays proposed/HELD for the human (D0337). Nothing new added to backlog (the anomaly is an observation, not an Issue - existing tracking: issue484 and d0444). Nothing else in the frontier moved."; }
    // RAN: verifier receipt batch1: DISCREPANCIES NONE; OWED WRITES NONE; dcReceiptShapeCensusIsASensor DoD result recorded; no new item beyond issue484 and d0444
    part receiptShapeCensusIsASensorCloseOutGateR1 : TestResult { :>> id = "0f9e504d-ae9e-4c2c-a445-48c4dbdffc42"; :>> outcome = VerdictKind::proposed; :>> judgedAgainst = "b8fab64"; :>> judgedAt = "2026-09-11"; :>> judgedBy = "claudeOpus5"; }
    verification receiptShapeCensusIsASensorRetroGate : Test { :>> id = "b0a417f8-2a54-4451-a726-28ee5560f695"; :>> title = "Sprint 673 retro gate (autonomous, D0049)"; :>> createdAt = "2026-09-11"; :>> createdBy = "claudeOpus5"; :>> method = VerificationMethod::analyze; :>> procedureText = "AVOIDABLE-ISSUE SCAN: No new item - already tracked: issue484 and d0444. One observation: a guard run in the worktree once named reverify.toml as a file it would change, though a later run did not; the symptom (a process-change guard fire) did not reproduce and no cause is known."; }
    // RAN: verifier receipt batch1: no new Issue; guard run anomaly noted (reverify.toml named then not reproduced)
    part receiptShapeCensusIsASensorRetroGateR1 : TestResult { :>> id = "be6efe12-b443-4ce8-98e4-851ec4ba1987"; :>> outcome = VerdictKind::proposed; :>> judgedAgainst = "b8fab64"; :>> judgedAt = "2026-09-11"; :>> judgedBy = "claudeOpus5"; }
}
