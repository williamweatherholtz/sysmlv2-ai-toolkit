// ProjectDeliveryS366 — Sprint 366: hardening round 6. The lens built to stop wrong numbers reported
// 100% when it could read nothing. A lens must not be able to pass vacuously. EXECUTE. 3 pts.
package ProjectDeliveryS366 {
    private import EngineElement::*;
    private import EngineWork::*;
    private import EngineVerification::*;
    private import EngineRelationships::*;

    #CharteredBy dependency from noFalseGreenStory to d0169;

    part noFalseGreenStory : Story {
        :>> id = "0d800690-0814-6690-9b3e-000000300690";
        :>> title = "Sprint 366: a lens that cannot read its input says so, rather than reporting 100% (3 pts)";
        :>> createdAt = "2026-08-20"; :>> createdBy = "claudeOpus5"; :>> kind = WorkKind::code; :>> priority = WorkPriority::p0; :>> owner = "claudeOpus5"; :>> estimatedPoints = 3;
    }

    action def DeliveryRunS366 {
        action storyNoFalseGreen;
        verification storyNoFalseGreenDoD : Test { :>> id = "0d800691-0814-6691-9b3e-000000300691"; :>> method = VerificationMethod::test; :>> procedureText = "DELIVERED BACKLOG ITEMS: dcLensCannotFalseGreen. Clears issue183 under D0169. `keel hardening` reported `helpCoverage 0/0 dispatched -> 100%` and `apiSurface unaccounted 0` against a tree containing only .engine and .tracking. THAT TREE IS EVERY DOWNSTREAM PROJECT - they install the binary and run it against their own model - so the lens built one sprint earlier to stop wrong numbers handed a clean bill of health to every consumer it could not measure, silently. THE MECHANISM WAS A HELPER I WROTE IN THE SAME SPRINT: `pct(part, whole)` returned 100 when whole was 0, a reasonable-looking divide-by-zero guard that converts `nothing measured` into `everything passed`; `unwrap_or_default()` on the file read turned an unreadable source into an empty one. FIXED: `pct` returns Option and refuses an empty population; both source lenses return `available: false` with a reason and emit NO percentage. VERIFIED BOTH WAYS - source-less tree reports unavailable, this tree still reports 100% help coverage and 0 unaccounted routes. validate 398 clean; check-engine clean; 38 guards ALL PASS; 199 tests; clippy clean."; }
        part storyNoFalseGreenDoDR1 : TestResult { :>> id = "0d800692-0814-6692-9b3e-000000300692"; :>> outcome = VerdictKind::pass; :>> judgedAgainst = "abde7ef"; :>> judgedAt = "2026-08-20"; :>> judgedBy = "claudeOpus5"; }
    }

    verification nfRefineGate : Test { :>> id = "0d800693-0814-6693-9b3e-000000300693"; :>> title = "Sprint 366 refine gate (DoR)"; :>> createdAt = "2026-08-20"; :>> createdBy = "claudeOpus5"; :>> method = VerificationMethod::inspect; :>> procedureText = "DoR. Pass 6 pointed at the code written in passes 1-5, which is the only target left that had never been audited. THREE PROBES CAME BACK CLEAN and are recorded as such: the write API refuses without a bound actor (a copy with no actor binding refused every write, correctly); recording the same issue twice creates two issues, which is CORRECT for an append-only fact log where identity is a UUID and title may duplicate (invariant 3); and a guard failure in the probe copy was my own doing, since I copied only .engine and .tracking so the manifest guard correctly reported missing source files. THE ONE REAL FINDING WAS IN MY OWN NEW CODE. estimatedPoints=3."; }
    part nfRefineGateR1 : TestResult { :>> id = "0d800694-0814-6694-9b3e-000000300694"; :>> outcome = VerdictKind::pass; :>> judgedAgainst = "abde7ef"; :>> judgedAt = "2026-08-20"; :>> judgedBy = "claudeOpus5"; }

    verification nfStandupGate : Test { :>> id = "0d800695-0814-6695-9b3e-000000300695"; :>> title = "Sprint 366 standup gate"; :>> createdAt = "2026-08-20"; :>> createdBy = "claudeOpus5"; :>> method = VerificationMethod::inspect; :>> procedureText = "Approach: probes that can WRITE run against a COPY, which is the rule sprint 365's retro set after a smoke test stamped two Measurements into the live model and sprint 363's `--help` sweep created a directory in it. Two passes in a row my probes mutated the repository they were auditing; this pass they did not. The copy is also what exposed the finding, because a tree without `keel-cli/src` is exactly the shape that triggers the false green. No blockers."; }
    part nfStandupGateR1 : TestResult { :>> id = "0d800696-0814-6696-9b3e-000000300696"; :>> outcome = VerdictKind::pass; :>> judgedAgainst = "abde7ef"; :>> judgedAt = "2026-08-20"; :>> judgedBy = "claudeOpus5"; }

    verification nfImplementGate : Test { :>> id = "0d800697-0814-6697-9b3e-000000300697"; :>> title = "Sprint 366 implement gate"; :>> createdAt = "2026-08-20"; :>> createdBy = "claudeOpus5"; :>> method = VerificationMethod::test; :>> procedureText = "THE FINDING IS AGAINST CODE I SHIPPED ONE HOUR EARLIER AS THE FIX FOR WRONG NUMBERS, and that irony is the substance rather than the decoration. Sprint 361 replaced hand probes with lenses because four probes had produced wrong numbers. Sprint 366 found that one of those lenses produces the WORST kind of wrong number - a green one - in the single most common deployment shape. THE PROGRESSION IS WORTH KEEPING: a hand probe fails credibly, a mis-aimed lens fails absurdly (0 of 75, 1 of 75 - both caught immediately), and a lens with an empty input fails INVISIBLY. I had ranked the first two and never considered the third. D0169 ALREADY DOCUMENTED THE LIMITATION - its consequences say plainly that hardening reads the repo's main.rs and audits a source tree rather than an installed binary. I wrote that sentence and then shipped the false green anyway, which is the sharpest available demonstration that documenting a limitation is not enforcing it. `pct` now returns Option; an unmeasurable value renders as the string `unavailable: <why>` rather than as a number, so a consumer parsing JSON cannot silently read it as zero either."; }
    part nfImplementGateR1 : TestResult { :>> id = "0d800698-0814-6698-9b3e-000000300698"; :>> outcome = VerdictKind::pass; :>> judgedAgainst = "abde7ef"; :>> judgedAt = "2026-08-20"; :>> judgedBy = "claudeOpus5"; }

    verification nfReviewGate : Test { :>> id = "0d800699-0814-6699-9b3e-000000300699"; :>> title = "Sprint 366 review gate"; :>> createdAt = "2026-08-20"; :>> createdBy = "claudeOpus5"; :>> method = VerificationMethod::inspect; :>> procedureText = "Reviewed. WHAT I WOULD DEFEND: `pct` returning `Option` rather than 0. Returning 0 for an empty population would have been the smaller change and it swaps a false PASS for a false FAIL - still a fabricated answer, just one that annoys instead of reassures. `unavailable: <reason>` is the only honest third state, and it is deliberately a STRING so a JSON consumer cannot coerce it to a number. WHAT A REVIEWER SHOULD ATTACK: `processEnforcement` still reports 83% on the source-less tree, because it reads `.engine/processes`, which downstream projects DO carry. That is correct today and it is inconsistent shaped - two lenses now carry `available` and one does not, so a reader has to know which lenses read source and which read the model. I left it rather than adding a field that is always true. THE HONEST SCORE OF THIS SERIES SO FAR: of 13 findings across six passes, three were in code written during the series itself. The passes are finding real defects, and a growing share of them are mine."; }
    part nfReviewGateR1 : TestResult { :>> id = "0d80069a-0814-669a-9b3e-00000030069a"; :>> outcome = VerdictKind::pass; :>> judgedAgainst = "abde7ef"; :>> judgedAt = "2026-08-20"; :>> judgedBy = "claudeOpus5"; }

    verification nfCloseOutGate : Test { :>> id = "0d80069b-0814-669b-9b3e-00000030069b"; :>> title = "Sprint 366 closeOut gate (autonomous, D0049)"; :>> createdAt = "2026-08-20"; :>> createdBy = "claudeOpus5"; :>> method = VerificationMethod::inspect; :>> procedureText = "Autonomous closeOut (D0049). issue183 cleared. Six passes: 13 findings recorded, 13 cleared, 9 permanent controls of which `keel hardening` now carries nine tests. Three of the 13 findings were in code written during this series. validate 398 clean; check-engine clean; 38 guards ALL PASS; 199 tests; clippy clean."; }
    part nfCloseOutGateR1 : TestResult { :>> id = "0d80069c-0814-669c-9b3e-00000030069c"; :>> outcome = VerdictKind::pass; :>> judgedAgainst = "abde7ef"; :>> judgedAt = "2026-08-20"; :>> judgedBy = "claudeOpus5"; }

    verification nfRetroGate : Test { :>> id = "0d80069d-0814-669d-9b3e-00000030069d"; :>> title = "Sprint 366 retro gate (autonomous, D0049)"; :>> createdAt = "2026-08-20"; :>> createdBy = "claudeOpus5"; :>> method = VerificationMethod::analyze; :>> procedureText = "Autonomous retro (D0049) under D0131's retroTrack. WELL: (1) the probes ran against a COPY, honouring the rule the previous retro set, and the copy is what surfaced the finding; (2) the pass attacked code written during the series rather than only pre-existing surface, which is where its one real finding was; (3) three clean results were recorded rather than dropped, so a successor knows the write API refuses an unbound actor and that duplicate titles are correct; (4) `pct` returns Option rather than 0, refusing to swap a false pass for a false fail; (5) the unmeasurable value is a STRING, so a JSON consumer cannot coerce it to zero. AVOIDABLE-ISSUE, AND IT IS THE ONE THAT MATTERS: I documented this exact limitation in D0169's consequences and then shipped the false green in the same sprint. Writing `this lens reads a source tree, not an installed binary` and NOT asking `so what does it say when there is no source tree` is a failure of the second question, not the first. THE RULE: a stated limitation is a test waiting to be written, and the test is what the statement was for. SECOND AVOIDABLE-ISSUE: `pct` returning 100 for an empty population was a divide-by-zero guard I wrote without asking what the value would MEAN - the arithmetic was safe and the semantics were a lie. Estimate 3 pts, delivered."; }
    part nfRetroGateR1 : TestResult { :>> id = "0d80069e-0814-669e-9b3e-00000030069e"; :>> outcome = VerdictKind::pass; :>> judgedAgainst = "abde7ef"; :>> judgedAt = "2026-08-20"; :>> judgedBy = "claudeOpus5"; }
}
