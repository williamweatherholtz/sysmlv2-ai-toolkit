// ProjectDeliveryS247 — Sprint 247: distributed-collaboration SE chain + the five day-one blockers
// (D0129). Prepares keel for an async remote mostly-AI team. The research pass found the doctrine
// already right and the MECHANIZATION absent, so this is D0047 applied to D0108 — not a redesign.
// EXECUTE. 8 pts.
package ProjectDeliveryS247 {
    private import EngineElement::*;
    private import EngineWork::*;
    private import EngineVerification::*;
    private import EngineRelationships::*;

    #CharteredBy dependency from distributedCollabDayOneStory to d0129;

    part distributedCollabDayOneStory : Story {
        :>> id = "0d620001-0812-4201-9b3e-000000120001";
        :>> title = "Sprint 247: distributed-collaboration SE chain + five day-one blockers (8 pts) — merge-only integration, duplicate-identity guard, CSPRNG ids, true provenance, portable gate";
        :>> createdAt = "2026-08-12"; :>> createdBy = "claudeOpus5"; :>> kind = WorkKind::code; :>> priority = WorkPriority::p0; :>> owner = "claudeOpus5"; :>> estimatedPoints = 8;
    }

    action def DeliveryRunS247 {
        action storyDistributedCollabDayOne;
        verification storyDistributedCollabDayOneDoD : Test { :>> id = "0d620002-0812-4202-9b3e-000000120002"; :>> method = VerificationMethod::demo; :>> procedureText = "Delivers D0129's day-one set plus its governing model. MODEL: 3 Personas / 10 Needs / 13 UseCases in the DECLARED Business succession (personas->needs->useCases, business.sysml:15-21) + 20 SystemRequirements with satisfy edges + D0129 (proposed, #ProspectiveChange, supersedes d0014 on acceptance) + 2 processes with 2 deploying skills (D0059) + 11 Issues (071-081), each carrying file:line evidence. CODE/CONFIG (each closes a verified defect): issue071 ancestry-preserving integration (squash+rebase-merge DISABLED on the remote, main blocks force-push/deletion with enforce_admins, required_linear_history deliberately FALSE since linear history would mandate the rebase we forbid; post-commit integrates a rejected push by MERGE and retries with a recursion guard; pre-merge-commit added so merge commits are gated at last); issue074 new hard guard duplicate-identity (18 guards, 16 hard) over id/item-name/package-name/sequence-number, FORWARD-ONLY (18 pre-existing bootstrap duplicate ids across 26 sites grandfathered to warning, tracked issue080); issue075 gen_uuid -> OS CSPRNG UUIDv4; issue072+073 provenance never defaulted (13 write paths lost their default actor, 7 of which named a HUMAN; new `keel actor show|set` + KEEL_ACTOR + explicit flag, else REFUSE; .keel/ gitignored); issue076 portable gate (no hardcoded conda/binary paths, kernel layer optional, unrunnable check FAILS LOUDLY, *.sysml eol pinned in .gitattributes). VERIFY: clippy -D warnings clean; 146 tests pass incl. new duplicate-scan/grandfather/uuid/actor tests; keel validate + guard (all 18) + check-engine green; `keel actor` refuses an unregistered id and binds a registered one; append-result attributed to claudeOpus5 from the machine binding with NO default; committed b518c23 and CI GREEN (first green in several commits — the included two-pass fix repaired the order-dependent failure at parse_engine_files.rs:99, filed as issue079)."; }
        part storyDistributedCollabDayOneDoDR1 : TestResult { :>> id = "0d620003-0812-4203-9b3e-000000120003"; :>> outcome = VerdictKind::pass; :>> judgedAgainst = "b518c23"; :>> judgedAt = "2026-08-12"; :>> judgedBy = "claudeOpus5"; }
    }

    verification dcRefineGate : Test { :>> id = "0d620004-0812-4204-9b3e-000000120004"; :>> title = "Sprint 247 refine gate (DoR)"; :>> createdAt = "2026-08-12"; :>> createdBy = "claudeOpus5"; :>> method = VerificationMethod::inspect; :>> procedureText = "DoR: the human directed operating keel as an async remote mostly-AI team within ~a week, asked for research into required features, for the SE chain (use cases/needs/reqs) and for a base collaboration process, then chose TWO-LANE integration and the scope 'SE chain + day-one blockers' via an explicit question. Scope fixed: SE chain + D0129 + 2 processes/skills + 5 mechanical blockers; DEFERRED with reasons — declared-marker vocabulary (frozen schema, needs sign-off), work claiming, land loop, enrollment command, unknownEvidence split, contention path, authority queue, ownership guard, duplicate-id migration. #CharteredBy d0129. estimatedPoints=8. DoR met."; }
    part dcRefineGateR1 : TestResult { :>> id = "0d620005-0812-4205-9b3e-000000120005"; :>> outcome = VerdictKind::pass; :>> judgedAgainst = "b518c23"; :>> judgedAt = "2026-08-12"; :>> judgedBy = "claudeOpus5"; }

    verification dcStandupGate : Test { :>> id = "0d620006-0812-4206-9b3e-000000120006"; :>> title = "Sprint 247 standup gate"; :>> createdAt = "2026-08-12"; :>> createdBy = "claudeOpus5"; :>> method = VerificationMethod::inspect; :>> procedureText = "Approach: two independent research lanes first (external prior-art + internal code audit), then verify EVERY load-bearing claim against code before authoring a requirement on it — several agent claims were re-checked directly (serve.rs defaults, gen_uuid, orient evidence resolution) and one was corrected (latest sprint is 246, not 163). Author in the declared succession so use cases stay rooted. Order the blockers by blast radius under concurrency: silent corruption and false attribution before throughput. No blockers."; }
    part dcStandupGateR1 : TestResult { :>> id = "0d620007-0812-4207-9b3e-000000120007"; :>> outcome = VerdictKind::pass; :>> judgedAgainst = "b518c23"; :>> judgedAt = "2026-08-12"; :>> judgedBy = "claudeOpus5"; }

    verification dcImplementGate : Test { :>> id = "0d620008-0812-4208-9b3e-000000120008"; :>> title = "Sprint 247 implement gate"; :>> createdAt = "2026-08-12"; :>> createdBy = "claudeOpus5"; :>> method = VerificationMethod::demo; :>> procedureText = "Implemented at b518c23. All five blockers delivered + the SE chain + D0129 + 2 processes + 2 skills + 11 Issues. Live-verified: remote merge methods (gh api shows squash=false rebase=false), branch protection (force_push=false deletions=false enforce_admins=true requires_pr=false so the facts lane still works), portable pre-commit runs clean and finds the binary by probing, duplicate-identity guard finds 26 real pre-existing duplicates and grandfathers them, `keel actor` refuses unregistered/binds registered, write path attributes from the binding. clippy clean; 146 tests; validate + guard + check-engine green; CI green at b518c23."; }
    part dcImplementGateR1 : TestResult { :>> id = "0d620009-0812-4209-9b3e-000000120009"; :>> outcome = VerdictKind::pass; :>> judgedAgainst = "b518c23"; :>> judgedAt = "2026-08-12"; :>> judgedBy = "claudeOpus5"; }

    verification dcReviewGate : Test { :>> id = "0d62000a-0812-420a-9b3e-00000012000a"; :>> title = "Sprint 247 review gate"; :>> createdAt = "2026-08-12"; :>> createdBy = "claudeOpus5"; :>> method = VerificationMethod::inspect; :>> procedureText = "Reviewed. The strongest property of this increment is that nothing was papered over: the duplicate-identity guard immediately found 26 REAL pre-existing violations and they were grandfathered VISIBLY (warnings every run + issue080) rather than suppressed or retro-failed, honouring the issue068 forward-only lesson; and the kernel instance validator's pre-existing failure on 11 committed decisions was recorded as issue081 with the SKIP_VALIDATE bypass stated in the record rather than used silently. The identity control refuses instead of defaulting, which is the correct direction for a security-relevant guard. Two things deliberately NOT done: the frozen-schema marker declarations (needs human sign-off) and the two-lane POLICY being written into CLAUDE.md as in-force (D0129 is proposed — only the mechanical controls are documented as active). Clean."; }
    part dcReviewGateR1 : TestResult { :>> id = "0d62000b-0812-420b-9b3e-00000012000b"; :>> outcome = VerdictKind::pass; :>> judgedAgainst = "b518c23"; :>> judgedAt = "2026-08-12"; :>> judgedBy = "claudeOpus5"; }

    verification dcCloseOutGate : Test { :>> id = "0d62000c-0812-420c-9b3e-00000012000c"; :>> title = "Sprint 247 closeOut gate (autonomous, D0049)"; :>> createdAt = "2026-08-12"; :>> createdBy = "claudeOpus5"; :>> method = VerificationMethod::inspect; :>> procedureText = "Autonomous closeOut (D0049). All six delivered actions carry passing DoD TestResults judged at b518c23 (dcMergeOnlyIntegration, dcDuplicateIdentityGuard, dcCollisionResistantIds, dcActorIdentityBinding, dcPortableGate, dcTwoPassRegistration). Self-evidencing: the gates ARE cargo test / clippy / keel validate / guard / check-engine / CI, all green. Eight follow-on actions remain on the backlog (dcDeclaredMarkers, dcWorkClaim, dcLandLoop, dcEnrollment, dcUnresolvedEvidence, dcContentionAdjudication, dcAuthorityQueue, dcMechanizeOwnership) plus two repair actions (dcRepairDuplicateIds, dcStaleKernelInstanceGate). Awaiting the human's per-sitting sign-off, which must also decide D0129's acceptance (still proposed — no acceptance event was fabricated)."; }
    part dcCloseOutGateR1 : TestResult { :>> id = "0d62000d-0812-420d-9b3e-00000012000d"; :>> outcome = VerdictKind::pass; :>> judgedAgainst = "b518c23"; :>> judgedAt = "2026-08-12"; :>> judgedBy = "claudeOpus5"; }

    verification dcRetroGate : Test { :>> id = "0d62000e-0812-420e-9b3e-00000012000e"; :>> title = "Sprint 247 retro gate (autonomous, D0049)"; :>> createdAt = "2026-08-12"; :>> createdBy = "claudeOpus5"; :>> method = VerificationMethod::analyze; :>> procedureText = "Autonomous retro (D0049). WELL: (1) verifying every agent claim against code before writing a requirement on it caught a wrong inference (latest sprint 246, not 163) and let each SR cite file:line — requirements grounded in evidence rather than in a report; (2) the new guard was made FORWARD-ONLY the moment it found pre-existing violations, so the honest-state doctrine held under pressure instead of being traded for a green board; (3) the number-collision defect was proven by EXPERIENCE mid-sprint (below), which is far stronger evidence than the audit alone. AVOIDABLE-ISSUE 1: I piped `git commit` output to `tail`, which hung the kernel JVM for five minutes — CLAUDE.md §6 documents exactly this ('NEVER pipe conda run output'). LESSON: the prohibition applies to any command whose HOOKS invoke conda, not just direct conda calls; redirect to a file instead. AVOIDABLE-ISSUE 2: a bare `cat > file` with no heredoc blocked on stdin for two minutes. LESSON: never emit a redirect without an input source in a non-interactive shell. LIVE CONFIRMATION OF issue074: mid-sprint I allocated issue071 while an earlier uncommitted session had already claimed 071 in two Rust comments; git reported NO conflict because the claims lived in different files, and it surfaced only because a hook told me to read a diff. That is the exact mechanism the guard now catches, and it happened to the engine's own authors within one hour — the strongest possible argument for the control. Resolved on the principle that the MODEL is the register of record and a code comment is not an allocation (mine kept 071, the unfiled defect became issue079). Estimate 8 pts, delivered. Two Issues (080, 081) were raised BY doing the work — both pre-existing debt that had never been visible."; }
    part dcRetroGateR1 : TestResult { :>> id = "0d62000f-0812-420f-9b3e-00000012000f"; :>> outcome = VerdictKind::pass; :>> judgedAgainst = "b518c23"; :>> judgedAt = "2026-08-12"; :>> judgedBy = "claudeOpus5"; }
}
