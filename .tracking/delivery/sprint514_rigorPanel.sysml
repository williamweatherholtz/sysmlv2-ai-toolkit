// ProjectDeliveryS514 — Sprint 514: the five-critic panel on rigor, and the two fixes it authorised.
// EXECUTE. 5 pts.
package ProjectDeliveryS514 {
    private import EngineElement::*;
    private import EngineWork::*;
    private import EngineVerification::*;
    private import EngineRelationships::*;

    #CharteredBy dependency from rigorPanelStory to d0279;

    part rigorPanelStory : Story {
        :>> id = "c3d8a917-6e42-4b05-a1f8-27b9f0e63c54";
        :>> title = "Sprint 514: why rigor slips - five critics, fifteen functions, one sentence, two fixes (5 pts)";
        :>> createdAt = "2026-09-01"; :>> createdBy = "claudeOpus5"; :>> kind = WorkKind::modeling; :>> priority = WorkPriority::p0; :>> owner = "claudeOpus5"; :>> estimatedPoints = 5;
    }

    action def DeliveryRunS514 {
        action storyRigorPanel;
        verification storyRigorPanelDoD : Test { :>> id = "d4e9ba28-7f53-4c16-b209-38c0a1f74d65"; :>> method = VerificationMethod::test; :>> procedureText = "DELIVERED BACKLOG ITEMS: dcRetroFindingsRoute (resolves issue335) and dcTurnGateFailsClosed (resolves issue334). Also recorded, not built: dcProcessStepsBindToChecks (issue336, a proposal for the human) and dcSessionActorReachesHooks (issue337, correcting issue332). THE PANEL: five critics, five lenses, fifteen functions read at file:line, recorded as critique facts in panel-rigor.sysml targeting the code registry. THE VERDICT they converged on: keel enforces FORM rigorously and SUBSTANCE weakly, and the enforcement it has is advisory by failure mode. MEASURED: 12 enforcement points, 2 fail-closed; 37 processes, 16 with any guard, 11 undeclared; the three guards between a finding and its loss all check existence. VERIFY: the Stop wrapper emits a block decision on a missing binary and the hardening table reports 3 fail-closed; retro_backlog examines every retro gate and fails when this commit adds no item the retro names, with both earlier holes kept as regression cases; this commit's own retro passes the new guard because it names issue334-337, which this commit adds."; }
        // RAN: retro_tie_tests 8/8 and the view-side case; generated_hooks test asserts Stop blocks and UserPromptSubmit still allows; hardening reports 3 fail-closed of 12; sync-claude regenerated settings.json and the Stop wrapper reads back BLOCKING; control-defect-registry 3 scanned after the retro-backlog entry was removed in this same commit
        part storyRigorPanelDoDR1 : TestResult { :>> id = "e5f0cb39-8064-4d27-c31a-49d1b2085e76"; :>> outcome = VerdictKind::pass; :>> judgedAgainst = "a52d81b"; :>> judgedAt = "2026-09-01"; :>> judgedBy = "claudeOpus5"; }
    }

    verification rigorPanelRefineGate : Test { :>> id = "f601dc4a-9175-4e38-d42b-5a02c3196f87"; :>> title = "Sprint 514 refine gate (DoR)"; :>> createdAt = "2026-09-01"; :>> createdBy = "claudeOpus5"; :>> method = VerificationMethod::inspect; :>> procedureText = "READY because the human asked a falsifiable question and the tools to answer it existed: keel hardening already computed the enforcement-point table and the process-enforcement buckets, so the panel could start from measurements rather than impressions. The fifteen functions were chosen by what they DECIDE - what is enforced, what counts as done, who is acting, what a finding becomes - not by size or recency."; }
    verification rigorPanelStandupGate : Test { :>> id = "0712ed5b-a286-4f49-e53c-6b13d42a7098"; :>> title = "Sprint 514 standup gate"; :>> createdAt = "2026-09-01"; :>> createdBy = "claudeOpus5"; :>> method = VerificationMethod::inspect; :>> procedureText = "THE DISCIPLINE THAT MATTERED: assume each claim FALSE until the source refutes the refutation. That produced one reversal of my own record - issue332 said the ownership guard reads the machine binding; actor::resolve at actor.rs:97-112 shows it prefers KEEL_ACTOR, and guards.rs:2498 shows ownership calls it. The guard was right; the session's identity never reaches the hook's environment. Had I not read the source, issue332's carry reason (guard source, keystone) would have stood, and it was wrong. And one reversal I chose NOT to make: the Stop hook's fail-open was a recorded design (D0134), not an oversight, so it is refined by Decision rather than patched - the pre-write precedent is what made the refinement defensible rather than a preference."; }
    verification rigorPanelImplementGate : Test { :>> id = "1823fe6c-b397-4050-f64d-7c24e5318109"; :>> title = "Sprint 514 implement gate"; :>> createdAt = "2026-09-01"; :>> createdBy = "claudeOpus5"; :>> method = VerificationMethod::test; :>> procedureText = "RAN: cargo test --lib retro -> 8 passed, including a_finding_in_any_words_with_no_new_item_is_a_violation (the issue335 hole) and naming_the_delivered_task_does_not_track_a_finding (the issue189 hole) - both earlier shapes of the guard would have passed those inputs. generated_hooks_have_five_events_and_fail_loud_resolution extended: Stop's command contains decision:block, UserPromptSubmit's does not. sync-claude regenerated the live settings.json and the Stop wrapper read back BLOCKING. keel hardening: fail-closed 3 of 12 (Stop, pre-write, pre-commit). The hardening row for Stop was hand-edited to be TRUE, because failMode there is keyword-classified from the row's own prose - a description, not a measurement, and named as such in D0279."; }
    verification rigorPanelReviewGate : Test { :>> id = "2934af7d-c4a8-4161-0752-8d35f6429210"; :>> title = "Sprint 514 review gate — three passes per D0172"; :>> createdAt = "2026-09-01"; :>> createdBy = "claudeOpus5"; :>> method = VerificationMethod::inspect; :>> procedureText = "THREE PASSES. (1) DID THE PANEL AFFIRM OR ATTACK: every critique states the claim it attacked, the file:line it read, and the refuting evidence; critic 2 also records what it could NOT refute (the form-checking guards hold), which is what separates a critique from a complaint. (2) IS THE TURN-GATE CHANGE A LOCKOUT RISK: yes, deliberately, and the trade is stated in D0279 - a project without keel cannot end a turn until it is installed, which is loud and says what to do, against an enforcement layer that disabled itself silently. Advisory hooks are untouched. (3) DID THE FINDINGS BECOME ITEMS OR PROSE: four Issues, four tasks, one Decision, five critique records - and this retro is the first one examined by the guard it fixed, because that guard now examines every retro."; }
    verification rigorPanelCloseOutGate : Test { :>> id = "3a45b08e-d5b9-4272-1863-9e46a753a321"; :>> title = "Sprint 514 closeOut gate (autonomous, D0049)"; :>> createdAt = "2026-09-01"; :>> createdBy = "claudeOpus5"; :>> method = VerificationMethod::inspect; :>> procedureText = "CLOSED. Two of the panel's four findings fixed and armed in this commit; two carried with written reasons - issue337 is a plumbing fix that needs no signature and is next; issue336 is a schema fork that goes to the human. The rigor panel's verdict stands as D0279's title, so it is a tracked claim and not a mood."; }
    verification rigorPanelRetroGate : Test { :>> id = "4b56c19f-e6ca-4383-2974-af57b864b432"; :>> title = "Sprint 514 retro gate (autonomous, D0049)"; :>> createdAt = "2026-09-01"; :>> createdBy = "claudeOpus5"; :>> method = VerificationMethod::analyze; :>> procedureText = "FINDINGS, and this retro is the first written under the guard it fixed. (1) tracked as issue334: the turn gate allowed on a missing binary - the control against a rogue turn switched itself off on a PATH problem, twice today, silently. (2) tracked as issue335: retro_backlog was vocabulary-keyed and satisfied by any task name, so every retro I wrote today was examined by nothing - the six findings they carried are now Issues only because a human asked why rigor was slipping. (3) tracked as issue336: a process is a document with an optional guard; steps bind to no predicate; analyses live in String fields. This is the root the other three are instances of, and it is the human's to decide. (4) tracked as issue337: the session's actor never reaches the hooks - and this finding CORRECTS my own issue332, whose diagnosis and carry-reason were both wrong, which I found only by reading the source I had earlier described from memory. THE GENERAL FORM, stated once: every control that failed today failed by checking that something EXISTS rather than that it is RIGHT, because existence is what a String field can be checked for. Until analyses are typed, the guards over them will be greps, and greps are bypassed by phrasing."; }
}
