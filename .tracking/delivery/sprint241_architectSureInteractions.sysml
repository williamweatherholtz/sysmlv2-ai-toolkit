// ProjectDeliveryS241 — Sprint 241: Architect Sure interaction batch — right-click context actions,
// undo/redo navigation, search-first discovery + single-type solo, Settings-housed connection (D0126).
// Delivers srViewerContextActions / srViewerNavHistory / srViewerSearchDiscovery; partially advances
// srViewerAuthoringSurface (context menu surfaces Supersede/Critique; create/edit = viewerAuthoringEndpoints).
// EXECUTE. 3 pts.
package ProjectDeliveryS241 {
    private import EngineElement::*;
    private import EngineWork::*;
    private import EngineVerification::*;
    private import EngineRelationships::*;

    #CharteredBy dependency from architectSureInteractionsStory to d0126;

    part architectSureInteractionsStory : Story {
        :>> id = "63940516-2c7d-4e8f-c241-51627384c001";
        :>> title = "Sprint 241: Architect Sure interactions (3 pts) - context menu, undo/redo, search-first discovery, single-type solo, Settings";
        :>> createdAt = "2026-07-16"; :>> createdBy = "wweatherholtz"; :>> kind = WorkKind::code; :>> priority = WorkPriority::p2; :>> owner = "claudeOpus"; :>> estimatedPoints = 3;
    }

    action def DeliveryRunS241 {
        action storyArchitectSureInteractions;
        verification storyArchitectSureInteractionsDoD : Test { :>> id = "63940516-2c7d-4e8f-c241-51627384c002"; :>> method = VerificationMethod::demo; :>> procedureText = "Delivers the human-directed (2026-07-16) interaction batch for Architect Sure (viewer@14d390e), governed by D0126. (1) srViewerContextActions: right-click a graph node -> a context menu of actions generated from keel's contract (Focus / Expand / Detail always; Critique when critique-plan advertised; Supersede when /api/edge advertised + the node is a Need/SR/Decision). (2) srViewerNavHistory: a navigation history with undo/redo (top-bar arrows + Ctrl+Z / Ctrl+Shift+Z), disabling at each end; Focus re-anchors on a fresh slice, Expand accumulates. (3) srViewerSearchDiscovery: discovery is SEARCH-FIRST — the finder returns matches to a query (or one solo'd type) rather than dumping all 728 items; empty query shows guidance; a type chip solos its type (click), 'only this type' (right-click), with a clear control. (4) Settings: the keel connection (address + Connect) moved into a Settings dialog with a connection-state dot; the prominent 'New decision' button removed (authoring now on the element via the context menu + a compact + in Find). VERIFY (demo, live): search-first (0 idle rows, 13 for 'encoding'); solo filters to one type; undo restores the prior focus + re-enables redo; context menu builds Focus/Expand/Detail/Critique/Supersede for a Need; connection lives in Settings; 0 console errors. HONEST: srViewerAuthoringSurface is PARTIALLY advanced (Supersede/Critique/Disposition reachable; create-item + edit-attributes need keel endpoints — tracked as viewerAuthoringEndpoints)."; }
        part storyArchitectSureInteractionsDoDR1 : TestResult { :>> id = "63940516-2c7d-4e8f-c241-51627384c003"; :>> outcome = VerdictKind::pass; :>> judgedAgainst = "8bb416c"; :>> judgedAt = "2026-07-16"; :>> judgedBy = "claudeOpus"; }
    }

    verification asRefineGate : Test { :>> id = "63940516-2c7d-4e8f-c241-51627384c004"; :>> title = "Sprint 241 refine gate (DoR)"; :>> createdAt = "2026-07-16"; :>> createdBy = "claudeOpus"; :>> method = VerificationMethod::inspect; :>> procedureText = "DoR: use cases + SRs recorded (architect-sure.sysml, D0126). Scope: the viewer-only interaction batch (context menu, undo/redo, search-first + solo, Settings); the authoring endpoints are deferred (viewerAuthoringEndpoints). #CharteredBy d0126. estimatedPoints=3. DoR met."; }
    part asRefineGateR1 : TestResult { :>> id = "63940516-2c7d-4e8f-c241-51627384c005"; :>> outcome = VerdictKind::pass; :>> judgedAgainst = "8bb416c"; :>> judgedAt = "2026-07-16"; :>> judgedBy = "claudeOpus"; }
    verification asStandupGate : Test { :>> id = "63940516-2c7d-4e8f-c241-51627384c006"; :>> title = "Sprint 241 standup gate"; :>> createdAt = "2026-07-16"; :>> createdBy = "claudeOpus"; :>> method = VerificationMethod::inspect; :>> procedureText = "Approach: cytoscape cxttap -> a generated context menu; a focus history array with undo/redo + keyboard; gate the finder on query/solo/date (search-first); move connection into a Settings dialog. All viewer-only over the existing API. No blockers."; }
    part asStandupGateR1 : TestResult { :>> id = "63940516-2c7d-4e8f-c241-51627384c007"; :>> outcome = VerdictKind::pass; :>> judgedAgainst = "8bb416c"; :>> judgedAt = "2026-07-16"; :>> judgedBy = "claudeOpus"; }
    verification asImplementGate : Test { :>> id = "63940516-2c7d-4e8f-c241-51627384c008"; :>> title = "Sprint 241 implement gate"; :>> createdAt = "2026-07-16"; :>> createdBy = "claudeOpus"; :>> method = VerificationMethod::demo; :>> procedureText = "Implemented (viewer@14d390e). Live-verified: context menu actions per type; undo/redo focus history; search-first (no dump) + single-type solo; Settings-housed connection; 0 console errors."; }
    part asImplementGateR1 : TestResult { :>> id = "63940516-2c7d-4e8f-c241-51627384c009"; :>> outcome = VerdictKind::pass; :>> judgedAgainst = "8bb416c"; :>> judgedAt = "2026-07-16"; :>> judgedBy = "claudeOpus"; }
    verification asReviewGate : Test { :>> id = "63940516-2c7d-4e8f-c241-51627384c00a"; :>> title = "Sprint 241 review gate"; :>> createdAt = "2026-07-16"; :>> createdBy = "claudeOpus"; :>> method = VerificationMethod::inspect; :>> procedureText = "Reviewed. The batch directly answers the human's feedback (right-click focus, undo/redo, single-type select, no full-list dump, Settings-housed connection, less 'new decision' prevalence). Actions stay GENERATED from the contract (no hardcoded per-type action set). HONEST caveat surfaced, not hidden: full create/edit authoring needs keel endpoints (tracked). Clean."; }
    part asReviewGateR1 : TestResult { :>> id = "63940516-2c7d-4e8f-c241-51627384c00b"; :>> outcome = VerdictKind::pass; :>> judgedAgainst = "8bb416c"; :>> judgedAt = "2026-07-16"; :>> judgedBy = "claudeOpus"; }
    verification asCloseOutGate : Test { :>> id = "63940516-2c7d-4e8f-c241-51627384c00c"; :>> title = "Sprint 241 closeOut gate (autonomous, D0049)"; :>> createdAt = "2026-07-16"; :>> createdBy = "claudeOpus"; :>> method = VerificationMethod::inspect; :>> procedureText = "Autonomous closeOut (D0049): the interaction batch is delivered + verified (srViewerContextActions / srViewerNavHistory / srViewerSearchDiscovery). Self-evidencing. NEXT: viewerAuthoringEndpoints (keel create/edit write endpoints) to complete srViewerAuthoringSurface; pending the human's per-sitting review of this sitting's Architect Sure work."; }
    part asCloseOutGateR1 : TestResult { :>> id = "63940516-2c7d-4e8f-c241-51627384c00d"; :>> outcome = VerdictKind::pass; :>> judgedAgainst = "8bb416c"; :>> judgedAt = "2026-07-16"; :>> judgedBy = "claudeOpus"; }
    verification asRetroGate : Test { :>> id = "63940516-2c7d-4e8f-c241-51627384c00e"; :>> title = "Sprint 241 retro gate (autonomous, D0049)"; :>> createdAt = "2026-07-16"; :>> createdBy = "claudeOpus"; :>> method = VerificationMethod::analyze; :>> procedureText = "Autonomous retro (D0049). WELL: recorded the use cases + SRs BEFORE building (the human's 'recording is part of the task'), so the batch shipped against a recorded charter (D0126). Kept the action surface generated from the contract. Verified each behaviour live in-browser + fixed the fonts to vendored/offline in the prior increment. AVOIDABLE-ISSUE: the earlier browse-first 'list all' was over-built for a huge model — the human corrected to search-first; LESSON: for large stores, default to search, not a full list (recorded as the srViewerSearchDiscovery rationale). Estimate 3 pts. NEXT: viewerAuthoringEndpoints."; }
    part asRetroGateR1 : TestResult { :>> id = "63940516-2c7d-4e8f-c241-51627384c00f"; :>> outcome = VerdictKind::pass; :>> judgedAgainst = "8bb416c"; :>> judgedAt = "2026-07-16"; :>> judgedBy = "claudeOpus"; }
}
