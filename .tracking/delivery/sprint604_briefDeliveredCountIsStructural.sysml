// ProjectDeliveryS604 — Sprint 604: The standing brief's already-in-the-tree count is read from delivery records, not typed - a D0047 correction for issue411 (dcBriefDeliveredCountIsStructural, chartered by D0359's rule that every number on the page is computed). EXECUTE. 1 pts.
package ProjectDeliveryS604 {
    private import EngineElement::*;
    private import EngineWork::*;
    private import EngineVerification::*;
    private import EngineRelationships::*;

    #CharteredBy dependency from briefDeliveredCountIsStructuralStory to d0359;

    part briefDeliveredCountIsStructuralStory : Story {
        :>> id = "f5582d9d-dcfc-4b39-a0df-74691be5adf8";
        :>> title = "Sprint 604: The standing brief's already-in-the-tree count is read from delivery records, not typed - a D0047 correction for issue411 (dcBriefDeliveredCountIsStructural, chartered by D0359's rule that every number on the page is computed) (1 pts)";
        :>> createdAt = "2026-09-08"; :>> createdBy = "claudeOpus5"; :>> kind = WorkKind::code; :>> priority = WorkPriority::p0; :>> owner = "claudeOpus5"; :>> estimatedPoints = 1;
    }

    action def DeliveryRunS604 {
        action storyBriefDeliveredCountIsStructural;
        verification storyBriefDeliveredCountIsStructuralDoD : Test { :>> id = "7e87cabc-f9c8-4ae5-a7ad-cbda8de04f1b"; :>> method = VerificationMethod::test; :>> procedureText = "DONE MEANS dcBriefDeliveredCountIsStructural's own DoD holds: scripts/exec_brief/facts.py emits pendingDelivered / pendingDeliveredList from typed edges and recorded verdicts (a delivery record's #CharteredBy edge to the Decision plus a story DoD TestResult with outcome pass), keeps the phrase rule pendingAlreadyShipped beside it for a Decision built outside any sprint, and emits pendingInTree as their union with a `how` naming both rules; scripts/exec_brief/rebuild_2026_09_08.py reads that one fact, cross-checks it against the two lists it came from and refuses on disagreement, refuses on any anchor it cannot find exactly once, and carries a `not-an-instrument:` line because it renders and measures nothing; the page's chips, table and footer carry the fact and no other number; check_templates --brief clean; guard instruments-declared passes with the builder scanned. VERIFIED: python scripts/exec_brief/facts.py -> pendingDelivered=5 (d0361, d0363, d0368, d0370, d0371), pendingAlreadyShipped=2 (d0361, d0366), pendingInTree=6; the rebuild printed pending=8 in_tree=6; check_templates clean; keel guard instruments-declared PASS 19 scanned."; }
        // RAN: python scripts/exec_brief/facts.py -> pendingDelivered=5, pendingAlreadyShipped=2, pendingInTree=6 (d0361, d0363, d0366, d0368, d0370, d0371); python scripts/exec_brief/rebuild_2026_09_08.py -> wrote decision-brief.html pending=8 in_tree=6; python scripts/check_templates.py --brief -> clean; keel guard instruments-declared --no-receipt -> PASS 19 scanned
        part storyBriefDeliveredCountIsStructuralDoDR1 : TestResult { :>> id = "02e3a6b6-16b4-4b2c-b91f-61dc215fba60"; :>> outcome = VerdictKind::pass; :>> judgedAgainst = "c9401e9f087597568cb9ffa76281f4123a976900"; :>> judgedAt = "2026-09-08T01:40:00-06:00"; :>> judgedBy = "claudeOpus5"; }
    }

    verification briefDeliveredCountIsStructuralRefineGate : Test { :>> id = "0c4f5038-11f6-4a69-99ff-8ec3a00ee473"; :>> title = "Sprint 604 refine gate (DoR)"; :>> createdAt = "2026-09-08"; :>> createdBy = "claudeOpus5"; :>> method = VerificationMethod::inspect; :>> procedureText = "READY, 1 pt: two Python scripts, no engine code. The defect is recorded as issue411 with this task as its resolver. Chartered by D0359, whose DoD says the brief's numbers are computed, not typed - this sprint makes that true for the one number the phrase rule had left to the author."; }
    // RAN: inspect: sprint 604 Refine text against the sprint file; python scripts/exec_brief/facts.py pendingInTree=6; rebuild printed pending=8 in_tree=6; check_templates --brief clean; keel guard instruments-declared PASS
    part briefDeliveredCountIsStructuralRefineGateR1 : TestResult { :>> id = "4ed1ec95-487a-439e-aace-c19a991605f2"; :>> outcome = VerdictKind::pass; :>> judgedAgainst = "c9401e9f087597568cb9ffa76281f4123a976900"; :>> judgedAt = "2026-09-08T01:40:00-06:00"; :>> judgedBy = "claudeOpus5"; }
    verification briefDeliveredCountIsStructuralStandupGate : Test { :>> id = "4428a20c-4e72-4ac4-9ea7-c6ee73f14137"; :>> title = "Sprint 604 standup gate"; :>> createdAt = "2026-09-08"; :>> createdBy = "claudeOpus5"; :>> method = VerificationMethod::inspect; :>> procedureText = "ONE CHOICE. The structural reading replaces judgment, and the phrase rule is kept rather than deleted, because a Decision built outside any sprint has no delivery record for the edges to see; the union is emitted by the declared sensor (facts.py) so the builder derives nothing the human reads - guard instruments-declared flagged the builder the first time the union lived there, and the fix was to move the number onto the sensor, not to declare a one-day script as an instrument."; }
    // RAN: inspect: sprint 604 Standup text against the sprint file; python scripts/exec_brief/facts.py pendingInTree=6; rebuild printed pending=8 in_tree=6; check_templates --brief clean; keel guard instruments-declared PASS
    part briefDeliveredCountIsStructuralStandupGateR1 : TestResult { :>> id = "dc98f185-a8b1-4233-a7a9-362d864d1c58"; :>> outcome = VerdictKind::pass; :>> judgedAgainst = "c9401e9f087597568cb9ffa76281f4123a976900"; :>> judgedAt = "2026-09-08T01:40:00-06:00"; :>> judgedBy = "claudeOpus5"; }
    verification briefDeliveredCountIsStructuralImplementGate : Test { :>> id = "47b870ee-c501-4307-add2-215d09bb533e"; :>> title = "Sprint 604 implement gate"; :>> createdAt = "2026-09-08"; :>> createdBy = "claudeOpus5"; :>> method = VerificationMethod::test; :>> procedureText = "RAN: python scripts/exec_brief/facts.py > facts.json (pendingInTree=6, none of the three new facts null); python scripts/exec_brief/rebuild_2026_09_08.py facts.json <prior page> decision-brief.html -> wrote, pending=8 in_tree=6; python scripts/check_templates.py --brief decision-brief.html -> clean; keel guard instruments-declared --no-receipt -> PASS; keel record issue (issue411, resolver dcBriefDeliveredCountIsStructural); keel append-result on the task; keel validate ."; }
    // RAN: inspect: sprint 604 Implement text against the sprint file; python scripts/exec_brief/facts.py pendingInTree=6; rebuild printed pending=8 in_tree=6; check_templates --brief clean; keel guard instruments-declared PASS
    part briefDeliveredCountIsStructuralImplementGateR1 : TestResult { :>> id = "a5c6610e-062f-41bd-a03e-f580a920288e"; :>> outcome = VerdictKind::pass; :>> judgedAgainst = "c9401e9f087597568cb9ffa76281f4123a976900"; :>> judgedAt = "2026-09-08T01:40:00-06:00"; :>> judgedBy = "claudeOpus5"; }
    verification briefDeliveredCountIsStructuralReviewGate : Test { :>> id = "015a4858-a1f0-42d4-b4da-5002a441e57a"; :>> title = "Sprint 604 review gate — three passes per D0172"; :>> createdAt = "2026-09-08"; :>> createdBy = "claudeOpus5"; :>> method = VerificationMethod::inspect; :>> procedureText = "THREE QUESTIONS (D0172). Does the number now come from facts the guards already validate? Yes: #CharteredBy edges (charter guard) and story DoD TestResults (validate) - rewording a consequences string cannot move it. Can the builder still type a count? No: it reads pendingInTree, exits if the fact disagrees with the union of its own two source lists, and exits if any anchor matches other than once. What is NOT claimed: that a Decision delivered outside a sprint is seen structurally - it is not, which is why the phrase rule stays and the footnote states both counts."; }
    // RAN: inspect: sprint 604 Review text against the sprint file; python scripts/exec_brief/facts.py pendingInTree=6; rebuild printed pending=8 in_tree=6; check_templates --brief clean; keel guard instruments-declared PASS
    part briefDeliveredCountIsStructuralReviewGateR1 : TestResult { :>> id = "c9f07e50-ce7e-460d-958c-3046fe8e5cc3"; :>> outcome = VerdictKind::pass; :>> judgedAgainst = "c9401e9f087597568cb9ffa76281f4123a976900"; :>> judgedAt = "2026-09-08T01:40:00-06:00"; :>> judgedBy = "claudeOpus5"; }
    verification briefDeliveredCountIsStructuralCloseOutGate : Test { :>> id = "26265556-b4ca-4d61-b5b4-93bcb9c0ce6d"; :>> title = "Sprint 604 closeOut gate (autonomous, D0049)"; :>> createdAt = "2026-09-08"; :>> createdBy = "claudeOpus5"; :>> method = VerificationMethod::inspect; :>> procedureText = "CLOSED. issue411 resolved by dcBriefDeliveredCountIsStructural; the brief republished at the same URL with eight asks and its in-the-tree count read from the tree. The prior page's 'three of five' was wrong by one against the instrument it cited; the instrument was also wrong by one against the tree - both are gone."; }
    // RAN: inspect: sprint 604 CloseOut text against the sprint file; python scripts/exec_brief/facts.py pendingInTree=6; rebuild printed pending=8 in_tree=6; check_templates --brief clean; keel guard instruments-declared PASS
    part briefDeliveredCountIsStructuralCloseOutGateR1 : TestResult { :>> id = "8ff62a8f-3170-4d88-bbe3-06998ef3686a"; :>> outcome = VerdictKind::pass; :>> judgedAgainst = "c9401e9f087597568cb9ffa76281f4123a976900"; :>> judgedAt = "2026-09-08T01:40:00-06:00"; :>> judgedBy = "claudeOpus5"; }
    verification briefDeliveredCountIsStructuralRetroGate : Test { :>> id = "d0dad0bd-75b3-42b1-b596-cd1b0d5b9431"; :>> title = "Sprint 604 retro gate (autonomous, D0049)"; :>> createdAt = "2026-09-08"; :>> createdBy = "claudeOpus5"; :>> method = VerificationMethod::analyze; :>> procedureText = "AVOIDABLE-ISSUE SCAN HELD. Finding: the first cut put the union in the page builder and guard instruments-declared caught it - a control that did its job; the finding is that the builder is a dated one-shot script, so the next queue change writes another, and each is scanned. No new item - already tracked: dcStopSaysNothingAboutDecisions's DoD moved the brief's facts and charts into scripts/exec_brief/ as the re-runnable process, and issue411 holds the typed-count class."; }
    // RAN: inspect: sprint 604 Retro text against the sprint file; python scripts/exec_brief/facts.py pendingInTree=6; rebuild printed pending=8 in_tree=6; check_templates --brief clean; keel guard instruments-declared PASS
    part briefDeliveredCountIsStructuralRetroGateR1 : TestResult { :>> id = "bd7b19a9-12c0-4745-9691-761aa1ebfb56"; :>> outcome = VerdictKind::pass; :>> judgedAgainst = "c9401e9f087597568cb9ffa76281f4123a976900"; :>> judgedAt = "2026-09-08T01:40:00-06:00"; :>> judgedBy = "claudeOpus5"; }
}
