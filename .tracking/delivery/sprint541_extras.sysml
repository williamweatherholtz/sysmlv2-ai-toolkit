// ProjectDeliveryS541 — Sprint 541: a unit's declared mechanism is required where the unit is installed. EXECUTE. 2 pts.
package ProjectDeliveryS541 {
    private import EngineElement::*;
    private import EngineWork::*;
    private import EngineVerification::*;
    private import EngineRelationships::*;

    #CharteredBy dependency from extrasStory to d0300;

    part extrasStory : Story {
        :>> id = "637f9d97-40ac-47b9-abea-55f4cc1e76e6";
        :>> title = "Sprint 541: guard 60 unit-extras-present, the contract's meaning flipped from optional to required, adoption-check states its scope, and an inline-array blind spot fixed in two readers (2 pts)";
        :>> createdAt = "2026-09-04"; :>> createdBy = "claudeOpus5"; :>> kind = WorkKind::code; :>> priority = WorkPriority::p0; :>> owner = "claudeOpus5"; :>> estimatedPoints = 2;
    }

    action def DeliveryRunS541 {
        action storyExtras;
        verification storyExtrasDoD : Test { :>> id = "0436ba2a-d4c7-494d-ba79-ef87af901134"; :>> method = VerificationMethod::test; :>> procedureText = "DELIVERED BACKLOG ITEMS: dcMechanismMustBePresent (resolves issue290). DONE: guard unit-extras-present - every file an INSTALLED unit declares in unit-extras.toml must exist, else a violation naming unit, path and remedy; uninstalled units not judged; unit-extras.toml header says REQUIRED (was: skipped silently), says import not hand-staging, and shows the declaration shape; adoption-check prints that it verifies the EXPORT and not a target; process_cmd::unit_extras and the guard both read inline TOML arrays, which the exporter's reader used to read as empty. VERIFY: fixture with a declared, installed, absent file FAILS; present PASSES; this tree scans 0 (stated in LEGITIMATELY_EMPTY and guards.md); two unit tests; 474 tests; clippy clean. The penumbra clause is satisfied by the control existing for that project to run on its own tree, not by this repository asserting its state."; }
        // RAN: keel guard unit-extras-present <fixture> FAIL 1 violation naming x and .github/workflows/x.yml; touch the file -> PASS; . -> 0 scanned; cargo test --release 474/0 after the example path fix; clippy 0; the first run of the suite FAILED adoption_check_can_fail because the contract header's example named .engine/tools/x.py and tool-reference refused the dead path in the scaffold - the example now names paths no guard resolves
        part storyExtrasDoDR1 : TestResult { :>> id = "82d69ad6-214e-4368-b6d8-b5ee4fa95b68"; :>> outcome = VerdictKind::pass; :>> judgedAgainst = "a708369"; :>> judgedAt = "2026-09-04"; :>> judgedBy = "claudeOpus5"; }
    }

    verification extrasRefineGate : Test { :>> id = "fafdf05d-beee-4214-b595-3bfd566d4f27"; :>> title = "Sprint 541 refine gate (DoR)"; :>> createdAt = "2026-09-04"; :>> createdBy = "claudeOpus5"; :>> method = VerificationMethod::inspect; :>> procedureText = "READY once the DoD's channel-specific wording was read against the tree: the channel unit is gone (D0292) and no installed unit declares extras, so the item is the CLASS - a guard the next unit with a mechanism inherits - and the fixture is what proves it, not this tree."; }
    verification extrasStandupGate : Test { :>> id = "c833e513-aada-48d6-98a0-56e857a2d85c"; :>> title = "Sprint 541 standup gate"; :>> createdAt = "2026-09-04"; :>> createdBy = "claudeOpus5"; :>> method = VerificationMethod::inspect; :>> procedureText = "ONE CHOICE: the guard judges INSTALLED units only. Judging every declared unit would fail every project on files it never adopted - the issue259 direction adoption-check exists to prevent. Second: the contract's meaning changed from optional to required, said in the header and in D0300, because 'skipped silently' is the sentence that let a missing mechanism read as a clean tree."; }
    verification extrasImplementGate : Test { :>> id = "cfdd492b-5497-43f1-929d-6ef2e05a3b78"; :>> title = "Sprint 541 implement gate"; :>> createdAt = "2026-09-04"; :>> createdBy = "claudeOpus5"; :>> method = VerificationMethod::test; :>> procedureText = "RAN: the first fixture scanned ZERO - the parser dropped an inline array, and so did the exporter's reader it was modelled on; both fixed, and the multi-line opener then read as an empty inline array until the closing bracket was required on the same line. Then tool-reference refused the header's example path in the scaffolded fixture. Three defects of mine, each found by a number or a failure that looked wrong."; }
    verification extrasReviewGate : Test { :>> id = "ee3bf221-23f1-44c0-a92d-9939d9cc431f"; :>> title = "Sprint 541 review gate — three passes per D0172"; :>> createdAt = "2026-09-04"; :>> createdBy = "claudeOpus5"; :>> method = VerificationMethod::inspect; :>> procedureText = "THREE PASSES. (1) WOULD IT HAVE CAUGHT PENUMBRA: yes, on penumbra's own gate, the moment it ran with the unit installed and .github absent - which is where the failure was. (2) WHAT IT CANNOT SEE: a unit that never declared its mechanism at all; the header now tells the author to declare it, and adoption-check tells the reader what it does not check. (3) IS THE EXPORTER FIX SAFE: inline and multi-line arrays parse identically now, tested; requires lines take both shapes too."; }
    verification extrasCloseOutGate : Test { :>> id = "7bc48c7f-4877-4018-b8c9-e054ee74f340"; :>> title = "Sprint 541 closeOut gate (autonomous, D0049)"; :>> createdAt = "2026-09-04"; :>> createdBy = "claudeOpus5"; :>> method = VerificationMethod::inspect; :>> procedureText = "CLOSED. issue290 resolves; guard count 60; guards.md row; control map anchor to ehz7."; }
    verification extrasRetroGate : Test { :>> id = "7fe3fcaf-d9d3-4547-8750-738dd5913937"; :>> title = "Sprint 541 retro gate (autonomous, D0049)"; :>> createdAt = "2026-09-04"; :>> createdBy = "claudeOpus5"; :>> method = VerificationMethod::analyze; :>> procedureText = "no new item - already tracked: the exporter's inline-array blind spot is fixed here and recorded in d0300 rather than opened, because it no longer exists; the undeclared-mechanism residual is the header's instruction and adoption-check's scope line, both covered by d0300. The pattern of the day - a check whose first run reports zero must be distrusted until a fixture makes it fire - is the LEGITIMATELY_EMPTY test's whole reason, and it did its job on this guard too."; }
}
