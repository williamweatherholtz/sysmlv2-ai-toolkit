// ProjectDeliveryS278 — Sprint 278: provenance navigability delivered by COMPUTATION; `ref Actor` is
// blocked by the engine/instance boundary (issue106). Panel finding (e). EXECUTE. 3 pts.
package ProjectDeliveryS278 {
    private import EngineElement::*;
    private import EngineWork::*;
    private import EngineVerification::*;
    private import EngineRelationships::*;

    #CharteredBy dependency from actorTraceStory to d0142;

    part actorTraceStory : Story {
        :>> id = "0d80010d-0814-610d-9b3e-00000030010d";
        :>> title = "Sprint 278: keel actor-trace — navigability without inverting the engine boundary (3 pts)";
        :>> createdAt = "2026-08-14"; :>> createdBy = "claudeOpus5"; :>> kind = WorkKind::code; :>> priority = WorkPriority::p0; :>> owner = "claudeOpus5"; :>> estimatedPoints = 3;
    }

    action def DeliveryRunS278 {
        action storyActorTrace;
        verification storyActorTraceDoD : Test { :>> id = "0d80010e-0814-610e-9b3e-00000030010e"; :>> method = VerificationMethod::test; :>> procedureText = "Covers dcActorTraceView (issue106), answering panel finding (e) — the second of the two migrations the human required completed. THE FINDING IS CORRECT: provenance is carried in Strings while `part def Actor` exists, so no viewer can select an actor and see what they authored, and that is the one trace surviving a provenance audit. MEASURED: 6132 values across four registered actors, plus 53 across TEN legacy names none of which are registered. THE PROPOSED FIX IS BLOCKED, structurally: `.engine` carries 137 of those values and the registry is `ProjectActors`, whose header declares it 'INSTANCE data; per-project'. `ref createdBy : Actor` would force every `.engine` decision file to import a tracking package; `.engine` imports only `Engine*` today and ships downstream via `keel init`, where this project's actors do not exist, so those references would arrive unresolved. The panel assessed the type surface and not the packaging. FOUR OPTIONS WEIGHED, three rejected: migrating `.tracking` only leaves two mechanisms for one fact; moving actors into `.engine` contradicts what actors are; a separate engine-author registry invents a second concept larger than the need. CHOSEN: deliver the NAVIGABILITY by computation — `keel actor-trace <actor>` reports authored / judged / owned from the strings. Same derive-do-not-author move the human reasoned to for `Assumption` (issue105); no schema change, no boundary crossed, cannot go stale. VERIFIED: wweatherholtz 643 authored / 233 judged / 0 owned; claudeSonnet46 9 / 91 / 13. clippy clean; 161 tests; validate + all 28 guards + check-engine green."; }
        part storyActorTraceDoDR1 : TestResult { :>> id = "0d80010f-0814-610f-9b3e-00000030010f"; :>> outcome = VerdictKind::pass; :>> judgedAgainst = "a14d564"; :>> judgedAt = "2026-08-14"; :>> judgedBy = "claudeOpus5"; }
    }

    verification atRefineGate : Test { :>> id = "0d800110-0814-6110-9b3e-000000300110"; :>> title = "Sprint 278 refine gate (DoR)"; :>> createdAt = "2026-08-14"; :>> createdBy = "claudeOpus5"; :>> method = VerificationMethod::inspect; :>> procedureText = "DoR: the human required both excluded migrations completed. The first (Process-as-behaviour) was mechanical once kernel-verified. This one required checking the packaging before transforming 6132 values — and that check is what found the blocker. estimatedPoints=3. DoR met."; }
    part atRefineGateR1 : TestResult { :>> id = "0d800111-0814-6111-9b3e-000000300111"; :>> outcome = VerdictKind::pass; :>> judgedAgainst = "a14d564"; :>> judgedAt = "2026-08-14"; :>> judgedBy = "claudeOpus5"; }

    verification atStandupGate : Test { :>> id = "0d800112-0814-6112-9b3e-000000300112"; :>> title = "Sprint 278 standup gate"; :>> createdAt = "2026-08-14"; :>> createdBy = "claudeOpus5"; :>> method = VerificationMethod::inspect; :>> procedureText = "Approach: measure the value distribution first, then check where the reference TARGET lives relative to where the references would be authored. That second check is the one that mattered and it takes one grep — `.engine` imports only Engine* packages — but it decides whether a 6132-value migration is possible at all. No blockers, but a redirect."; }
    part atStandupGateR1 : TestResult { :>> id = "0d800113-0814-6113-9b3e-000000300113"; :>> outcome = VerdictKind::pass; :>> judgedAgainst = "a14d564"; :>> judgedAt = "2026-08-14"; :>> judgedBy = "claudeOpus5"; }

    verification atImplementGate : Test { :>> id = "0d800114-0814-6114-9b3e-000000300114"; :>> title = "Sprint 278 implement gate"; :>> createdAt = "2026-08-14"; :>> createdBy = "claudeOpus5"; :>> method = VerificationMethod::test; :>> procedureText = "Rejecting the tracking-only migration was the decisive call. It would have been the easy way to report the finding 'done' — 6079 of 6132 values converted, a big number in a commit message — and it would have left the model with two mechanisms for one fact, which is strictly worse than one imperfect mechanism and precisely the dual-truth failure this engine exists to prevent. A partial migration that looks like progress is the most expensive possible outcome here."; }
    part atImplementGateR1 : TestResult { :>> id = "0d800115-0814-6115-9b3e-000000300115"; :>> outcome = VerdictKind::pass; :>> judgedAgainst = "a14d564"; :>> judgedAt = "2026-08-14"; :>> judgedBy = "claudeOpus5"; }

    verification atReviewGate : Test { :>> id = "0d800116-0814-6116-9b3e-000000300116"; :>> title = "Sprint 278 review gate"; :>> createdAt = "2026-08-14"; :>> createdBy = "claudeOpus5"; :>> method = VerificationMethod::inspect; :>> procedureText = "Reviewed. The residual limitation is real and is recorded rather than glossed: a viewer loading the RAW model still sees provenance strings, so the navigability now lives in keel and not in SysML v2 itself. That is the price of not inverting the engine boundary, and a reader deserves to know it was a trade rather than a win. The 53 legacy provenance values also remain, still surfaced as warnings by the `actors` guard — untouched, because converting them would have been part of the migration that is not happening."; }
    part atReviewGateR1 : TestResult { :>> id = "0d800117-0814-6117-9b3e-000000300117"; :>> outcome = VerdictKind::pass; :>> judgedAgainst = "a14d564"; :>> judgedAt = "2026-08-14"; :>> judgedBy = "claudeOpus5"; }

    verification atCloseOutGate : Test { :>> id = "0d800118-0814-6118-9b3e-000000300118"; :>> title = "Sprint 278 closeOut gate (autonomous, D0049)"; :>> createdAt = "2026-08-14"; :>> createdBy = "claudeOpus5"; :>> method = VerificationMethod::inspect; :>> procedureText = "Autonomous closeOut (D0049). dcActorTraceView carries a passing DoD TestResult; issue106 resolves and supersedes the SHAPE of dcProvenanceAsRefs, which must not be executed as written. Both migrations the human required are now resolved — one delivered as specified (D0143), one redirected with the blocker recorded and the value delivered another way. clippy clean; 161 tests; validate + all 28 guards + check-engine green. No gate bypassed."; }
    part atCloseOutGateR1 : TestResult { :>> id = "0d800119-0814-6119-9b3e-000000300119"; :>> outcome = VerdictKind::pass; :>> judgedAgainst = "a14d564"; :>> judgedAt = "2026-08-14"; :>> judgedBy = "claudeOpus5"; }

    verification atRetroGate : Test { :>> id = "0d80011a-0814-611a-9b3e-00000030011a"; :>> title = "Sprint 278 retro gate (autonomous, D0049)"; :>> createdAt = "2026-08-14"; :>> createdBy = "claudeOpus5"; :>> method = VerificationMethod::analyze; :>> procedureText = "Autonomous retro (D0049) under D0131's retroTrack. WELL: (1) the packaging was checked BEFORE transforming 6132 values, and that one grep is what found a structural blocker the three-critic panel missed — they assessed the type surface, not where the reference target lives relative to where references would be authored; (2) the tracking-only partial migration was rejected even though it would have let me report a large number as done, because two mechanisms for one fact is worse than one imperfect mechanism; (3) the residual limitation — navigability lives in keel, not in the raw model — is recorded as a trade rather than presented as a win. AVOIDABLE-ISSUE 1: I began this sprint intending to execute the migration as specified, and only checked the packaging when scoping the transform. Had I checked at the point the panel's finding was first RECORDED, dcProvenanceAsRefs would never have been written with that shape and the human would not have been told it was merely 'excluded pending review'. NO NEW ITEM, reason stated: this is the same check-the-consumer-first lesson as sprints 270 and 277, now its third instance in this pass; it is not gate-able because the relevant consumer differs per change, but three instances is enough that it belongs in how findings are TRIAGED rather than only in how they are executed — recorded here and in issue106. Estimate 3 pts, delivered."; }
    part atRetroGateR1 : TestResult { :>> id = "0d80011b-0814-611b-9b3e-00000030011b"; :>> outcome = VerdictKind::pass; :>> judgedAgainst = "a14d564"; :>> judgedAt = "2026-08-14"; :>> judgedBy = "claudeOpus5"; }
}
