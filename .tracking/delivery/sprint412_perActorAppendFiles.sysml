// ProjectDeliveryS412 — Sprint 412: per-actor append routing (issue210): critiques and issues land in the actor's own file - the probe issue is its own evidence. EXECUTE. 2 pts.
package ProjectDeliveryS412 {
    private import EngineElement::*;
    private import EngineWork::*;
    private import EngineVerification::*;
    private import EngineRelationships::*;

    #CharteredBy dependency from perActorAppendFilesStory to d0193;

    part perActorAppendFilesStory : Story {
        :>> id = "9d84c434-a159-49c5-9bb6-2d0423902e67";
        :>> title = "Sprint 412: appends stop sharing an anchor (2 pts)";
        :>> createdAt = "2026-08-22"; :>> createdBy = "claudeFable5"; :>> kind = WorkKind::code; :>> priority = WorkPriority::p0; :>> owner = "claudeFable5"; :>> estimatedPoints = 2;
    }

    action def DeliveryRunS412 {
        action storyPerActorAppendFiles;
        verification storyPerActorAppendFilesDoD : Test { :>> id = "4bffdc58-3407-4b92-a36d-9e15f27a310b"; :>> method = VerificationMethod::test; :>> procedureText = "DELIVERED: dcPerActorAppendFiles (resolves issue210 and its own probe issue214). FORWARD-ONLY routing per the DoD: write::per_actor_file creates .tracking/<kind>-<actor>.sysml on first use (unique package name, standard imports), and the two high-traffic surfaces route through it - record issue lands in the AUTHOR's issues file (allocation stays GLOBAL: the number scans all of .tracking under the legacy file's lock as the allocation mutex, so per-actor files cannot fork the sequence; offline-clone collisions remain the duplicate-identity guard's job exactly as before), and the three critique/disposition writers (the sitting endpoint, the disposition endpoint, apply-review) land in the JUDGE's critiques file. Existing shared files stay where history put them; readers glob .tracking (validate immediately counted the new file: 449 -> 450). VERIFIED LIVE: issue214 was recorded through the changed path and landed in issues-claudeFable5.sysml with the next global number - the probe is kept as its own evidence. The protected-path patterns widened to prefixes so per-actor files inherit the pre-write protection (surface regenerated via sync-claude, drift check green). Merge-cleanliness is by construction (distinct paths - the same property obligations and runs already had), proven for distinct paths generally by the sprint-410 two-clone harness."; }
        part storyPerActorAppendFilesDoDR1 : TestResult { :>> id = "db615009-4343-45ab-82f3-8825fac6d167"; :>> outcome = VerdictKind::pass; :>> judgedAgainst = "f8279a8"; :>> judgedAt = "2026-08-22"; :>> judgedBy = "claudeFable5"; }
    }

    verification perActorAppendFilesRefineGate : Test { :>> id = "3ff88ee4-e2f7-4ede-8056-d33f5ef84946"; :>> title = "Sprint 412 refine gate (DoR)"; :>> createdAt = "2026-08-22"; :>> createdBy = "claudeFable5"; :>> method = VerificationMethod::inspect; :>> procedureText = "DoR. Chartered by d0193's family (the same designed-somewhere-not-everywhere closure shape); resolves the critique campaign's shared-anchor finding whose instances include this campaign's own writes. 2 points."; }
    part perActorAppendFilesRefineGateR1 : TestResult { :>> id = "d689bc62-7e27-4075-b610-110ed1776267"; :>> outcome = VerdictKind::pass; :>> judgedAgainst = "f8279a8"; :>> judgedAt = "2026-08-22"; :>> judgedBy = "claudeFable5"; }
    verification perActorAppendFilesStandupGate : Test { :>> id = "d091ff2a-fa9c-490c-bdbc-90f7328d8f6c"; :>> title = "Sprint 412 standup gate"; :>> createdAt = "2026-08-22"; :>> createdBy = "claudeFable5"; :>> method = VerificationMethod::inspect; :>> procedureText = "Approach: forward-only (no history migration - the fix is routing, not rewriting), global allocation under one mutex, judge-routed critiques, author-routed issues, protection patterns widened to match. No blockers."; }
    part perActorAppendFilesStandupGateR1 : TestResult { :>> id = "a9137871-bf93-4fed-b393-e7563690ec4d"; :>> outcome = VerdictKind::pass; :>> judgedAgainst = "f8279a8"; :>> judgedAt = "2026-08-22"; :>> judgedBy = "claudeFable5"; }
    verification perActorAppendFilesImplementGate : Test { :>> id = "ce836408-31fd-47ec-b5a3-63ae03ba90a7"; :>> title = "Sprint 412 implement gate"; :>> createdAt = "2026-08-22"; :>> createdBy = "claudeFable5"; :>> method = VerificationMethod::test; :>> procedureText = "Verified: issue214 recorded through the live changed path into issues-claudeFable5.sysml with the next global number; validate clean at 450 files (the reader glob picked the new file up with zero reader changes); sync-claude --check green after the pattern widening; cargo test 10 suites 279 passed 0 failed; clippy pedantic+nursery clean."; }
    part perActorAppendFilesImplementGateR1 : TestResult { :>> id = "b41f1b86-3edd-4211-a691-c1e9bde37675"; :>> outcome = VerdictKind::pass; :>> judgedAgainst = "f8279a8"; :>> judgedAt = "2026-08-22"; :>> judgedBy = "claudeFable5"; }
    verification perActorAppendFilesReviewGate : Test { :>> id = "8cc461de-9b82-40c1-834d-d6bb14b04c70"; :>> title = "Sprint 412 review gate — three passes per D0172"; :>> createdAt = "2026-08-22"; :>> createdBy = "claudeFable5"; :>> method = VerificationMethod::inspect; :>> procedureText = "PASS 1, CLAIMS: the routing evidence is a live record's own path and number. PASS 2, BOUNDARY: the allocation mutex covers ONE machine (as before) - two offline clones can still allocate the same number, and the record says the duplicate-identity guard remains that backstop, unchanged; also backlog.sysml's add-task anchor is NOT routed (outside the DoD's two named surfaces) and remains a shared anchor - stated, not hidden. PASS 3, OWN DIFF: the probe issue's first description was sloppy authoring (a visible self-correction mid-sentence) - cleaned pre-commit as an owner edit, noted here so the edit is visible. WHAT A REVIEWER SHOULD ATTACK: judge-routed critiques mean one REVIEW SESSION's records spread across files when multiple judges act - readers compute over the glob so nothing breaks, but a human browsing raw files loses the one-file chronology; the computed views are the sanctioned lens, which is the repo's standing answer."; }
    part perActorAppendFilesReviewGateR1 : TestResult { :>> id = "b0cbfd0d-428a-4f79-82b8-34ae6c2eaa60"; :>> outcome = VerdictKind::pass; :>> judgedAgainst = "f8279a8"; :>> judgedAt = "2026-08-22"; :>> judgedBy = "claudeFable5"; }
    verification perActorAppendFilesCloseOutGate : Test { :>> id = "2adf4aca-1f8f-4125-a98b-4ea01f3f9d38"; :>> title = "Sprint 412 closeOut gate (autonomous, D0049)"; :>> createdAt = "2026-08-22"; :>> createdBy = "claudeFable5"; :>> method = VerificationMethod::inspect; :>> procedureText = "Autonomous closeOut (D0049). DoDs flipped for dcPerActorAppendFiles; issues 210 + 214 resolve; validate + all 45 guards green; surface regenerated."; }
    part perActorAppendFilesCloseOutGateR1 : TestResult { :>> id = "a31e8dcb-328e-4828-b0b1-82b6ecb5c6ac"; :>> outcome = VerdictKind::pass; :>> judgedAgainst = "f8279a8"; :>> judgedAt = "2026-08-22"; :>> judgedBy = "claudeFable5"; }
    verification perActorAppendFilesRetroGate : Test { :>> id = "3691db1b-6745-4d95-bdda-126cee5590e9"; :>> title = "Sprint 412 retro gate (autonomous, D0049)"; :>> createdAt = "2026-08-22"; :>> createdBy = "claudeFable5"; :>> method = VerificationMethod::analyze; :>> procedureText = "Autonomous retro (D0049). AVOIDABLE-ISSUE SCAN under rcRecurrence: none new - though the backlog add-task anchor is now the LAST shared high-traffic anchor, named in the review gate for the day its traffic warrants the same routing. WELL: keeping the probe issue as its own evidence beats deleting it (the test IS a record); the forward-only rule kept a 3000-record migration out of scope. Estimate 2 pts, delivered 2."; }
    part perActorAppendFilesRetroGateR1 : TestResult { :>> id = "5e6d0df7-8674-4bc8-b516-fa17731cc187"; :>> outcome = VerdictKind::pass; :>> judgedAgainst = "f8279a8"; :>> judgedAt = "2026-08-22"; :>> judgedBy = "claudeFable5"; }
}
