// ProjectDeliveryS289 — Sprint 289: `keel sync` / `keel land` — gate the tree that will LAND, and let
// orientation carry the sync state it was computed against (dcLandLoop, D0129). EXECUTE. 8 pts.
package ProjectDeliveryS289 {
    private import EngineElement::*;
    private import EngineWork::*;
    private import EngineVerification::*;
    private import EngineRelationships::*;

    #CharteredBy dependency from landLoopStory to d0144;

    part landLoopStory : Story {
        :>> id = "0d8001bd-0814-61bd-9b3e-0000003001bd";
        :>> title = "Sprint 289: keel sync + keel land — the merge queue, executed client-side (8 pts)";
        :>> createdAt = "2026-08-15"; :>> createdBy = "claudeOpus5"; :>> kind = WorkKind::code; :>> priority = WorkPriority::p0; :>> owner = "claudeOpus5"; :>> estimatedPoints = 8;
    }

    action def DeliveryRunS289 {
        action storyLandLoop;
        verification storyLandLoopDoD : Test { :>> id = "0d8001be-0814-61be-9b3e-0000003001be"; :>> method = VerificationMethod::demo; :>> procedureText = "Delivers dcLandLoop (srDcGateOnMergedTree + srDcSyncAwareOrient, D0129). Two contributions that each pass the gate alone can fail together, which is why the gate must run on the tree that will LAND — the merge queue, executed client-side because there is no server. DELIVERED: `keel sync` (fetch, report divergence, integrate by MERGE, gate the result, hand off to orient); `keel land` (push; on rejection fetch, merge, GATE THE MERGED TREE, retry — bounded, with no force path in the module by construction); and `orient` now carries a `sync` block, so every computed answer states the tree position it was computed against — a frontier computed 40 commits behind is a frontier for work someone else may already have done. VERIFIED ON TWO REAL CLONES sharing a bare remote, never touching this project's origin. THE CENTRAL CASE, demonstrated end to end: clone A and clone B each authored an item with the SAME uuid in different files; each was fully GREEN alone (validate clean, all 29 guards exit 0); A landed; B's push was rejected, B merged, and the merged tree FAILED `duplicate-identity` — reported with both file:line locations, exit 1, and the remote verifiably unchanged (0 files from B). The push RACE also resolved with no human action: rejected on attempt 1, integrated, landed on attempt 2. `orient` in the diverged clone reported `behind 0, ahead 2`. TWO REAL BUGS FOUND BY RUNNING IT rather than by reading it, both fixed: `git merge --no-rebase` is not a flag — `--no-rebase` belongs to `git pull` — so the first real merge failed with a usage dump; and `keel land` merged WITHOUT gating, relying on `.githooks/pre-merge-commit`, which a contributor who has not run `git config core.hooksPath` does not have, so it would have pushed a broken trunk while reporting success. clippy clean; 132 lib tests; validate 311 clean; 29 guards green."; }
        part storyLandLoopDoDR1 : TestResult { :>> id = "0d8001bf-0814-61bf-9b3e-0000003001bf"; :>> outcome = VerdictKind::pass; :>> judgedAgainst = "fe7f8ea"; :>> judgedAt = "2026-08-15"; :>> judgedBy = "claudeOpus5"; }
    }

    verification llRefineGate : Test { :>> id = "0d8001c0-0814-61c0-9b3e-0000003001c0"; :>> title = "Sprint 289 refine gate (DoR)"; :>> createdAt = "2026-08-15"; :>> createdBy = "claudeOpus5"; :>> method = VerificationMethod::inspect; :>> procedureText = "DoR, and the consumer check (D0144) CHANGED THE SCOPE. The item's text says 'today nothing fetches: post-commit is fire-and-forget', and that was no longer true — `.githooks/post-commit` already implements the fetch/merge/retry loop and `.githooks/pre-merge-commit` already delegates to pre-commit for the merged-tree gate. Building a Rust copy alongside would have been two live mechanisms for one fact. So the scope became: implement it in the BINARY and make the hook DELEGATE, leaving the shell path only as a degradation for a machine with no `keel` — the same reasoning as D0134. Reading the existing artifact before writing the new one is what turned a duplication into a consolidation. estimatedPoints=8. DoR met."; }
    part llRefineGateR1 : TestResult { :>> id = "0d8001c1-0814-61c1-9b3e-0000003001c1"; :>> outcome = VerdictKind::pass; :>> judgedAgainst = "fe7f8ea"; :>> judgedAt = "2026-08-15"; :>> judgedBy = "claudeOpus5"; }

    verification llStandupGate : Test { :>> id = "0d8001c2-0814-61c2-9b3e-0000003001c2"; :>> title = "Sprint 289 standup gate"; :>> createdAt = "2026-08-15"; :>> createdBy = "claudeOpus5"; :>> method = VerificationMethod::inspect; :>> procedureText = "Approach: test against a THROWAWAY bare repo with two clones, never against this project's origin — `land` pushes, and a command that pushes must be exercised somewhere a mistake costs nothing. Construct a genuine semantic conflict rather than a textual one: two items carrying the same uuid in different files, so each side is green alone and only the merged tree is red. My first attempt was not a conflict at all (two same-named parts in different packages, which is legal) and the test passed for the wrong reason — corrected before drawing any conclusion from it. No blockers."; }
    part llStandupGateR1 : TestResult { :>> id = "0d8001c3-0814-61c3-9b3e-0000003001c3"; :>> outcome = VerdictKind::pass; :>> judgedAgainst = "fe7f8ea"; :>> judgedAt = "2026-08-15"; :>> judgedBy = "claudeOpus5"; }

    verification llImplementGate : Test { :>> id = "0d8001c4-0814-61c4-9b3e-0000003001c4"; :>> title = "Sprint 289 implement gate"; :>> createdAt = "2026-08-15"; :>> createdBy = "claudeOpus5"; :>> method = VerificationMethod::test; :>> procedureText = "The second bug is the one worth recording. `keel land` merged and pushed WITHOUT gating the merged tree, on the assumption that `.githooks/pre-merge-commit` would catch it — and that assumption is exactly the class of defect this project keeps paying for: a control that depends on something its owner cannot guarantee. A contributor who has never run `git config core.hooksPath .githooks` has no hook at all, so `land` would have pushed a broken trunk and reported success. It is now gated in the binary, which is the only place that runs unconditionally. The first bug was cheaper and equally instructive: `git merge --no-rebase` is not valid — `--no-rebase` is a `git pull` flag — and I wrote it to make the never-rebase property explicit. The property comes from choosing `merge` over `pull` at all; the flag was decoration that broke the command, and only running it revealed that."; }
    part llImplementGateR1 : TestResult { :>> id = "0d8001c5-0814-61c5-9b3e-0000003001c5"; :>> outcome = VerdictKind::pass; :>> judgedAgainst = "fe7f8ea"; :>> judgedAt = "2026-08-15"; :>> judgedBy = "claudeOpus5"; }

    verification llReviewGate : Test { :>> id = "0d8001c6-0814-61c6-9b3e-0000003001c6"; :>> title = "Sprint 289 review gate"; :>> createdAt = "2026-08-15"; :>> createdBy = "claudeOpus5"; :>> method = VerificationMethod::inspect; :>> procedureText = "Reviewed. `orient`'s `sync` block reports the UNKNOWN case as itself rather than as zeros, which is the detail that makes it trustworthy: 'I could not tell' and 'you are in sync' are different answers, and a view rendering them identically is the silent-failure shape this project has now paid for three times (issue093, issue096, and the enrollment gate check). The unit test asserts specifically that an unknown state does NOT render as `behind:0`. Also deliberate: `divergence` never fetches. `orient` is run constantly, and a view that silently performs network I/O is a view people stop running — so it reports what the last fetch knew, and `keel sync` is the command that goes and looks."; }
    part llReviewGateR1 : TestResult { :>> id = "0d8001c7-0814-61c7-9b3e-0000003001c7"; :>> outcome = VerdictKind::pass; :>> judgedAgainst = "fe7f8ea"; :>> judgedAt = "2026-08-15"; :>> judgedBy = "claudeOpus5"; }

    verification llCloseOutGate : Test { :>> id = "0d8001c8-0814-61c8-9b3e-0000003001c8"; :>> title = "Sprint 289 closeOut gate (autonomous, D0049)"; :>> createdAt = "2026-08-15"; :>> createdBy = "claudeOpus5"; :>> method = VerificationMethod::inspect; :>> procedureText = "Autonomous closeOut (D0049). dcLandLoop carries a passing DoD TestResult. `.githooks/post-commit` now delegates to `keel land`, with the shell loop surviving only as a no-binary degradation, so there is one authoritative implementation rather than two that can drift. hook-config-integrity passes. clippy clean; 132 lib tests; validate 311 clean; check-engine clean; 29 guards green. No gate bypassed, and this project's own origin was never a test target."; }
    part llCloseOutGateR1 : TestResult { :>> id = "0d8001c9-0814-61c9-9b3e-0000003001c9"; :>> outcome = VerdictKind::pass; :>> judgedAgainst = "fe7f8ea"; :>> judgedAt = "2026-08-15"; :>> judgedBy = "claudeOpus5"; }

    verification llRetroGate : Test { :>> id = "0d8001ca-0814-61ca-9b3e-0000003001ca"; :>> title = "Sprint 289 retro gate (autonomous, D0049)"; :>> createdAt = "2026-08-15"; :>> createdBy = "claudeOpus5"; :>> method = VerificationMethod::analyze; :>> procedureText = "Autonomous retro (D0049) under D0131's retroTrack. WELL: (1) reading the existing hook BEFORE writing the Rust turned a duplication into a consolidation — the item's own text was out of date about what already existed, and taking it at face value would have shipped two live copies of the land loop; (2) the test was built on two real clones and a throwaway remote, which found two bugs that no amount of reading would have — an invalid git flag and a missing gate; (3) my first conflict fixture was not a conflict, and I noticed the test had passed for the wrong reason before drawing any conclusion from it. AVOIDABLE-ISSUE 1: `keel land` shipped its first version relying on `.githooks/pre-merge-commit` to gate the merged tree. That is the fifth instance in this pass of the same shape — a control depending on something its owner cannot guarantee (issue076 runtime, issue081 bypass scope, issue089/090 project data, issue093 gitignored config). NO NEW ITEM, reason stated: caught before commit by the end-to-end test, and the class is already carried by those five issues; what this instance adds is that I wrote it while holding the pattern in mind, which suggests the tell is not 'am I depending on something external' but 'is the thing I am depending on OPTIONAL for the person I am protecting' — hook config is opt-in, and that is precisely what made it unsafe to lean on. Estimate 8 pts, delivered."; }
    part llRetroGateR1 : TestResult { :>> id = "0d8001cb-0814-61cb-9b3e-0000003001cb"; :>> outcome = VerdictKind::pass; :>> judgedAgainst = "fe7f8ea"; :>> judgedAt = "2026-08-15"; :>> judgedBy = "claudeOpus5"; }
}
