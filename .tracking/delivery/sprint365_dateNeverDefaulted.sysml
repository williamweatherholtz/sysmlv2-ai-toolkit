// ProjectDeliveryS365 — Sprint 365: hardening round 5. Five write paths defaulted a provenance date to
// the literal 2026-01-01, and one of them wrote on a bare invocation. EXECUTE. 5 pts.
package ProjectDeliveryS365 {
    private import EngineElement::*;
    private import EngineWork::*;
    private import EngineVerification::*;
    private import EngineRelationships::*;

    #CharteredBy dependency from dateDefaultStory to d0169;

    part dateDefaultStory : Story {
        :>> id = "0d800680-0814-6680-9b3e-000000300680";
        :>> title = "Sprint 365: a provenance date is refused, never defaulted — and no command writes on a bare invocation (5 pts)";
        :>> createdAt = "2026-08-20"; :>> createdBy = "claudeOpus5"; :>> kind = WorkKind::code; :>> priority = WorkPriority::p0; :>> owner = "claudeOpus5"; :>> estimatedPoints = 5;
    }

    action def DeliveryRunS365 {
        action storyDateDefault;
        verification storyDateDefaultDoD : Test { :>> id = "0d800681-0814-6681-9b3e-000000300681"; :>> method = VerificationMethod::test; :>> procedureText = "DELIVERED BACKLOG ITEMS: dcDateNeverDefaulted. Clears issue182 under D0169. FIVE write paths read their date as `flag(args, X).unwrap_or_else(|| '2026-01-01'.to_owned())`: append-result, append-gate-result, record-measurement, snapshot-indicators, apply-review. CLAUDE.md says provenance is never defaulted - implemented for the ACTOR, where a missing actor makes the write REFUSE, while the DATE fell back to a false constant. Guard 36 exists to catch evidence citing a date it could not have had; this was the write path fabricating one. LATENT, NOT ACTIVE, and that is stated rather than buried: zero corpus items carry 2026-01-01, because every real invocation passed an explicit date. FOUND BY A WRITE-API SMOKE TEST that invoked every write command with NO arguments and diffed the tree - eleven refused, and `keel snapshot-indicators` mutated the tree, stamping two Measurements dated 2026-01-01. FIXED by refusing rather than defaulting: an AI has no clock it can attest to, and guessing is what produced the constant. One change closes both halves, because refusing the date makes the bare invocation refuse too - verified: five write commands invoked bare now leave the tree byte-identical. validate 397 clean; check-engine clean; 38 guards ALL PASS; 197 tests; clippy clean."; }
        part storyDateDefaultDoDR1 : TestResult { :>> id = "0d800682-0814-6682-9b3e-000000300682"; :>> outcome = VerdictKind::pass; :>> judgedAgainst = "09a2fb3"; :>> judgedAt = "2026-08-20"; :>> judgedBy = "claudeOpus5"; }
    }

    verification ddRefineGate : Test { :>> id = "0d800683-0814-6683-9b3e-000000300683"; :>> title = "Sprint 365 refine gate (DoR)"; :>> createdAt = "2026-08-20"; :>> createdBy = "claudeOpus5"; :>> method = VerificationMethod::inspect; :>> procedureText = "DoR. Pass 5 probed doc-vs-reality and dead surface, and MOST OF IT CAME BACK CLEAN, which is worth recording as plainly as a finding: guards.md documents exactly the 38 live guards with no drift either way; all 7 declared views compute; and the 14 never-instantiated schema types are 13 STPA types in the OPTIONAL safety schema plus one regex false positive - the word `can` from the phrase `requirement def can't specialize`. Reporting those as dead surface would have been metrics theater on a reusable engine whose safety schema exists for downstream projects. THE FINDING CAME FROM THE ONE PROBE THAT MUTATED STATE: a write-API smoke test that diffed the tree afterwards. estimatedPoints=5."; }
    part ddRefineGateR1 : TestResult { :>> id = "0d800684-0814-6684-9b3e-000000300684"; :>> outcome = VerdictKind::pass; :>> judgedAgainst = "09a2fb3"; :>> judgedAt = "2026-08-20"; :>> judgedBy = "claudeOpus5"; }

    verification ddStandupGate : Test { :>> id = "0d800685-0814-6685-9b3e-000000300685"; :>> title = "Sprint 365 standup gate"; :>> createdAt = "2026-08-20"; :>> createdBy = "claudeOpus5"; :>> method = VerificationMethod::inspect; :>> procedureText = "Approach: REFUSE, do not default to today. Defaulting to the current date would have been the obvious fix and is the same mistake one step further on - the engine would then assert a date nobody stated, which is what the constant did. An AI has no clock it can honestly attest to. Refusing also closes the bare-invocation write for free, because a command that cannot proceed without a date cannot proceed with no arguments. No blockers."; }
    part ddStandupGateR1 : TestResult { :>> id = "0d800686-0814-6686-9b3e-000000300686"; :>> outcome = VerdictKind::pass; :>> judgedAgainst = "09a2fb3"; :>> judgedAt = "2026-08-20"; :>> judgedBy = "claudeOpus5"; }

    verification ddImplementGate : Test { :>> id = "0d800687-0814-6687-9b3e-000000300687"; :>> title = "Sprint 365 implement gate"; :>> createdAt = "2026-08-20"; :>> createdBy = "claudeOpus5"; :>> method = VerificationMethod::test; :>> procedureText = "THE SMOKE TEST THAT FOUND THIS WROTE TO THE MODEL, and I nearly missed that it had. The probe ran twelve write commands with no arguments and compared `git status` line counts before and after: 0 became 1. Without that diff the finding does not exist - a bare invocation printing usage and a bare invocation silently stamping two Measurements look identical on a terminal. THE WORSE HALF WAS IN THE DIFF, NOT THE COUNT: `measuredAt = 2026-01-01` on both rows, in August. Reading the payload rather than just noticing the write is what turned `snapshot-indicators writes on a bare call` into `five write paths fabricate a provenance date`. THREE THINGS PASS 5 DELIBERATELY DID NOT REPORT: 21 never-instantiated types, which became 14 once specialization was counted and then 13 legitimate STPA types plus one false positive; 7 `BROKEN view` lines that were my probe stripping `.view.toml` wrongly and re-appending it; and guard doc drift, of which there is none. Two of those three were my instrument being wrong AGAIN, caught before recording this time rather than after. CONTROL verified by regression: re-introducing one defaulted date literal fails the build."; }
    part ddImplementGateR1 : TestResult { :>> id = "0d800688-0814-6688-9b3e-000000300688"; :>> outcome = VerdictKind::pass; :>> judgedAgainst = "09a2fb3"; :>> judgedAt = "2026-08-20"; :>> judgedBy = "claudeOpus5"; }

    verification ddReviewGate : Test { :>> id = "0d800689-0814-6689-9b3e-000000300689"; :>> title = "Sprint 365 review gate"; :>> createdAt = "2026-08-20"; :>> createdBy = "claudeOpus5"; :>> method = VerificationMethod::inspect; :>> procedureText = "Reviewed. THE INTERESTING PROPERTY OF THIS FINDING IS THAT IT NEVER FIRED. Zero corpus items carry 2026-01-01, so nothing is corrupt and nothing needed repairing - the defect is a loaded trap rather than a wound. That makes it exactly the kind of thing a critique pass is FOR, and exactly the kind of thing a status report would never surface, because every observable number was fine. WHAT MAKES IT HIGH RATHER THAN MEDIUM: guard 36 was written after I fabricated an attestation mechanically (issue144), and it checks that a TestResult's cited commit predates its judgedAt. A write path silently supplying a January date would have produced results that either passed the guard wrongly or failed it for the wrong reason, and either way the guard's verdict would have stopped meaning what it says. A control that can be fed a false input by the sanctioned write path is not a control. WHAT I AM STILL UNEASY ABOUT: `provenance_date` refuses, which is right, but every existing caller of these five commands must now pass a date - and CLAUDE.md's write-API bullet does not say so. Doc-sync covers it in this commit."; }
    part ddReviewGateR1 : TestResult { :>> id = "0d80068a-0814-668a-9b3e-00000030068a"; :>> outcome = VerdictKind::pass; :>> judgedAgainst = "09a2fb3"; :>> judgedAt = "2026-08-20"; :>> judgedBy = "claudeOpus5"; }

    verification ddCloseOutGate : Test { :>> id = "0d80068b-0814-668b-9b3e-00000030068b"; :>> title = "Sprint 365 closeOut gate (autonomous, D0049)"; :>> createdAt = "2026-08-20"; :>> createdBy = "claudeOpus5"; :>> method = VerificationMethod::inspect; :>> procedureText = "Autonomous closeOut (D0049). issue182 cleared. Five passes complete: 12 findings recorded, 12 cleared, 7 permanent controls. Pass 5 is the first to come back mostly CLEAN - guard docs match exactly, all views compute, no dead schema beyond the optional safety package - and the one finding it produced came from the only probe that mutated state. validate 397 clean; check-engine clean; 38 guards ALL PASS; 197 tests; clippy clean."; }
    part ddCloseOutGateR1 : TestResult { :>> id = "0d80068c-0814-668c-9b3e-00000030068c"; :>> outcome = VerdictKind::pass; :>> judgedAgainst = "09a2fb3"; :>> judgedAt = "2026-08-20"; :>> judgedBy = "claudeOpus5"; }

    verification ddRetroGate : Test { :>> id = "0d80068d-0814-668d-9b3e-00000030068d"; :>> title = "Sprint 365 retro gate (autonomous, D0049)"; :>> createdAt = "2026-08-20"; :>> createdBy = "claudeOpus5"; :>> method = VerificationMethod::analyze; :>> procedureText = "Autonomous retro (D0049) under D0131's retroTrack. WELL: (1) the probe DIFFED THE TREE, which is the only reason the finding exists - a silent write and a printed usage line are indistinguishable on a terminal; (2) the payload was read, not just the count, which turned one finding into the larger one behind it; (3) refuse rather than default-to-today, so the engine never asserts a date nobody stated; (4) three candidate findings were discarded before recording - 21 types that were 13 legitimate ones, 7 broken views that were my own suffix bug, guard doc drift that does not exist - which is the first pass where I caught my instrument BEFORE writing the issue rather than after; (5) the clean results are recorded as plainly as the finding, because a pass that reports only what is broken cannot tell a successor what has been checked. AVOIDABLE-ISSUE: the probe wrote to the live model. I ran a write-API smoke test in the working tree, and it stamped two Measurements I then had to revert - the same lesson as sprint 363, where a `--help` sweep created a directory. Two passes running, my probes have mutated the repository they were auditing. THE RULE: a probe that can write runs against a COPY, and if that is inconvenient the probe is the thing to fix. SECOND AVOIDABLE-ISSUE: three clippy rejections in one small helper (match-as-if-let, map_or_else, and a mangled multi-line string). Estimate 5 pts, delivered."; }
    part ddRetroGateR1 : TestResult { :>> id = "0d80068e-0814-668e-9b3e-00000030068e"; :>> outcome = VerdictKind::pass; :>> judgedAgainst = "09a2fb3"; :>> judgedAt = "2026-08-20"; :>> judgedBy = "claudeOpus5"; }
}
