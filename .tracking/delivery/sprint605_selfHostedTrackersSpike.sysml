// ProjectDeliveryS605 — Sprint 605: Research spike, saved on the human's word ('ok. save this as a spike for now.'): Linear, Jira and the self-hosted tracker field compared with keel on where truth lives and who computes state, every external fact checked against a named source (D0374). EXECUTE. 1 pts.
package ProjectDeliveryS605 {
    private import EngineElement::*;
    private import EngineWork::*;
    private import EngineVerification::*;
    private import EngineRelationships::*;

    #CharteredBy dependency from selfHostedTrackersSpikeStory to d0374;

    part selfHostedTrackersSpikeStory : Story {
        :>> id = "1f32cf6f-723f-4bcc-99c8-b582efc6fbf9";
        :>> title = "Sprint 605: Research spike, saved on the human's word ('ok. save this as a spike for now.'): Linear, Jira and the self-hosted tracker field compared with keel on where truth lives and who computes state, every external fact checked against a named source (D0374) (1 pts)";
        :>> createdAt = "2026-09-08"; :>> createdBy = "claudeOpus5"; :>> kind = WorkKind::code; :>> priority = WorkPriority::p0; :>> owner = "claudeOpus5"; :>> estimatedPoints = 1;
    }

    action def DeliveryRunS605 {
        action storySelfHostedTrackersSpike;
        verification storySelfHostedTrackersSpikeDoD : Test { :>> id = "5c2993b4-ec2f-48ed-bad6-6e06504a22a4"; :>> method = VerificationMethod::test; :>> procedureText = "DONE MEANS docs/reviews/self-hosted-trackers-2026-09-07.md exists carrying the human's three questions verbatim, the answer first, the Linear/Jira facts (no self-hosting; Data Center read-only 28 Mar 2029; agents cloud-only), the contrast table on the truth/status/done/priority/history/identity/sign-off/exit axes, agent practice on each, the self-hosted field table (GitLab, Plane, OpenProject, Huly, Taiga/Redmine/Vikunja), the Plane caveat with its two UNVERIFIED claims labelled as such, the ranking on the self-hosting surface alone, the statement that nothing is adopted, and the sources with their check date; D0374 records the spike as saved with no tracker adopted and this sprint is chartered by it. No engine, process or tracking-model change. VERIFIED: the review file is present with every section named; keel validate .; keel guard."; }
        // RAN: grep -c over docs/reviews/self-hosted-trackers-2026-09-07.md for each DoD section heading = present; .engine/decisions/0374-self-hosted-trackers-spike-saved.sysml AUTO-ACCEPTED; keel validate . 688 clean; keel guard --no-receipt ALL PASS
        part storySelfHostedTrackersSpikeDoDR1 : TestResult { :>> id = "2c85974e-6f99-46e4-97b4-acc7022fdeb5"; :>> outcome = VerdictKind::pass; :>> judgedAgainst = "a08f2a194520e7d4d2c6a96c413985881215cecf"; :>> judgedAt = "2026-09-08T02:10:00-06:00"; :>> judgedBy = "claudeOpus5"; }
    }

    verification selfHostedTrackersSpikeRefineGate : Test { :>> id = "00e6043e-db49-4a7d-9c41-d2cb3568fbcb"; :>> title = "Sprint 605 refine gate (DoR)"; :>> createdAt = "2026-09-08"; :>> createdBy = "claudeOpus5"; :>> method = VerificationMethod::inspect; :>> procedureText = "READY, 1 pt: a research record and one Decision, no code. Chartered by D0374. The material was produced in conversation on 2026-09-07 with each external claim fetched from its source that day; this sprint moves it from conversation into the repository, because a conversation is not a record (D0040)."; }
    // RAN: inspect: sprint 605 Refine text; docs/reviews/self-hosted-trackers-2026-09-07.md present with every section named in the DoD; D0374 recorded and auto-accepted; keel validate .
    part selfHostedTrackersSpikeRefineGateR1 : TestResult { :>> id = "2b004d7c-1fa4-4459-bae9-413644b9468a"; :>> outcome = VerdictKind::pass; :>> judgedAgainst = "a08f2a194520e7d4d2c6a96c413985881215cecf"; :>> judgedAt = "2026-09-08T02:10:00-06:00"; :>> judgedBy = "claudeOpus5"; }
    verification selfHostedTrackersSpikeStandupGate : Test { :>> id = "c62e5764-e0bd-4f8b-8a3a-6b1596b97d29"; :>> title = "Sprint 605 standup gate"; :>> createdAt = "2026-09-08"; :>> createdBy = "claudeOpus5"; :>> method = VerificationMethod::inspect; :>> procedureText = "ONE CHOICE. The review keeps the two claims that could not be verified from public documentation labelled UNVERIFIED rather than dropped or resolved by guess - whether Plane's agent framework runs on the AGPL Community build, and which GitLab tier gates Duo on self-managed - because they are exactly what a later adoption trial would have to answer first, and a spike that hid them would read as more settled than it is."; }
    // RAN: inspect: sprint 605 Standup text; docs/reviews/self-hosted-trackers-2026-09-07.md present with every section named in the DoD; D0374 recorded and auto-accepted; keel validate .
    part selfHostedTrackersSpikeStandupGateR1 : TestResult { :>> id = "41ce4176-2227-4b76-87c3-79c681c5bd07"; :>> outcome = VerdictKind::pass; :>> judgedAgainst = "a08f2a194520e7d4d2c6a96c413985881215cecf"; :>> judgedAt = "2026-09-08T02:10:00-06:00"; :>> judgedBy = "claudeOpus5"; }
    verification selfHostedTrackersSpikeImplementGate : Test { :>> id = "e0ceaf63-d1d8-49f8-8e81-89e5f7897c8b"; :>> title = "Sprint 605 implement gate"; :>> createdAt = "2026-09-08"; :>> createdBy = "claudeOpus5"; :>> method = VerificationMethod::test; :>> procedureText = "RAN: recovered the three conversation answers from the session transcript by line (2046, 2086, 2144) and rewrote them as one review with the same facts, tables and sources; keel record decision --from d0374.md (AUTO-ACCEPTED, non-fork); keel new sprint 605; keel validate .; keel guard --no-receipt."; }
    // RAN: inspect: sprint 605 Implement text; docs/reviews/self-hosted-trackers-2026-09-07.md present with every section named in the DoD; D0374 recorded and auto-accepted; keel validate .
    part selfHostedTrackersSpikeImplementGateR1 : TestResult { :>> id = "9d238328-300c-47d6-8691-fe09b3f52291"; :>> outcome = VerdictKind::pass; :>> judgedAgainst = "a08f2a194520e7d4d2c6a96c413985881215cecf"; :>> judgedAt = "2026-09-08T02:10:00-06:00"; :>> judgedBy = "claudeOpus5"; }
    verification selfHostedTrackersSpikeReviewGate : Test { :>> id = "5a544262-fc63-464f-961d-ac985d89e307"; :>> title = "Sprint 605 review gate — three passes per D0172"; :>> createdAt = "2026-09-08"; :>> createdBy = "claudeOpus5"; :>> method = VerificationMethod::inspect; :>> procedureText = "THREE QUESTIONS (D0172). Is every external claim sourced? Yes: thirteen sources listed with the check date, and each factual row traces to one. Is anything asserted that was not checked? Two claims are labelled UNVERIFIED in the text where they appear and again in the Decision's context. What is NOT claimed: that any tracker should be adopted, that GitLab's or Plane's agent path was exercised, or that the external facts hold past 2026-09-07 - Jira's dates in particular are a vendor schedule that can move."; }
    // RAN: inspect: sprint 605 Review text; docs/reviews/self-hosted-trackers-2026-09-07.md present with every section named in the DoD; D0374 recorded and auto-accepted; keel validate .
    part selfHostedTrackersSpikeReviewGateR1 : TestResult { :>> id = "10ccb7b3-22d6-4e99-a409-67a4d168be96"; :>> outcome = VerdictKind::pass; :>> judgedAgainst = "a08f2a194520e7d4d2c6a96c413985881215cecf"; :>> judgedAt = "2026-09-08T02:10:00-06:00"; :>> judgedBy = "claudeOpus5"; }
    verification selfHostedTrackersSpikeCloseOutGate : Test { :>> id = "ed120cbc-2d63-42f6-9715-a543d1d43509"; :>> title = "Sprint 605 closeOut gate (autonomous, D0049)"; :>> createdAt = "2026-09-08"; :>> createdBy = "claudeOpus5"; :>> method = VerificationMethod::inspect; :>> procedureText = "CLOSED. The spike is a record in docs/reviews with D0374 as its charter; the human's request of 2026-09-07 is no longer held only in conversation. Nothing adopted, nothing in the engine changed."; }
    // RAN: inspect: sprint 605 CloseOut text; docs/reviews/self-hosted-trackers-2026-09-07.md present with every section named in the DoD; D0374 recorded and auto-accepted; keel validate .
    part selfHostedTrackersSpikeCloseOutGateR1 : TestResult { :>> id = "867518c8-2a61-43b8-9dfa-4452aeb6d60b"; :>> outcome = VerdictKind::pass; :>> judgedAgainst = "a08f2a194520e7d4d2c6a96c413985881215cecf"; :>> judgedAt = "2026-09-08T02:10:00-06:00"; :>> judgedBy = "claudeOpus5"; }
    verification selfHostedTrackersSpikeRetroGate : Test { :>> id = "cbb247d3-3ea1-4c08-b253-32163209585d"; :>> title = "Sprint 605 retro gate (autonomous, D0049)"; :>> createdAt = "2026-09-08"; :>> createdBy = "claudeOpus5"; :>> method = VerificationMethod::analyze; :>> procedureText = "AVOIDABLE-ISSUE SCAN HELD. Finding: the request to save the spike was made on 2026-09-07 and recorded on 2026-09-08, after the performance work the same message asked for - a day in which the answer lived only in a transcript that had to be recovered by line number after compaction. No new item - already tracked: the recording-is-part-of-the-task rule this project already holds, and dcStopSaysNothingAboutDecisions's DoD names the same class (a process the next session cannot re-run is a memory rather than a process)."; }
    // RAN: inspect: sprint 605 Retro text; docs/reviews/self-hosted-trackers-2026-09-07.md present with every section named in the DoD; D0374 recorded and auto-accepted; keel validate .
    part selfHostedTrackersSpikeRetroGateR1 : TestResult { :>> id = "f9dc5651-032c-4262-93b7-b4621ad90947"; :>> outcome = VerdictKind::pass; :>> judgedAgainst = "a08f2a194520e7d4d2c6a96c413985881215cecf"; :>> judgedAt = "2026-09-08T02:10:00-06:00"; :>> judgedBy = "claudeOpus5"; }
}
