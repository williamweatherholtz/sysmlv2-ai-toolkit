// ProjectDeliveryS501 — Sprint 501: an issues pull pipeline whose autonomy follows repository visibility. EXECUTE. 5 pts.
package ProjectDeliveryS501 {
    private import EngineElement::*;
    private import EngineWork::*;
    private import EngineVerification::*;
    private import EngineRelationships::*;

    #CharteredBy dependency from issuePullPipelineStory to d0264;

    part issuePullPipelineStory : Story {
        :>> id = "ed0bbde7-6323-4abd-bb44-f7eea688ae15";
        :>> title = "Sprint 501: private acts, public plans, undetermined fails closed (5 pts)";
        :>> createdAt = "2026-08-30"; :>> createdBy = "claudeOpus5"; :>> kind = WorkKind::code; :>> priority = WorkPriority::p0; :>> owner = "claudeOpus5"; :>> estimatedPoints = 5;
    }

    action def DeliveryRunS501 {
        action storyIssuePullPipeline;
        verification storyIssuePullPipelineDoD : Test { :>> id = "9c8ebe40-55cd-4b74-a8ab-80ba863af5f9"; :>> method = VerificationMethod::test; :>> procedureText = "DELIVERED (D0264, from st047): keel github-pull enumerates open issues and ingests each one no Statement cites, skipping pull requests (a PR carries a diff, not a report). SourceTrust joins the schema and sourceTrust joins Statement, RECORDED ON THE UTTERANCE rather than decided at act time - a repo's visibility can change after an issue is filed, and without the record a stranger's words are indistinguishable from a maintainer's. Derived from gh api .private, overridable by --trust, UNDETERMINED FAILS CLOSED. Guard 56 untrusted-routing enforces the boundary: a story descending from an untrusted utterance and already routed must have a Decision among its targets. The process gains giPull and giBoundary; the skill states the tier table and the reason. VERIFY: 675 tests pass 0 fail; clippy clean; guard 56 armed by 5 probes including the two allow-cases that must NOT fire; a LIVE pull against this repository read it PUBLIC, printed plan-only, ingested 4 issues at untrusted and skipped the 1 already recorded; the unit is published to the library (6 units) and a fresh project's import path demonstrated.: DELIVERED BACKLOG ITEMS: <items>. <what done means, verified how>."; }
        // RAN: // RAN: 675 tests 0 failed; clippy clean; validate_schema 19/19 kernel; 56 guards 0 violations; LIVE github-pull read this repo PUBLIC, printed plan-only, ingested GH#34-37 at untrusted, skipped GH#38; untrusted_routing_bites 5/5 incl. two allow-cases; unit published (6 in library)
        part storyIssuePullPipelineDoDR1 : TestResult { :>> id = "29d6bbee-a8ee-4e60-89a6-ad8599e2f520"; :>> outcome = VerdictKind::pass; :>> judgedAgainst = "93458ad"; :>> judgedAt = "2026-08-30"; :>> judgedBy = "claudeOpus5"; }
    }

    verification issuePullPipelineRefineGate : Test { :>> id = "8510cc23-7c2b-4991-9a02-522eedd5e440"; :>> title = "Sprint 501 refine gate (DoR)"; :>> createdAt = "2026-08-30"; :>> createdBy = "claudeOpus5"; :>> method = VerificationMethod::inspect; :>> procedureText = "READY: the mechanism was small and the POLICY was the substance, so the decision text argues the policy first - a public issue is an instruction from an unauthenticated stranger, and feeding it to an autonomous agent is prompt injection with a filing form. Scope bounded by what it EXCLUDES: no author-association refinement, because that would WIDEN a security boundary the human drew explicitly."; }
    verification issuePullPipelineStandupGate : Test { :>> id = "8dae7ec5-f445-4066-954a-0615895e7012"; :>> title = "Sprint 501 standup gate"; :>> createdAt = "2026-08-30"; :>> createdBy = "claudeOpus5"; :>> method = VerificationMethod::inspect; :>> procedureText = "No blocker. One design question decided deliberately: author_association (OWNER/MEMBER/COLLABORATOR/NONE) is a strictly better trust signal than repository visibility and would let a public project's maintainer act on their own issues. NOT adopted - widening a stated security boundary uninvited is the wrong direction to be inventive in. Named in D0264 as the next increment, to be taken deliberately or not at all."; }
    verification issuePullPipelineImplementGate : Test { :>> id = "d17285d5-6abb-42ea-bdf4-61f4aaba610b"; :>> title = "Sprint 501 implement gate"; :>> createdAt = "2026-08-30"; :>> createdBy = "claudeOpus5"; :>> method = VerificationMethod::test; :>> procedureText = "RAN: cargo test --workspace --release -> 675 passed, 0 failed. clippy -D warnings clean. validate_schema.py -> 19/19 against the kernel for the SourceTrust addition. keel guard -> 56 guards, 0 violations. LIVE: keel github-pull against williamweatherholtz/sysmlv2-ai-toolkit reported 'trust tier: untrusted - PUBLIC', printed the plan-only verdict, ingested GH#34/35/36/37 and skipped GH#38 as already recorded. TWO THINGS FAILED AND BOTH WERE MINE: the sourceTrust field was declared on the struct and never emitted by the writer, so the first live pull recorded four statements with no tier - caught by reading the tree back rather than trusting the run, and the four were DELETED and re-pulled rather than hand-patched. Then the liveness meta-test rejected the guard for reporting 0 scanned; scanned now counts the population POLICED (untrusted utterances, 4) rather than the subset in violation."; }
    verification issuePullPipelineReviewGate : Test { :>> id = "14d6c098-a488-43ef-88e2-d1008888e2a6"; :>> title = "Sprint 501 review gate — three passes per D0172"; :>> createdAt = "2026-08-30"; :>> createdBy = "claudeOpus5"; :>> method = VerificationMethod::inspect; :>> procedureText = "THREE PASSES. (1) DOES THE GUARD ENFORCE THE POLICY OR NARRATE IT: five probes, and two of them are ALLOW cases that must not fire - an unrouted story (untriaged is not misrouted) and a trusted-source story with identical shape. Without the second, the guard would be about the channel rather than about trust and the distinction the design rests on would not exist. (2) CAN IT LOCK OUT LEGITIMATE WORK: no - untrusted input proceeds THROUGH a Decision, and the routed-through-a-decision case asserts it. A guard that blocked untrusted input entirely would be a lockout, not a boundary. (3) DOES IT OVERCLAIM: the guard checks ROUTING, not judgment. It cannot tell whether the plan is any good, and D0264 says so rather than implying the boundary makes the input safe."; }
    verification issuePullPipelineCloseOutGate : Test { :>> id = "550de2af-9459-45c8-a68f-38aef1c8e9ac"; :>> title = "Sprint 501 closeOut gate (autonomous, D0049)"; :>> createdAt = "2026-08-30"; :>> createdBy = "claudeOpus5"; :>> method = VerificationMethod::inspect; :>> procedureText = "CLOSED. 56 guards, 0 violations, 675 tests. The library holds 6 units. The residual is recorded and it bites this project: THIS repository is public, so its own issues - including the human's own - are untrusted by this policy, and --trust trusted is the deliberate override."; }
    verification issuePullPipelineRetroGate : Test { :>> id = "118c32e8-30c7-496c-84d3-4dc1405edf7b"; :>> title = "Sprint 501 retro gate (autonomous, D0049)"; :>> createdAt = "2026-08-30"; :>> createdBy = "claudeOpus5"; :>> method = VerificationMethod::analyze; :>> procedureText = "FINDING: I wired a schema field, built clean, ran live, and the field was never written - the struct had it, the format string did not. Nothing failed; the run printed the right tier and the tree recorded none of it. It was caught by reading the TREE back rather than the command's own report, which is the same discipline that caught the tier-satisfaction number in sprint 483. A command's output is its claim about what it did; the tree is what it did. BECOMES: the four statements were deleted and re-pulled rather than hand-patched, so the records carry the provenance the path actually produces. No new control filed - the existing habit (read the tree, not the report) is what worked, and a guard for 'a struct field that is never emitted' is a compiler feature, not a governance one."; }
}
