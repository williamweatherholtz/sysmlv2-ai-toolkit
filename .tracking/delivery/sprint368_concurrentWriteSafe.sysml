// ProjectDeliveryS368 — Sprint 368: hardening round 8. Four concurrent writes landed two issues, all
// four exiting 0. One model-wide lock; 8 of 8 now land. EXECUTE. 5 pts.
package ProjectDeliveryS368 {
    private import EngineElement::*;
    private import EngineWork::*;
    private import EngineVerification::*;
    private import EngineRelationships::*;

    #CharteredBy dependency from concurrentWriteStory to d0169;

    part concurrentWriteStory : Story {
        :>> id = "0d8006b0-0814-66b0-9b3e-0000003006b0";
        :>> title = "Sprint 368: concurrent writers no longer silently lose facts (5 pts)";
        :>> createdAt = "2026-08-20"; :>> createdBy = "claudeOpus5"; :>> kind = WorkKind::code; :>> priority = WorkPriority::p0; :>> owner = "claudeOpus5"; :>> estimatedPoints = 5;
    }

    action def DeliveryRunS368 {
        action storyConcurrentWrite;
        verification storyConcurrentWriteDoD : Test { :>> id = "0d8006b1-0814-66b1-9b3e-0000003006b1"; :>> method = VerificationMethod::test; :>> procedureText = "DELIVERED BACKLOG ITEMS: dcConcurrentWriteSafe. Clears issue185 under D0169. MEASURED BEFORE: four concurrent `keel record issue` calls landed TWO issues. All four exited 0, the tree validated clean, no temp file was left behind - two recorded facts vanished and nothing said so. Every write is a read-modify-write with no lock and no conflict detection. MEASURED AFTER: eight concurrent writers land 8 of 8, zero duplicate issue numbers, no leftover lock or temp, tree validates clean. ONE MODEL-WIDE LOCK rather than one per file, because `set_attr` and `create_item` SEARCH for the file they will modify - the target is unknown until after the read, so a per-file lock cannot be taken up front. Serialising every writer costs nothing measurable on millisecond text writes and removes the whole class instead of most of it. A writer that cannot acquire the lock FAILS LOUDLY; a stale lock older than twice the retry budget is broken, so a crash is not a permanent outage. validate 400 clean; check-engine clean; 38 guards ALL PASS; 202 tests; clippy clean."; }
        part storyConcurrentWriteDoDR1 : TestResult { :>> id = "0d8006b2-0814-66b2-9b3e-0000003006b2"; :>> outcome = VerdictKind::pass; :>> judgedAgainst = "4233289"; :>> judgedAt = "2026-08-20"; :>> judgedBy = "claudeOpus5"; }
    }

    verification cwRefineGate : Test { :>> id = "0d8006b3-0814-66b3-9b3e-0000003006b3"; :>> title = "Sprint 368 refine gate (DoR)"; :>> createdAt = "2026-08-20"; :>> createdBy = "claudeOpus5"; :>> method = VerificationMethod::inspect; :>> procedureText = "DoR. Pass 8 followed directly from pass 7: making each write ATOMIC guarantees a file is never half-written and says NOTHING about whether it contains both writers' work. Those are two different properties and I had only just fixed the first. The probe was four parallel `record issue` calls against a copy - the cheapest possible experiment, and it failed immediately. NOT THEORETICAL: D0108 and D0129 are explicitly about multi-contributor work, and D0108's rule is that a non-owner ADDS items rather than overwriting - two contributors both obeying that rule at the same moment discarded one contribution. The console's write endpoints make it easier still, since a human clicking accept while a session records an issue IS two writers. estimatedPoints=5."; }
    part cwRefineGateR1 : TestResult { :>> id = "0d8006b4-0814-66b4-9b3e-0000003006b4"; :>> outcome = VerdictKind::pass; :>> judgedAgainst = "4233289"; :>> judgedAt = "2026-08-20"; :>> judgedBy = "claudeOpus5"; }

    verification cwStandupGate : Test { :>> id = "0d8006b5-0814-66b5-9b3e-0000003006b5"; :>> title = "Sprint 368 standup gate"; :>> createdAt = "2026-08-20"; :>> createdBy = "claudeOpus5"; :>> method = VerificationMethod::inspect; :>> procedureText = "Approach: SILENCE is the defect, not slowness. A refused write is recoverable because the caller retries; a lost write with a success exit code is undetectable by anything, and the write API is what D0093 makes the automation substrate. So the fix had to either prevent loss or report it, and preventing it turned out to be cheaper than detecting it. No blockers. ONE TECHNIQUE CHOICE THAT MATTERED: rename-and-wrap - rename `pub fn X` to a private `X_locked` and add a thin public wrapper - rather than editing function bodies. My first attempt wrapped bodies by counting braces and left the file with an unclosed delimiter, so it was reverted."; }
    part cwStandupGateR1 : TestResult { :>> id = "0d8006b6-0814-66b6-9b3e-0000003006b6"; :>> outcome = VerdictKind::pass; :>> judgedAgainst = "4233289"; :>> judgedAt = "2026-08-20"; :>> judgedBy = "claudeOpus5"; }

    verification cwImplementGate : Test { :>> id = "0d8006b7-0814-66b7-9b3e-0000003006b7"; :>> title = "Sprint 368 implement gate"; :>> createdAt = "2026-08-20"; :>> createdBy = "claudeOpus5"; :>> method = VerificationMethod::test; :>> procedureText = "THE CONTROL FOUND FIVE MORE UNLOCKED ENTRY POINTS THAN I HAD FIXED - set_attr, add_task, create_item, accept_decision, reject_decision - which is the THIRD sprint running where a text-level control out-performed my reading. The pattern is now unambiguous: I fix the sites I can see, and the control finds the rest. Writing the control BEFORE believing the fix is complete is the only version of this that works. A CONCURRENCY TEST WOULD BE FLAKY, so the control pins STRUCTURE instead: a `pub fn` that reads the file it is about to rewrite has not taken the lock, because a wrapped one delegates to a private `*_locked` sibling and does no reading itself. That property is exact, cheap, and cannot pass by luck. TWO ENTRY POINTS FORCED THE DESIGN. `set_attr` iterates every tracking file looking for its item and `create_item` derives its target, so neither knows the path before reading - which is what turned a per-file lock into ONE MODEL-WIDE lock. That is a coarser lock than strictly needed and it is the honest answer: for millisecond text writes the cost is unmeasurable, and a partial fix that covers seven of nine entry points would have left the class open while looking closed. THE LOCK FILES ARE GITIGNORED, because `git add -A` is the standing instruction here and a crashed writer's lock would otherwise be COMMITTED and then block every clone that pulled it."; }
    part cwImplementGateR1 : TestResult { :>> id = "0d8006b8-0814-66b8-9b3e-0000003006b8"; :>> outcome = VerdictKind::pass; :>> judgedAgainst = "4233289"; :>> judgedAt = "2026-08-20"; :>> judgedBy = "claudeOpus5"; }

    verification cwReviewGate : Test { :>> id = "0d8006b9-0814-66b9-9b3e-0000003006b9"; :>> title = "Sprint 368 review gate"; :>> createdAt = "2026-08-20"; :>> createdBy = "claudeOpus5"; :>> method = VerificationMethod::inspect; :>> procedureText = "Reviewed. WHAT A REVIEWER SHOULD ATTACK: the stale-lock takeover. A lock older than twice the retry budget - four seconds - is assumed dead and broken. That is a heuristic about elapsed time, which is the same shape as the TTL I refused in D0167 on the grounds that nothing should expire on a clock. The difference I would argue: D0167's memo was about CORRECTNESS of a cached answer, where a clock can make you serve stale truth, whereas this is about LIVENESS, where the alternative to a clock is a crash becoming a permanent outage. A reviewer may reasonably say I have talked myself into a timer twice with different words. WHAT I WOULD DEFEND: failing loudly on lock contention rather than blocking forever. And the model-wide lock over a clever per-file scheme - two of nine entry points cannot know their file before reading, so any per-file scheme is incomplete by construction and would have looked complete. THE SERIES SCORE: 15 findings across eight passes, 15 cleared, and four of the eight passes found a defect in code written during the series."; }
    part cwReviewGateR1 : TestResult { :>> id = "0d8006ba-0814-66ba-9b3e-0000003006ba"; :>> outcome = VerdictKind::pass; :>> judgedAgainst = "4233289"; :>> judgedAt = "2026-08-20"; :>> judgedBy = "claudeOpus5"; }

    verification cwCloseOutGate : Test { :>> id = "0d8006bb-0814-66bb-9b3e-0000003006bb"; :>> title = "Sprint 368 closeOut gate (autonomous, D0049)"; :>> createdAt = "2026-08-20"; :>> createdBy = "claudeOpus5"; :>> method = VerificationMethod::inspect; :>> procedureText = "Autonomous closeOut (D0049). issue185 cleared: 8 of 8 concurrent writers land, was 2 of 4. All nine public write entry points are under the lock, verified structurally. Doc-sync: CLAUDE.md gains the atomic-and-mutually-exclusive bullet; .gitignore covers the lock and temp files. Eight passes: 15 findings recorded, 15 cleared, 12 permanent controls. validate 400 clean; check-engine clean; 38 guards ALL PASS; 202 tests; clippy clean."; }
    part cwCloseOutGateR1 : TestResult { :>> id = "0d8006bc-0814-66bc-9b3e-0000003006bc"; :>> outcome = VerdictKind::pass; :>> judgedAgainst = "4233289"; :>> judgedAt = "2026-08-20"; :>> judgedBy = "claudeOpus5"; }

    verification cwRetroGate : Test { :>> id = "0d8006bd-0814-66bd-9b3e-0000003006bd"; :>> title = "Sprint 368 retro gate (autonomous, D0049)"; :>> createdAt = "2026-08-20"; :>> createdBy = "claudeOpus5"; :>> method = VerificationMethod::analyze; :>> procedureText = "Autonomous retro (D0049) under D0131's retroTrack. WELL: (1) the probe was four parallel commands and a grep - the cheapest experiment available, run before any theorising; (2) the control was written before I believed the fix was complete, and found five more entry points; (3) rename-and-wrap replaced brace-counting after the first attempt corrupted the file, and the corrupted attempt was REVERTED rather than patched forward; (4) the model-wide lock was chosen because a per-file scheme is incomplete by construction here, and the reasoning is recorded rather than the conclusion alone; (5) the .gitignore entry was added because `git add -A` would otherwise commit a crashed writer's lock - a second-order consequence I have now been bitten by once this session already, with the `--help` directory. AVOIDABLE-ISSUE: my first fix attempt wrapped function bodies by counting braces and left write.rs with an unclosed delimiter. Mechanical source surgery that has to BALANCE something is the wrong tool; renaming a declaration and adding a wrapper never has to. SECOND AVOIDABLE-ISSUE, and it is a judgment a reviewer may reject: I refused a TTL in D0167 on the principle that nothing expires on a clock, and this lock breaks a stale holder after four seconds. I believe liveness and correctness are different cases and the review gate argues why, but I have now reached for elapsed time twice while claiming not to. Estimate 5 pts, delivered."; }
    part cwRetroGateR1 : TestResult { :>> id = "0d8006be-0814-66be-9b3e-0000003006be"; :>> outcome = VerdictKind::pass; :>> judgedAgainst = "4233289"; :>> judgedAt = "2026-08-20"; :>> judgedBy = "claudeOpus5"; }
}
