// ProjectDeliveryS651 — Sprint 651: Deliver dcMethodVocabularyIsTheSchemas (issue451, GH#70 / st117 / us108): `keel add-task --method` accepts exactly the members VerificationMethod declares. The CLI carried a hand-written list (test, inspect, confirmation, demo, analysis) beside the schema's (inspect, analyze, demo, test, confirmation, critique), so it wrote a member validate refused and refused two validate accepts - the adopter met it at their own terminal on 0.3.1. Chartered by D0054 (authoring friction is the #1 risk): a write path that emits what the authority rejects is friction the tool made.. EXECUTE. 1 pts.
package ProjectDeliveryS651 {
    private import EngineElement::*;
    private import EngineWork::*;
    private import EngineVerification::*;
    private import EngineRelationships::*;

    #CharteredBy dependency from methodVocabularyIsTheSchemasStory to d0054;

    part methodVocabularyIsTheSchemasStory : Story {
        :>> id = "d97cbc45-a30e-47f6-bfc1-9b65df735899";
        :>> title = "Sprint 651: Deliver dcMethodVocabularyIsTheSchemas (issue451, GH#70 / st117 / us108): `keel add-task --method` accepts exactly the members VerificationMethod declares. The CLI carried a hand-written list (test, inspect, confirmation, demo, analysis) beside the schema's (inspect, analyze, demo, test, confirmation, critique), so it wrote a member validate refused and refused two validate accepts - the adopter met it at their own terminal on 0.3.1. Chartered by D0054 (authoring friction is the #1 risk): a write path that emits what the authority rejects is friction the tool made. (1 pts)";
        :>> createdAt = "2026-09-10"; :>> createdBy = "claudeOpus5"; :>> kind = WorkKind::code; :>> priority = WorkPriority::p0; :>> owner = "claudeOpus5"; :>> estimatedPoints = 1;
    }

    action def DeliveryRunS651 {
        action storyMethodVocabularyIsTheSchemas;
        verification storyMethodVocabularyIsTheSchemasDoD : Test { :>> id = "aca8e7e5-00a2-4995-9958-fcbb3522c9ec"; :>> method = VerificationMethod::test; :>> procedureText = "The dcMethodVocabularyIsTheSchemasDoD text at HEAD. VERIFY (probe pair): the unit test add_task_accepts_exactly_the_schemas_verification_methods in keel-cli/src/write.rs adds a task per schema-declared member and reads each back as `method = VerificationMethod::<member>;`, then refuses `analysis` with the file unchanged and the refusal naming every accepted member; the live CLI probe on the built binary accepts `--method analyze` (exit 0, the member written) and refuses `--method analysis` (exit 1, `expected one of inspect | analyze | demo | test | confirmation | critique`); no literal VerificationMethod member list remains in keel-cli/src outside the schema; usage.md names the flag's members from the schema; clippy clean."; }
        // RAN: cargo test --release -p keel-cli --lib -- add_task - test result: ok. 1 passed; 0 failed; cargo test --release -p keel-cli --lib -- write:: - test result: ok. 27 passed; 0 failed; cargo test --release -p keel-cli --lib -- intake_write - test result: ok. 4 passed; 0 failed; clippy 0 warnings; keel validate . - 741 tracking file(s) validated clean; live probe add-task --method analyze exit=0, --method analysis exit=1
        part storyMethodVocabularyIsTheSchemasDoDR1 : TestResult { :>> id = "d973024e-edde-4eac-99ed-3a6f0d8f1381"; :>> outcome = VerdictKind::pass; :>> judgedAgainst = "8adda1d"; :>> judgedAt = "2026-09-10"; :>> judgedBy = "claudeOpus5"; }
    }

    verification methodVocabularyIsTheSchemasRefineGate : Test { :>> id = "a25b9970-099c-4722-b673-78967feb2c03"; :>> title = "Sprint 651 refine gate (DoR)"; :>> createdAt = "2026-09-10"; :>> createdBy = "claudeOpus5"; :>> method = VerificationMethod::inspect; :>> procedureText = "Scope: write.rs (add_task_locked reads the accepted set through enum_members_union when the file sits in a model tree - the write-path rule intake_write already applies to its vocabularies - and the embedded schema otherwise; WriteError::InvalidMethod carries the accepted set so the refusal names it, the same shape intake_write's check_member used inline), intake_write.rs (its InvalidMethod site passes the set instead of formatting it), the new probe-pair test beside the other add-task tests, .engine/docs/usage.md doc-sync. Priority: the resolver was declared ahead of dcModelParsesInParallel because a shipped-release defect an adopter met outranks a performance item; `keel show priority` reads no inversion after the move. 1 point (a vocabulary read from the schema, one test, one doc line)."; }
    part methodVocabularyIsTheSchemasRefineGateR1 : TestResult { :>> id = "a09f7201-6c0e-47e2-a765-54ee32cc7c4d"; :>> outcome = VerdictKind::pass; :>> judgedAgainst = "8adda1d"; :>> judgedAt = "2026-09-10"; :>> judgedBy = "claudeOpus5"; }
    verification methodVocabularyIsTheSchemasStandupGate : Test { :>> id = "7fa15907-8246-4484-9bb0-6a2be17d4e4f"; :>> title = "Sprint 651 standup gate"; :>> createdAt = "2026-09-10"; :>> createdBy = "claudeOpus5"; :>> method = VerificationMethod::inspect; :>> procedureText = "Blockers: none. intake_write.rs is CRLF on disk, so the first textpatch anchor (LF) was refused and nothing was written - re-run with the file's own line endings. clippy asked for map_or_else and a dropped clone; both applied before the verifier ran."; }
    part methodVocabularyIsTheSchemasStandupGateR1 : TestResult { :>> id = "36e72061-4fa1-4298-b478-6c647deeb8a8"; :>> outcome = VerdictKind::pass; :>> judgedAgainst = "8adda1d"; :>> judgedAt = "2026-09-10"; :>> judgedBy = "claudeOpus5"; }
    verification methodVocabularyIsTheSchemasImplementGate : Test { :>> id = "9e4f2c93-cfd4-4c51-ad35-13d5398902ed"; :>> title = "Sprint 651 implement gate"; :>> createdAt = "2026-09-10"; :>> createdBy = "claudeOpus5"; :>> method = VerificationMethod::test; :>> procedureText = "keel-cli/src/write.rs (add_task_locked's accepted set from the schema, InvalidMethod(String, Vec<String>) and its Display, the test add_task_accepts_exactly_the_schemas_verification_methods), keel-cli/src/intake_write.rs (check_member constructs the two-field variant), .engine/docs/usage.md line 96."; }
    // RAN: cargo test --release -p keel-cli --lib -- add_task - test result: ok. 1 passed; 0 failed; cargo test --release -p keel-cli --lib -- write:: - test result: ok. 27 passed; 0 failed; cargo test --release -p keel-cli --lib -- intake_write - test result: ok. 4 passed; 0 failed; clippy 0 warnings; keel validate . - 741 tracking file(s) validated clean; live probe add-task --method analyze exit=0, --method analysis exit=1
    part methodVocabularyIsTheSchemasImplementGateR1 : TestResult { :>> id = "8b28e9e0-1490-4c91-92bd-1b8d64c8d4d4"; :>> outcome = VerdictKind::pass; :>> judgedAgainst = "8adda1d"; :>> judgedAt = "2026-09-10"; :>> judgedBy = "claudeOpus5"; }
    verification methodVocabularyIsTheSchemasReviewGate : Test { :>> id = "812c91be-f95d-4e30-990a-ad6d82d3fdfe"; :>> title = "Sprint 651 review gate — three passes per D0172"; :>> createdAt = "2026-09-10"; :>> createdBy = "claudeOpus5"; :>> method = VerificationMethod::inspect; :>> procedureText = "Three passes (D0172). Correctness: the accepted set is computed before the file is parsed, so a refused method touches nothing - the test asserts byte-for-byte equality after the refusal. Scope: serve.rs's add_task call passes the literal 'inspect', a schema member, and is unchanged; write_bdd's add_task step passes the method through and its features name only schema members (grep). Evidence: the live probe on the built binary wrote VerificationMethod::analyze once and refused analysis naming six members - the exact pair GH#70 reported inverted."; }
    part methodVocabularyIsTheSchemasReviewGateR1 : TestResult { :>> id = "306f47cd-33ff-4d39-aa06-d54af201a476"; :>> outcome = VerdictKind::pass; :>> judgedAgainst = "8adda1d"; :>> judgedAt = "2026-09-10"; :>> judgedBy = "claudeOpus5"; }
    verification methodVocabularyIsTheSchemasCloseOutGate : Test { :>> id = "6e7334ae-db11-4d06-b695-c179c7709524"; :>> title = "Sprint 651 closeOut gate (autonomous, D0049)"; :>> createdAt = "2026-09-10"; :>> createdBy = "claudeOpus5"; :>> method = VerificationMethod::inspect; :>> procedureText = "Recorded by the RECORDER subagent from the verifier's receipt (D0425); the primary wrote no ceremony result."; }
    part methodVocabularyIsTheSchemasCloseOutGateR1 : TestResult { :>> id = "babbc903-b2f0-44ca-9a9f-bc36b86abecb"; :>> outcome = VerdictKind::pass; :>> judgedAgainst = "8adda1d"; :>> judgedAt = "2026-09-10"; :>> judgedBy = "claudeOpus5"; }
    verification methodVocabularyIsTheSchemasRetroGate : Test { :>> id = "d19e10b9-7e72-431e-986b-33f96467e23e"; :>> title = "Sprint 651 retro gate (autonomous, D0049)"; :>> createdAt = "2026-09-10"; :>> createdBy = "claudeOpus5"; :>> method = VerificationMethod::analyze; :>> procedureText = "Avoidable-issue scan: the intake write path had already been fixed for the SAME class (issue300: a hand-maintained list beside a schema enum sat at 12 against 15) and grew a test that walks the schema's members; add-task's list was left as it was because nothing enumerates the write paths that validate against an enum. That is the recurrence pattern D0047 names - a fix applied at one site of a class. The control this retro asks for is a test that finds every `enum_members`/`enum_members_union`-free literal vocabulary in keel-cli/src that names a schema enum's members, so the third copy cannot appear silently - recorded as issue452 (in-field, Medium) with resolver dcLiteralVocabulariesAreFoundByATest added to the backlog in this commit, not as prose here."; }
    part methodVocabularyIsTheSchemasRetroGateR1 : TestResult { :>> id = "2005af0c-77a0-40d5-977d-493e23691700"; :>> outcome = VerdictKind::pass; :>> judgedAgainst = "8adda1d"; :>> judgedAt = "2026-09-10"; :>> judgedBy = "claudeOpus5"; }
}
