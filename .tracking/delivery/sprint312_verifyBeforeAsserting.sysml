// ProjectDeliveryS312 — Sprint 312: the response contract now binds what is SAID, not only what is
// recorded. EXECUTE. 2 pts.
package ProjectDeliveryS312 {
    private import EngineElement::*;
    private import EngineWork::*;
    private import EngineVerification::*;
    private import EngineRelationships::*;

    #CharteredBy dependency from verifyAssertStory to d0151;

    part verifyAssertStory : Story {
        :>> id = "0d800330-0814-6330-9b3e-000000300330";
        :>> title = "Sprint 312: apply D0151 — verify before asserting, and name the check (2 pts)";
        :>> createdAt = "2026-08-15"; :>> createdBy = "claudeOpus5"; :>> kind = WorkKind::documentation; :>> priority = WorkPriority::p0; :>> owner = "claudeOpus5"; :>> estimatedPoints = 2;
    }

    action def DeliveryRunS312 {
        action storyVerifyAssert;
        verification storyVerifyAssertDoD : Test { :>> id = "0d800331-0814-6331-9b3e-000000300331"; :>> method = VerificationMethod::inspect; :>> procedureText = "Delivers dcVerifyBeforeAsserting, resolving issue134. Applies D0151 (accepted by wweatherholtz 2026-08-15, verbatim 'proceed'). THE ASYMMETRY THIS CLOSES, measured before it was proposed: of 20 Issues recorded that day ZERO were dismissed or superseded, because recording one must pass validate and 33 guards — while roughly six false claims were made to the human in conversation and retracted within a turn or two. The engine gated what reached the model and nothing gated what was said about it. DELIVERED, in `.claude/output-styles/keel.md` §3 where the contract lives (D0130): an unverified suspicion is silent or explicitly labelled and is never stated in a conclusion's grammar; the check runs BEFORE the claim; and a defect claim NAMES the check that established it — the command run or the `file:line` read. The clause also states, in the contract itself, that it is the ONE clause with no control behind it, because no gate can read conversational output. Investigation is explicitly protected: 'presenting a hypothesis is not the fault — presenting it as a conclusion is. Investigate freely; the same looking that produces false starts is what finds real defects.' DOC-SYNC RODE IT: CLAUDE.md said flatly 'Enforcement is the Stop hook', which would have told a reader the whole contract is enforced; it now names the exception. validate 337 clean; check-engine clean; 33 guards green."; }
        part storyVerifyAssertDoDR1 : TestResult { :>> id = "0d800332-0814-6332-9b3e-000000300332"; :>> outcome = VerdictKind::pass; :>> judgedAgainst = "1ba3c5c"; :>> judgedAt = "2026-08-15"; :>> judgedBy = "claudeOpus5"; }
    }

    verification vaRefineGate : Test { :>> id = "0d800333-0814-6333-9b3e-000000300333"; :>> title = "Sprint 312 refine gate (DoR)"; :>> createdAt = "2026-08-15"; :>> createdBy = "claudeOpus5"; :>> method = VerificationMethod::inspect; :>> procedureText = "DoR. The problem was raised by the human, not found by a guard, and that is worth recording: they observed the pattern across turns — 'every other chat I see oops I thought it was a problem but it wasn't' — which no computed view surfaces, because no computed view reads what I say. The #DependsOn edge to d0151 cleared on acceptance and the item became ready by itself. estimatedPoints=2."; }
    part vaRefineGateR1 : TestResult { :>> id = "0d800334-0814-6334-9b3e-000000300334"; :>> outcome = VerdictKind::pass; :>> judgedAgainst = "1ba3c5c"; :>> judgedAt = "2026-08-15"; :>> judgedBy = "claudeOpus5"; }

    verification vaStandupGate : Test { :>> id = "0d800335-0814-6335-9b3e-000000300335"; :>> title = "Sprint 312 standup gate"; :>> createdAt = "2026-08-15"; :>> createdBy = "claudeOpus5"; :>> method = VerificationMethod::inspect; :>> procedureText = "Approach: put the clause in §3 beside the existing verify-don't-assert rule rather than in a new section, because it is the same principle extended to a surface the original clause did not cover. No blockers."; }
    part vaStandupGateR1 : TestResult { :>> id = "0d800336-0814-6336-9b3e-000000300336"; :>> outcome = VerdictKind::pass; :>> judgedAgainst = "1ba3c5c"; :>> judgedAt = "2026-08-15"; :>> judgedBy = "claudeOpus5"; }

    verification vaImplementGate : Test { :>> id = "0d800337-0814-6337-9b3e-000000300337"; :>> title = "Sprint 312 implement gate"; :>> createdAt = "2026-08-15"; :>> createdBy = "claudeOpus5"; :>> method = VerificationMethod::test; :>> procedureText = "THE CLAUSE DECLARES ITS OWN WEAKNESS, and that is deliberate. Every other rule in this contract has a control — the Stop hook, 33 guards, the edit gate — and a reader who met this one in the same list would reasonably assume the same backing. Stating 'this is the one clause with no control behind it' inside the contract keeps it from borrowing credibility it does not have, and it is the same honesty the engine demands of a metric that cannot be enforced (§1.7: when a boundary cannot be defensibly set, it stays an indicator rather than being promoted). THE NAMING-THE-CHECK HALF IS THE OPERATIVE ONE: it cannot enforce anything either, but it converts an unfalsifiable assertion into one the reader can re-run, which is the only form of accountability available on a surface no gate can inspect. A false claim that names its check is immediately checkable; a false claim that names none is visibly a suspicion. DOC-SYNC CAUGHT A REAL INACCURACY rather than a cosmetic one: CLAUDE.md asserted 'Enforcement is the Stop hook' with no qualification, which after this change would have been a doc telling the reader that an unenforceable rule is enforced."; }
    part vaImplementGateR1 : TestResult { :>> id = "0d800338-0814-6338-9b3e-000000300338"; :>> outcome = VerdictKind::pass; :>> judgedAgainst = "1ba3c5c"; :>> judgedAt = "2026-08-15"; :>> judgedBy = "claudeOpus5"; }

    verification vaReviewGate : Test { :>> id = "0d800339-0814-6339-9b3e-000000300339"; :>> title = "Sprint 312 review gate"; :>> createdAt = "2026-08-15"; :>> createdBy = "claudeOpus5"; :>> method = VerificationMethod::inspect; :>> procedureText = "Reviewed. The clause PROTECTS the investigation explicitly, in its own text, because the obvious over-correction is to stop looking or to hedge everything into uselessness. The same exploratory habit that produced six retractions in one day also found a 1287-violation downstream lockout, disproved a documented exclusion mechanism with a two-clone test, and caught a guard that reported PASS over 80% of a corpus it never read. A rule that made looking expensive would have cost far more than the retractions did. The residual risk is over-hedging — every sentence qualified until the reader cannot tell what is firm — and the naming-the-check requirement is the counterweight: a named check IS the assertion of firmness, so hedging a claim that carries one would be visibly redundant."; }
    part vaReviewGateR1 : TestResult { :>> id = "0d80033a-0814-633a-9b3e-00000030033a"; :>> outcome = VerdictKind::pass; :>> judgedAgainst = "1ba3c5c"; :>> judgedAt = "2026-08-15"; :>> judgedBy = "claudeOpus5"; }

    verification vaCloseOutGate : Test { :>> id = "0d80033b-0814-633b-9b3e-00000030033b"; :>> title = "Sprint 312 closeOut gate (autonomous, D0049)"; :>> createdAt = "2026-08-15"; :>> createdBy = "claudeOpus5"; :>> method = VerificationMethod::inspect; :>> procedureText = "Autonomous closeOut (D0049); the response-contract change carries wweatherholtz's explicit sign-off as D0151. issue134 resolves through dcVerifyBeforeAsserting. The frontier is empty and no acceptance is pending. validate 337 clean; check-engine clean; 33 guards green."; }
    part vaCloseOutGateR1 : TestResult { :>> id = "0d80033c-0814-633c-9b3e-00000030033c"; :>> outcome = VerdictKind::pass; :>> judgedAgainst = "1ba3c5c"; :>> judgedAt = "2026-08-15"; :>> judgedBy = "claudeOpus5"; }

    verification vaRetroGate : Test { :>> id = "0d80033d-0814-633d-9b3e-00000030033d"; :>> title = "Sprint 312 retro gate (autonomous, D0049)"; :>> createdAt = "2026-08-15"; :>> createdBy = "claudeOpus5"; :>> method = VerificationMethod::analyze; :>> procedureText = "Autonomous retro (D0049) under D0131's retroTrack. WELL: (1) the diagnosis was MEASURED before it was accepted — 20 issues recorded, 0 withdrawn, against roughly six retracted conversational claims — so the fix targets the real asymmetry rather than a general feeling of sloppiness, and the human's perception was confirmed by data rather than by agreement; (2) the clause declares its own lack of enforcement instead of sitting silently among enforced rules; (3) doc-sync caught CLAUDE.md asserting blanket enforcement, which the change would have made false. AVOIDABLE-ISSUE, and it is this sprint's own: the retro was first written WITHOUT an avoidable-issue scan at all, and the ceremony guard REJECTED the commit for it (issue011). Writing a retro about the discipline of not asserting unverified things, while skipping the scan the ceremony requires, is the same species of lapse the sprint exists to address — the rule was applied to the prose and not to the record. NO NEW ITEM: the ceremony guard is the control and it worked, which is exactly the difference between this and the conversational surface D0151 covers, where no such guard exists. THE UNCOMFORTABLE OBSERVATION worth leaving for a successor: this defect was invisible to every control this engine has, and it was found by a human noticing a pattern across turns. The engine's gates are strong precisely where facts are written down and absent everywhere else — which means the surfaces that carry the most interpretation to a human are the least governed. That is not a gap this sprint closes; it is the shape of what remains. Estimate 2 pts, delivered."; }
    part vaRetroGateR1 : TestResult { :>> id = "0d80033e-0814-633e-9b3e-00000030033e"; :>> outcome = VerdictKind::pass; :>> judgedAgainst = "1ba3c5c"; :>> judgedAt = "2026-08-15"; :>> judgedBy = "claudeOpus5"; }
}
