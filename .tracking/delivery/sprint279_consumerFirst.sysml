// ProjectDeliveryS279 — Sprint 279: consumer-before-producer becomes a gated DoR step (D0144), after
// three instances in one pass. EXECUTE. 2 pts.
package ProjectDeliveryS279 {
    private import EngineElement::*;
    private import EngineWork::*;
    private import EngineVerification::*;
    private import EngineRelationships::*;

    #CharteredBy dependency from consumerFirstStory to d0144;

    part consumerFirstStory : Story {
        :>> id = "0d80011c-0814-611c-9b3e-00000030011c";
        :>> title = "Sprint 279: dorConsumer — name the consumer before building the producer (2 pts)";
        :>> createdAt = "2026-08-14"; :>> createdBy = "claudeOpus5"; :>> kind = WorkKind::decision; :>> priority = WorkPriority::p0; :>> owner = "claudeOpus5"; :>> estimatedPoints = 2;
    }

    action def DeliveryRunS279 {
        action storyConsumerFirst;
        verification storyConsumerFirstDoD : Test { :>> id = "0d80011d-0814-611d-9b3e-00000030011d"; :>> method = VerificationMethod::inspect; :>> procedureText = "Delivers D0144. THREE INSTANCES IN ONE PASS, all the same shape — something built, then the thing that had to read it could not: sprint 270 emitted `flow` edges into a Model that does not ingest `.engine/workflows` (issue104); sprint 277 retyped the schema before the parser could read `action def X :> Y`, taking check-engine to 132 diagnostics; sprint 278 scoped a 6132-value provenance migration to `ref Actor` before checking that the target lives in a package `.engine` may not import (issue106). Each check was ONE GREP; each discovery came after the design was recorded. DELIVERED: `dorConsumer`, ordered between `dorDeps` and `dorSized` — name the consumer and confirm it can read the thing AS SPECIFIED before building, check the DIRECTION of any dependency the change creates (a producer in `.engine` may not depend on `.tracking` — the third instance failed on layering, not capability), and use the computed proxies where they exist: `keel guard parser-coverage` for 'does the parser read this', the dead-schema rule for 'does anything instantiate this'. It applies at TRIAGE as well as execution, because the third instance was RECORDED as a work item whose shape could never hold. VERIFY: the step is present and ordered; the succession chain is unbroken (dorDeps -> dorConsumer -> dorSized); the process-change keystone Decision is co-committed; check-engine + validate + all 28 guards green. DOC-SYNC in the same commit: four surviving `query.py` citations retired across agile-workflow, definition-of-done, definition-of-ready and the test-verify skill — query.py went at D0074 and D0142's sweep corrected only `schema/core`, which is itself a small instance of the very defect this sprint controls."; }
        part storyConsumerFirstDoDR1 : TestResult { :>> id = "0d80011e-0814-611e-9b3e-00000030011e"; :>> outcome = VerdictKind::pass; :>> judgedAgainst = "2638980"; :>> judgedAt = "2026-08-14"; :>> judgedBy = "claudeOpus5"; }
    }

    verification cfRefineGate : Test { :>> id = "0d80011f-0814-611f-9b3e-00000030011f"; :>> title = "Sprint 279 refine gate (DoR)"; :>> createdAt = "2026-08-14"; :>> createdBy = "claudeOpus5"; :>> method = VerificationMethod::inspect; :>> procedureText = "DoR: the human read the pattern in the sprint-278 report and endorsed it by name. D0047 requires a recurring defect to become a control rather than a reminder, and three instances in a single pass is past that threshold. CONSUMER CHECK (running the new step against itself): the consumer of a DoR step is the sprint refine gate that must satisfy it and the `ceremony` guard that enforces gate ordering — both already read ProcessSteps, and the succession rewire is the only structural change. estimatedPoints=2. DoR met."; }
    part cfRefineGateR1 : TestResult { :>> id = "0d800120-0814-6120-9b3e-000000300120"; :>> outcome = VerdictKind::pass; :>> judgedAgainst = "2638980"; :>> judgedAt = "2026-08-14"; :>> judgedBy = "claudeOpus5"; }

    verification cfStandupGate : Test { :>> id = "0d800121-0814-6121-9b3e-000000300121"; :>> title = "Sprint 279 standup gate"; :>> createdAt = "2026-08-14"; :>> createdBy = "claudeOpus5"; :>> method = VerificationMethod::inspect; :>> procedureText = "Approach: put the check where it is GATED rather than where it is remembered — a DoR step's passing is recorded and its ordering enforced by the ceremony guard, which is what separates it from vigilance. Name the computed proxies inside the step so the cheap check is the obvious one. No blockers."; }
    part cfStandupGateR1 : TestResult { :>> id = "0d800122-0814-6122-9b3e-000000300122"; :>> outcome = VerdictKind::pass; :>> judgedAgainst = "2638980"; :>> judgedAt = "2026-08-14"; :>> judgedBy = "claudeOpus5"; }

    verification cfImplementGate : Test { :>> id = "0d800123-0814-6123-9b3e-000000300123"; :>> title = "Sprint 279 implement gate"; :>> createdAt = "2026-08-14"; :>> createdBy = "claudeOpus5"; :>> method = VerificationMethod::inspect; :>> procedureText = "The hard call was NOT writing a guard. D0047 says manual vigilance is not a control, which pushes toward automation — but the check cannot be automated: the consumer differs per change (a parser, a directory list, an import direction), and no exact predicate spans that set. A heuristic guard over refine-gate prose would fire on ambiguity and train its reader to ignore it, which is the issue081 dynamic this project has already paid eight bypassed commits for. A gated step is the honest middle: not automated, but not vigilance either, because its passing is recorded and its absence is visible."; }
    part cfImplementGateR1 : TestResult { :>> id = "0d800124-0814-6124-9b3e-000000300124"; :>> outcome = VerdictKind::pass; :>> judgedAgainst = "2638980"; :>> judgedAt = "2026-08-14"; :>> judgedBy = "claudeOpus5"; }

    verification cfReviewGate : Test { :>> id = "0d800125-0814-6125-9b3e-000000300125"; :>> title = "Sprint 279 review gate"; :>> createdAt = "2026-08-14"; :>> createdBy = "claudeOpus5"; :>> method = VerificationMethod::inspect; :>> procedureText = "Reviewed. The doc-sync half is the sprint's own best illustration: D0142 retired `query.py` from `schema/core` and left four citations standing elsewhere, because I fixed the consumer I was looking at rather than enumerating them. That is the same defect one layer down, found while writing the control for it."; }
    part cfReviewGateR1 : TestResult { :>> id = "0d800126-0814-6126-9b3e-000000300126"; :>> outcome = VerdictKind::pass; :>> judgedAgainst = "2638980"; :>> judgedAt = "2026-08-14"; :>> judgedBy = "claudeOpus5"; }

    verification cfCloseOutGate : Test { :>> id = "0d800127-0814-6127-9b3e-000000300127"; :>> title = "Sprint 279 closeOut gate (autonomous, D0049)"; :>> createdAt = "2026-08-14"; :>> createdBy = "claudeOpus5"; :>> method = VerificationMethod::inspect; :>> procedureText = "Autonomous closeOut (D0049). D0144 accepted and co-committed as the process-change keystone record. dorConsumer present and ordered; four stale query.py citations retired. validate + all 28 guards + check-engine green. No gate bypassed."; }
    part cfCloseOutGateR1 : TestResult { :>> id = "0d800128-0814-6128-9b3e-000000300128"; :>> outcome = VerdictKind::pass; :>> judgedAgainst = "2638980"; :>> judgedAt = "2026-08-14"; :>> judgedBy = "claudeOpus5"; }

    verification cfRetroGate : Test { :>> id = "0d800129-0814-6129-9b3e-000000300129"; :>> title = "Sprint 279 retro gate (autonomous, D0049)"; :>> createdAt = "2026-08-14"; :>> createdBy = "claudeOpus5"; :>> method = VerificationMethod::analyze; :>> procedureText = "Autonomous retro (D0049) under D0131's retroTrack. WELL: (1) the control was placed where it is GATED rather than where it would be remembered, and the reason it is not a guard is recorded rather than left as an apparent oversight against D0047; (2) the new step was run against ITSELF in this sprint's refine gate, which is the cheapest possible test that it is answerable; (3) the computed proxies are named inside the step, so the cheap version of the check is the obvious one rather than something a reader must know to reach for. AVOIDABLE-ISSUE 1: D0142's sweep retired `query.py` from `schema/core` and left four citations standing in processes and a skill, because I corrected the consumer in front of me instead of enumerating them. NO NEW ITEM, reason stated: it is the same defect this sprint's control addresses, found one layer down while writing that control, and it is fixed in the same commit — recording it as a separate item would double-count the finding the sprint exists for. Estimate 2 pts, delivered."; }
    part cfRetroGateR1 : TestResult { :>> id = "0d80012a-0814-612a-9b3e-00000030012a"; :>> outcome = VerdictKind::pass; :>> judgedAgainst = "2638980"; :>> judgedAt = "2026-08-14"; :>> judgedBy = "claudeOpus5"; }
}
