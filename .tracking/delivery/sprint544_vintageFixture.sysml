// ProjectDeliveryS544 — Sprint 544: adoption-check gates units against a real prior release too, and every guard has its constraint-def identity. EXECUTE. 3 pts.
package ProjectDeliveryS544 {
    private import EngineElement::*;
    private import EngineWork::*;
    private import EngineVerification::*;
    private import EngineRelationships::*;

    #CharteredBy dependency from vintageFixtureStory to d0302;

    part vintageFixtureStory : Story {
        :>> id = "d0726f03-57a3-4a03-b195-890bb0afa6c9";
        :>> title = "Sprint 544: adoption-check gates units against a real prior release too, and every guard has its constraint-def identity (3 pts)";
        :>> createdAt = "2026-09-04"; :>> createdBy = "claudeOpus5"; :>> kind = WorkKind::code; :>> priority = WorkPriority::p0; :>> owner = "claudeOpus5"; :>> estimatedPoints = 3;
    }

    action def DeliveryRunS544 {
        action storyVintageFixture;
        verification storyVintageFixtureDoD : Test { :>> id = "18cf788e-196c-4610-bb81-2c36e5c1ae60"; :>> method = VerificationMethod::test; :>> procedureText = "DELIVERED BACKLOG ITEMS: dcVintageFixture (resolves issue265; issue370 found and resolved on the way). DONE: adoption-check --vintage VERSION fetches that release's binary (keelw cache, curl from the release origin, KEELW_BASE_URL honoured, version proved, KEEL_OFFLINE refuses with the reason), scaffolds a second fixture with it, strips and imports each current export into it and gates it with the OLD binary, and reports CURRENT and VINTAGE as two tables that never merge; both loops sync-claude between import and gate; the failure tail prefers ERROR and FAIL lines; twelve guards gain constraint defs and a test holds GUARD_NAMES equal to the defs. VERIFY: the live issue263 probe - intake asserting unitExtrasPresent - CURRENT clean, VINTAGE v0.3.0 refused at import by the K8 handshake naming the guard; removed, both clean; v0.2.3 reports no importer per unit; offline unit test; 479 tests; clippy clean."; }
        // RAN: adoption-check --vintage 0.3.0 --unit intake x4 probes (see the implement gate); cargo test --release 479/0; clippy 0; keel new sprint 544 --fill wrote this record with zero results
        part storyVintageFixtureDoDR1 : TestResult { :>> id = "e2ea3d70-7abf-43cd-9f6e-3620b05a048a"; :>> outcome = VerdictKind::pass; :>> judgedAgainst = "284bac7"; :>> judgedAt = "2026-09-04"; :>> judgedBy = "claudeOpus5"; }
    }

    verification vintageFixtureRefineGate : Test { :>> id = "a608b5a9-9b3f-4bfd-b933-9f593e52b1cc"; :>> title = "Sprint 544 refine gate (DoR)"; :>> createdAt = "2026-09-04"; :>> createdBy = "claudeOpus5"; :>> method = VerificationMethod::inspect; :>> procedureText = "READY once a real prior release was reachable and its binary ran: the DoD said obtained from the release channel rather than synthesised, and v0.3.0 and v0.2.3 were both fetched and version-proved before any fixture was built on them."; }
    verification vintageFixtureStandupGate : Test { :>> id = "11738708-abc9-4e5a-9257-460ba640ce1a"; :>> title = "Sprint 544 standup gate"; :>> createdAt = "2026-09-04"; :>> createdBy = "claudeOpus5"; :>> method = VerificationMethod::inspect; :>> procedureText = "ONE CHOICE: the vintage fixture is scaffolded, imported into AND gated by the old binary. A vintage scaffold gated by the current binary is the current fixture with older files - and D0251's pin would refuse it anyway. Second: sync-claude runs between import and gate in BOTH loops, because the first vintage run judged the engine's no-sync-on-import behaviour and called it the unit's failure. Third: an unavailable vintage fails the command; a check that quietly ran on one fixture is the pass-at-zero shape."; }
    verification vintageFixtureImplementGate : Test { :>> id = "83158062-6e59-4970-8dde-da3ccf8bc8ab"; :>> title = "Sprint 544 implement gate"; :>> createdAt = "2026-09-04"; :>> createdBy = "claudeOpus5"; :>> method = VerificationMethod::test; :>> procedureText = "RAN: the first vintage failure was a tail of PASS lines - the last four lines of guard all - so the error extraction now prefers failing lines; the first issue263 probe failed on BOTH fixtures because the planted constraint existed nowhere, which is how the twelve missing constraint defs were found (issue370); the second probe failed on the current fixture because include_dir embeds .engine at build time and an incremental build shipped the stale rules file (touch main.rs); the third failed because the assert lacked the EngineGuardConstraints import; the fourth was the DoD's exact picture. The constraint-def test's first draft kept a trailing semicolon and named six false misses."; }
    verification vintageFixtureReviewGate : Test { :>> id = "148bb3ce-a1fc-4595-81a4-2ac9bc6cc63c"; :>> title = "Sprint 544 review gate — three passes per D0172"; :>> createdAt = "2026-09-04"; :>> createdBy = "claudeOpus5"; :>> method = VerificationMethod::inspect; :>> procedureText = "THREE PASSES. (1) IS THE VINTAGE REAL: a release asset, fetched and version-proved, running its own init, import and gate - not a synthesised tree. (2) CAN A PASS ON ONE FIXTURE HIDE THE OTHER: no - two tables, both counted into the exit code, the vintage named in its header. (3) WHAT IT COSTS: a network fetch once per version per machine and a second full pass per unit; CI does not run it yet and D0302 says so."; }
    verification vintageFixtureCloseOutGate : Test { :>> id = "c31fa5a5-7d70-4af2-b765-d7ca8beec3a6"; :>> title = "Sprint 544 closeOut gate (autonomous, D0049)"; :>> createdAt = "2026-09-04"; :>> createdBy = "claudeOpus5"; :>> method = VerificationMethod::inspect; :>> procedureText = "CLOSED. issue265 and issue370 resolve; D0302 records the layering, the sync ordering, the twelve identities and the tail fix; CLAUDE.md's project-migration bullet names --vintage."; }
    verification vintageFixtureRetroGate : Test { :>> id = "af8bb8d1-bd5d-4958-8c20-838d86ff7b6a"; :>> title = "Sprint 544 retro gate (autonomous, D0049)"; :>> createdAt = "2026-09-04"; :>> createdBy = "claudeOpus5"; :>> method = VerificationMethod::analyze; :>> procedureText = "no new item - already tracked: the twelve identities are issue370 with a test as their control; the stale-embed hygiene fact is in d0302's consequences and is a build habit, not a control; wiring --vintage into CI is d0302's stated deferral, to be raised when the fetch cost is accepted there. Four probes to reach one clean picture is the day's pattern again: each wrong result was a real fact about something else, and reading it was cheaper than reasoning about it."; }
}
