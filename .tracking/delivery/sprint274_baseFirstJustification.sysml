// ProjectDeliveryS274 — Sprint 274: custom vocabulary must justify itself — the automated control
// D0139(B) requires. EXECUTE. 2 pts.
package ProjectDeliveryS274 {
    private import EngineElement::*;
    private import EngineWork::*;
    private import EngineVerification::*;
    private import EngineRelationships::*;

    #CharteredBy dependency from baseFirstStory to d0139;

    part baseFirstStory : Story {
        :>> id = "0d8000c9-0814-60c9-9b3e-0000003000c9";
        :>> title = "Sprint 274: base-first-justification guard — a custom marker must state why (2 pts)";
        :>> createdAt = "2026-08-14"; :>> createdBy = "claudeOpus5"; :>> kind = WorkKind::code; :>> priority = WorkPriority::p0; :>> owner = "claudeOpus5"; :>> estimatedPoints = 2;
    }

    action def DeliveryRunS274 {
        action storyBaseFirst;
        verification storyBaseFirstDoD : Test { :>> id = "0d8000ca-0814-60ca-9b3e-0000003000ca"; :>> method = VerificationMethod::test; :>> procedureText = "Covers dcBaseFirstVocabulary (issue095) — the CONTROL half of D0139(B), the rule half having been stated when D0139 was accepted. The rule exists because a documented PREFERENCE demonstrably does not work here: sysmlv2-syntax-notes.md:16 already recorded `:>` as the idiomatic derivation form and #DerivedFrom was used 37 times anyway, and D0047 is explicit that manual vigilance is not a control. DELIVERED: warning-level `base-first-justification`, requiring every PROJECT-declared `metadata def` to carry a justification — a `doc` clause on the declaration or comment lines directly above it, which is how this repo actually documents markers today. SCOPE IS NARROW ON PURPOSE: the engine's own 17 markers are GRANDFATHERED under the forward-only rule (issue068), and D0140 has since supplied kernel-verified justifications for the two that needed them, so this fires only on markers a project declares from here on — currently zero. A guard that reports nothing today and blocks a bad habit tomorrow is the intended shape, not a defect. TEXT-BASED, stated rather than hidden: the AST captures no `doc` clauses or comments, so there is nothing structural to inspect; capturing doc text is a separate parser increment, and the scan is scoped to the declaration line plus the three above it rather than the whole file. VERIFIED both polarities: an undocumented project marker is REPORTED with file:line; the same marker with a justification above it PASSES; the engine's 17 are not scanned at all. clippy clean; 161 tests; validate + all 28 guards + check-engine green."; }
        part storyBaseFirstDoDR1 : TestResult { :>> id = "0d8000cb-0814-60cb-9b3e-0000003000cb"; :>> outcome = VerdictKind::pass; :>> judgedAgainst = "bf8e1b0"; :>> judgedAt = "2026-08-14"; :>> judgedBy = "claudeOpus5"; }
    }

    verification bfRefineGate : Test { :>> id = "0d8000cc-0814-60cc-9b3e-0000003000cc"; :>> title = "Sprint 274 refine gate (DoR)"; :>> createdAt = "2026-08-14"; :>> createdBy = "claudeOpus5"; :>> method = VerificationMethod::inspect; :>> procedureText = "DoR: D0139's rule has been accepted since the pass began and has had no enforcement, which is precisely the state D0047 says produces nothing. Small, and it closes the last open clause of D0139 apart from the migrations D0140 retired. estimatedPoints=2. DoR met."; }
    part bfRefineGateR1 : TestResult { :>> id = "0d8000cd-0814-60cd-9b3e-0000003000cd"; :>> outcome = VerdictKind::pass; :>> judgedAgainst = "bf8e1b0"; :>> judgedAt = "2026-08-14"; :>> judgedBy = "claudeOpus5"; }

    verification bfStandupGate : Test { :>> id = "0d8000ce-0814-60ce-9b3e-0000003000ce"; :>> title = "Sprint 274 standup gate"; :>> createdAt = "2026-08-14"; :>> createdBy = "claudeOpus5"; :>> method = VerificationMethod::inspect; :>> procedureText = "Approach: warning-level, since a justification is prose and no exact check exists for whether prose actually justifies anything — a hard guard on a heuristic is the issue081 dynamic. Grandfather the engine's own markers so the control is forward-only. No blockers."; }
    part bfStandupGateR1 : TestResult { :>> id = "0d8000cf-0814-60cf-9b3e-0000003000cf"; :>> outcome = VerdictKind::pass; :>> judgedAgainst = "bf8e1b0"; :>> judgedAt = "2026-08-14"; :>> judgedBy = "claudeOpus5"; }

    verification bfImplementGate : Test { :>> id = "0d8000d0-0814-60d0-9b3e-0000003000d0"; :>> title = "Sprint 274 implement gate"; :>> createdAt = "2026-08-14"; :>> createdBy = "claudeOpus5"; :>> method = VerificationMethod::test; :>> procedureText = "The first run reported 1 scanned when the correct answer was 0, and finding out why was the useful part: `metadata def View;   // marks a computed artifact` has a TRAILING COMMENT, and I trimmed only from the end, so the name became the whole comment, failed the grandfather check, and an ENGINE marker was classified as a project one. It passed only by accident, because a comment line happened to sit above it. Fixed by splitting on `//` before taking the name. A guard that gets the right verdict for the wrong reason is worse than one that fails, because nothing prompts you to look."; }
    part bfImplementGateR1 : TestResult { :>> id = "0d8000d1-0814-60d1-9b3e-0000003000d1"; :>> outcome = VerdictKind::pass; :>> judgedAgainst = "bf8e1b0"; :>> judgedAt = "2026-08-14"; :>> judgedBy = "claudeOpus5"; }

    verification bfReviewGate : Test { :>> id = "0d8000d2-0814-60d2-9b3e-0000003000d2"; :>> title = "Sprint 274 review gate"; :>> createdAt = "2026-08-14"; :>> createdBy = "claudeOpus5"; :>> method = VerificationMethod::inspect; :>> procedureText = "Reviewed. D0139 now has enforcement for every clause it retains: (A)(B) base-first rule + this control, (C) classifiers retained and empirically confirmed by the marker census, (D) delivered as `assert constraint` in sprint 272, (F) the syntax notes corrected. (E) and (G) were superseded by D0140 on kernel evidence. The text-based check is the one soft spot and it is recorded as such — when the parser captures doc clauses this guard should move to the AST, which is the same progression `parser-coverage` and `sequence-multiplicity` are on."; }
    part bfReviewGateR1 : TestResult { :>> id = "0d8000d3-0814-60d3-9b3e-0000003000d3"; :>> outcome = VerdictKind::pass; :>> judgedAgainst = "bf8e1b0"; :>> judgedAt = "2026-08-14"; :>> judgedBy = "claudeOpus5"; }

    verification bfCloseOutGate : Test { :>> id = "0d8000d4-0814-60d4-9b3e-0000003000d4"; :>> title = "Sprint 274 closeOut gate (autonomous, D0049)"; :>> createdAt = "2026-08-14"; :>> createdBy = "claudeOpus5"; :>> method = VerificationMethod::inspect; :>> procedureText = "Autonomous closeOut (D0049). dcBaseFirstVocabulary carries a passing DoD TestResult; issue095 resolves. 28 guards (19 hard, 9 warning-only). Doc-sync: guards.md count + catalogue entry, CLAUDE.md §5. clippy clean; 161 tests; validate + all 28 guards + check-engine green. No gate bypassed."; }
    part bfCloseOutGateR1 : TestResult { :>> id = "0d8000d5-0814-60d5-9b3e-0000003000d5"; :>> outcome = VerdictKind::pass; :>> judgedAgainst = "bf8e1b0"; :>> judgedAt = "2026-08-14"; :>> judgedBy = "claudeOpus5"; }

    verification bfRetroGate : Test { :>> id = "0d8000d6-0814-60d6-9b3e-0000003000d6"; :>> title = "Sprint 274 retro gate (autonomous, D0049)"; :>> createdAt = "2026-08-14"; :>> createdBy = "claudeOpus5"; :>> method = VerificationMethod::analyze; :>> procedureText = "Autonomous retro (D0049) under D0131's retroTrack. WELL: (1) the scope was kept narrow and forward-only rather than retro-applied to 17 existing markers, which would have produced 17 warnings on correct work and taught the reader to ignore the guard; (2) the text-based limitation is recorded in the code and the catalogue rather than glossed, with the AST migration named as the successor; (3) both polarities were tested, and the positive case is what exposed the trailing-comment bug. AVOIDABLE-ISSUE 1: my first implementation misclassified an ENGINE marker as a project marker because I trimmed a trailing comment only from the end of the line, and it PASSED anyway by accident — a comment line happened to sit above it. NO NEW ITEM, reason stated: the defect was in a guard written this sprint and fixed this sprint, and the general lesson is already the one this pass keeps relearning — a right verdict reached for the wrong reason is the dangerous case, because nothing prompts you to look. It was caught only because the scanned COUNT was 1 when I expected 0, which is an argument for reading a control's counters and not just its verdict. AVOIDABLE-ISSUE 2: a clippy `slicing may panic` on my range index, fixed with `.get(..)`. NO NEW ITEM: clippy is the control, it fired, one build cycle. Estimate 2 pts, delivered."; }
    part bfRetroGateR1 : TestResult { :>> id = "0d8000d7-0814-60d7-9b3e-0000003000d7"; :>> outcome = VerdictKind::pass; :>> judgedAgainst = "bf8e1b0"; :>> judgedAt = "2026-08-14"; :>> judgedBy = "claudeOpus5"; }
}
