// ProjectDeliveryS341 — Sprint 341: D0160 deferred with its condition evaluated; D0161 designs
// `.knowledge/` and names the two invariants it breaks. CHANGE (§3a). 3 pts.
package ProjectDeliveryS341 {
    private import EngineElement::*;
    private import EngineWork::*;
    private import EngineVerification::*;
    private import EngineRelationships::*;

    #CharteredBy dependency from knowledgeDesignStory to d0161;

    part knowledgeDesignStory : Story {
        :>> id = "0d800500-0814-6500-9b3e-000000300500";
        :>> title = "Sprint 341: D0160 deferral (condition evaluated) + D0161 knowledge-store design (3 pts)";
        :>> createdAt = "2026-08-18"; :>> createdBy = "claudeOpus5"; :>> kind = WorkKind::decision; :>> priority = WorkPriority::p0; :>> owner = "claudeOpus5"; :>> estimatedPoints = 3;
    }

    action def DeliveryRunS341 {
        action storyKnowledgeDesign;
        verification storyKnowledgeDesignDoD : Test { :>> id = "0d800501-0814-6501-9b3e-000000300501"; :>> method = VerificationMethod::inspect; :>> procedureText = "TWO PARTS. (1) D0160 ACCEPTED AS A DEFERRAL, with the condition the human attached ('defer for now if there is not a good solution out there') EVALUATED rather than assumed: the repository carries eleven dependencies and no JS engine or HTML parser; jsdom and Playwright are both DOM-capable and both need a Node toolchain; the only Node-free route is boa_engine plus a hand-written DOM shim, which is a project rather than a dependency for one 470-line console. No option is both DOM-capable and Node-free, so the condition failed and the deferral applies, with a named trigger — a third console defect a DOM test would have caught, or a Node-free DOM option appearing. Rung 1 stands as built. THE DEFERRAL BRANCH OF D0160's OWN TEXT CREATED AN OBLIGATION AND IT IS DISCHARGED HERE: the console requirements now STATE that the console has no behavioural coverage and that a wrong destination or dead control reaches the human before a gate, as an accepted risk rather than an implicit one. (2) D0161 PROPOSED, designing `.knowledge/` — the store D0153's accepted process specifies and never locates. Grounded rather than invented: D0153 step 3 says 'the store schema — one table per fact shape' and names tiers up to a graph database while naming no tier-1 location or format, so an accepted process currently emits entities, relations and aliases with nowhere to put them. validate 369 clean; check-engine clean; 35 guards ALL PASS; no code changed."; }
        part storyKnowledgeDesignDoDR1 : TestResult { :>> id = "0d800502-0814-6502-9b3e-000000300502"; :>> outcome = VerdictKind::pass; :>> judgedAgainst = "04d3d6f"; :>> judgedAt = "2026-08-18"; :>> judgedBy = "claudeOpus5"; }
    }

    verification kdRefineGate : Test { :>> id = "0d800503-0814-6503-9b3e-000000300503"; :>> title = "Sprint 341 refine gate (DoR)"; :>> createdAt = "2026-08-18"; :>> createdBy = "claudeOpus5"; :>> method = VerificationMethod::inspect; :>> procedureText = "DoR. The design request was answered by reading D0153 and its process file FIRST rather than designing from the idea — which changed the result in two places: identity is COMPUTED (a hash of type and normalised name) because that process already fixed it and it is what makes re-extraction merge, and facts get ONE FILE PER SHAPE because that process forbids folding a new shape into an existing table with a nullable column. Both are inherited constraints, not preferences of mine, and one of them breaks a stated keel invariant. estimatedPoints=3."; }
    part kdRefineGateR1 : TestResult { :>> id = "0d800504-0814-6504-9b3e-000000300504"; :>> outcome = VerdictKind::pass; :>> judgedAgainst = "04d3d6f"; :>> judgedAt = "2026-08-18"; :>> judgedBy = "claudeOpus5"; }

    verification kdStandupGate : Test { :>> id = "0d800505-0814-6505-9b3e-000000300505"; :>> title = "Sprint 341 standup gate"; :>> createdAt = "2026-08-18"; :>> createdBy = "claudeOpus5"; :>> method = VerificationMethod::inspect; :>> procedureText = "Approach: DESIGN ONLY, no directory created and no code written, because a new top-level model with its own schema is a §3a CHANGE and the request was to design it out. Name every conflict with a stated invariant explicitly in the Decision instead of trimming the design until it fits — a design that quietly violates §1.3 would be worse than one that asks for a scoped exception. No blockers."; }
    part kdStandupGateR1 : TestResult { :>> id = "0d800506-0814-6506-9b3e-000000300506"; :>> outcome = VerdictKind::pass; :>> judgedAgainst = "04d3d6f"; :>> judgedAt = "2026-08-18"; :>> judgedBy = "claudeOpus5"; }

    verification kdImplementGate : Test { :>> id = "0d800507-0814-6507-9b3e-000000300507"; :>> title = "Sprint 341 implement gate"; :>> createdAt = "2026-08-18"; :>> createdBy = "claudeOpus5"; :>> method = VerificationMethod::analyze; :>> procedureText = "THE DESIGN BREAKS TWO STATED INVARIANTS AND SAYS SO IN ITS OWN TEXT, which is the substance of this sprint rather than the layout. FIRST, the two-model rule: CLAUDE.md opens by insisting the engine model tracks the WORK and the deliverable is what the work PRODUCES, and domain knowledge is neither — it is an input consumed while working, so filing it under .tracking would put facts about the world into the work model, which is the same conflation §1 forbids in the other direction. A third model is therefore the honest option, and its cost is concrete: /api/scope computes engine | deliverable | UNSCOPED and would need a third classification, and the two-model sentence needs revising in the same commit. SECOND, UUID identity: §1.3 makes identity an immutable minted UUID so two items never collide, which is right when each item is a distinct ACT — and wrong for knowledge, where the same referent extracted from two documents must converge on ONE node with no matching service. D0153 already fixed that as a computed hash, so the exception is inherited, and it is precisely why `.knowledge/` needs its own schema rather than importing schema/core. A DESIGN CHOICE FORCED BY A MEASUREMENT, not by taste: /api/decisions was observed today at 12.8 then 33.2 seconds over a 369-file, ~8000-item SysML model while every other endpoint answered under 150ms. A machine-extracted fact corpus is larger than the work model by construction, so facts go to JSONL — one line per fact, atomic, diffable, independently mergeable — while the small human-owned VOCABULARY stays SysML where the existing vocabulary guards can see it. That split is the same reasoning D0105 used when it rejected TOML for rules but kept it for pure execution parameters."; }
    part kdImplementGateR1 : TestResult { :>> id = "0d800508-0814-6508-9b3e-000000300508"; :>> outcome = VerdictKind::pass; :>> judgedAgainst = "04d3d6f"; :>> judgedAt = "2026-08-18"; :>> judgedBy = "claudeOpus5"; }

    verification kdReviewGate : Test { :>> id = "0d800509-0814-6509-9b3e-000000300509"; :>> title = "Sprint 341 review gate"; :>> createdAt = "2026-08-18"; :>> createdBy = "claudeOpus5"; :>> method = VerificationMethod::inspect; :>> procedureText = "Reviewed. THE HEADLINE VIEW IS THE PART I WOULD DEFEND HARDEST: question-coverage. D0153 makes questions drive everything, and a knowledge store's failure mode is being large and unable to answer anything — so the one number that keeps it honest is, for each DECLARED question, whether seeding hits an entity and traversal reaches an answer. That is falsifiable in the way `keel verification` is: it can report that the graph CANNOT answer a question the human wrote down, which no size or count can. TWO THINGS I DELIBERATELY EXCLUDED. Duplicate-identity must NOT run over `.knowledge/` — here a duplicate IS the merge mechanism, so a guard that is correct everywhere else would be exactly wrong, and that inversion is worth stating because a lane that inherits the wrong guards silently is how a separate model rots. And the work-discipline guards (charter, ceremony, sprint-coverage, retro-backlog) are meaningless over a fact corpus; if they fire, the lane is misconfigured rather than the corpus non-compliant. ONE HONEST NOTE IN THE DECISION: for THIS repository the store would likely start EMPTY, since keel's own domain knowledge is its docs and decisions — the first real user is a downstream project with documents to ingest. That is an argument for keeping the design cheap, and NOT the D0157/D0159 argument for declining it, because unlike those cases the demand is already rooted in an accepted Decision that cannot otherwise be implemented."; }
    part kdReviewGateR1 : TestResult { :>> id = "0d80050a-0814-650a-9b3e-00000030050a"; :>> outcome = VerdictKind::pass; :>> judgedAgainst = "04d3d6f"; :>> judgedAt = "2026-08-18"; :>> judgedBy = "claudeOpus5"; }

    verification kdCloseOutGate : Test { :>> id = "0d80050b-0814-650b-9b3e-00000030050b"; :>> title = "Sprint 341 closeOut gate (autonomous, D0049)"; :>> createdAt = "2026-08-18"; :>> createdBy = "claudeOpus5"; :>> method = VerificationMethod::inspect; :>> procedureText = "Autonomous closeOut (D0049). D0160 accepted as a deferral and its obligation discharged in the console requirements; D0161 PROPOSED and awaiting the human, since it asks for two scoped exceptions to stated invariants and no design should grant itself those. NOTHING WAS BUILT: no `.knowledge/` directory exists, no schema, no command — the request was to design it out, and creating the structure before the exceptions are granted would be the CHANGE route skipped. validate 369 clean; check-engine clean; 35 guards ALL PASS; no code changed."; }
    part kdCloseOutGateR1 : TestResult { :>> id = "0d80050c-0814-650c-9b3e-00000030050c"; :>> outcome = VerdictKind::pass; :>> judgedAgainst = "04d3d6f"; :>> judgedAt = "2026-08-18"; :>> judgedBy = "claudeOpus5"; }

    verification kdRetroGate : Test { :>> id = "0d80050d-0814-650d-9b3e-00000030050d"; :>> title = "Sprint 341 retro gate (autonomous, D0049)"; :>> createdAt = "2026-08-18"; :>> createdBy = "claudeOpus5"; :>> method = VerificationMethod::analyze; :>> procedureText = "Autonomous retro (D0049) under D0131's retroTrack. WELL: (1) the human attached a CONDITION to their deferral and I evaluated it and recorded the evaluation, so they can disagree with my finding rather than only with the outcome — the alternative, deferring because they said defer, would have hidden whether anyone had actually looked; (2) D0160's own consequences clause created an obligation for the deferral branch and it was discharged in the same sprint rather than becoming the kind of inert clause the Decision critiques kept finding; (3) the design was grounded by reading the accepted process first, which changed two of its central choices and revealed that one of them breaks a stated invariant. AVOIDABLE-ISSUE: none this sprint. WHAT I AM WATCHING: D0161 asks for exceptions to two invariants, and the honest failure mode of a design like this is that the exceptions get granted quietly because the layout looks tidy. If either exception is unacceptable the design does not survive, and the Decision says so rather than offering a trimmed version that would violate §1.3 without asking. Estimate 3 pts, delivered."; }
    part kdRetroGateR1 : TestResult { :>> id = "0d80050e-0814-650e-9b3e-00000030050e"; :>> outcome = VerdictKind::pass; :>> judgedAgainst = "04d3d6f"; :>> judgedAt = "2026-08-18"; :>> judgedBy = "claudeOpus5"; }
}
