// ProjectDeliveryS433 — Sprint 433: advisory blindness ends (issue230): spoken advisories and repeat-ignores are ledgered, so D0197's revisit condition can finally trigger. EXECUTE. 1 pts.
package ProjectDeliveryS433 {
    private import EngineElement::*;
    private import EngineWork::*;
    private import EngineVerification::*;
    private import EngineRelationships::*;

    #CharteredBy dependency from advisoryInstrumentationStory to d0197;

    part advisoryInstrumentationStory : Story {
        :>> id = "cf33cac8-8056-4901-9d2d-b773dfde8e68";
        :>> title = "Sprint 433: the advisory learns to count (1 pts)";
        :>> createdAt = "2026-08-23"; :>> createdBy = "claudeFable5"; :>> kind = WorkKind::code; :>> priority = WorkPriority::p0; :>> owner = "claudeFable5"; :>> estimatedPoints = 1;
    }

    action def DeliveryRunS433 {
        action storyAdvisoryInstrumentation;
        verification storyAdvisoryInstrumentationDoD : Test { :>> id = "7fa4828f-b8ab-4a74-8670-89a05329a772"; :>> method = VerificationMethod::test; :>> procedureText = "DELIVERED: dcAdvisoryInstrumentation (resolves issue230 - three panel lenses independently found the zero-advisory-blocks datum uninformative: 1,164 pre-bash fires could mean deterrence or dead weight, and D0197's declared revisit condition was structurally untriggerable). THE FIX, entirely WITHIN the frozen 6-field ledger schema (events are declared vocabulary; fields were not touched, so D0180's freeze holds): an advisory that actually SPEAKS emits advisory-issued, and speaking the SAME advice hash again in the same session emits advisory-repeated - the mechanical ignore signal, tracked per-session under .keel/metrics. All three pre-bash speak paths instrumented (shell-adaptation advisories, blocked-under-strict patterns, human-channel asks). enforcement-report gains advisoryIssued / advisoryRepeated / advisoryApproxHeedPct with its honesty note IN the output: heeded-vs-never-retried is indistinguishable by design, so the rate is stated approximate. control-events.toml declares both events (the D0193 contract mechanism used as designed, application note riding its marker); the guard-45 emitted list matches. VERIFIED LIVE: the same advisable command fired twice read back issued 2 / repeated 1 / heed 50 percent - the first non-vacuous advisory measurement this repo has ever produced; suite 10/10; clippy clean after a line-budget extraction."; }
        part storyAdvisoryInstrumentationDoDR1 : TestResult { :>> id = "130ac19e-2c9d-47da-b368-0a0406911f6f"; :>> outcome = VerdictKind::pass; :>> judgedAgainst = "d6c341701aefa9bf1cad16c900bc6391cf24f305"; :>> judgedAt = "2026-08-23"; :>> judgedBy = "claudeFable5"; }
    }

    verification advisoryInstrumentationRefineGate : Test { :>> id = "7bd80b58-8c54-4fa4-b64e-2548471011f3"; :>> title = "Sprint 433 refine gate (DoR)"; :>> createdAt = "2026-08-23"; :>> createdBy = "claudeFable5"; :>> method = VerificationMethod::inspect; :>> procedureText = "DoR. Chartered by d0197's own revisit condition (via issue230). In scope: pre-bash speak-path instrumentation, the two ledger events, the report section, the contract declaration. Out of scope (stated): stop/pre-write advisory instrumentation - pre-bash is 79 percent of all fires and the pattern extends mechanically when wanted. 1 point."; }
    part advisoryInstrumentationRefineGateR1 : TestResult { :>> id = "2217dcb3-5cc8-4ee6-a699-abd8c76bb032"; :>> outcome = VerdictKind::pass; :>> judgedAgainst = "d6c341701aefa9bf1cad16c900bc6391cf24f305"; :>> judgedAt = "2026-08-23"; :>> judgedBy = "claudeFable5"; }
    verification advisoryInstrumentationStandupGate : Test { :>> id = "622f8143-6f9f-45ba-95f6-1e18e57e609a"; :>> title = "Sprint 433 standup gate"; :>> createdAt = "2026-08-23"; :>> createdBy = "claudeFable5"; :>> method = VerificationMethod::inspect; :>> procedureText = "Approach: fit INSIDE the frozen schema by adding EVENTS, not fields - the freeze protects the line shape, and the event vocabulary is exactly the extension joint D0193 built; repeat-of-same-hash as the ignore signal is the only mechanically observable proxy this harness offers, and every surface that reports it says approximate."; }
    part advisoryInstrumentationStandupGateR1 : TestResult { :>> id = "67353786-fbe0-4886-a100-a8f04b13f71b"; :>> outcome = VerdictKind::pass; :>> judgedAgainst = "d6c341701aefa9bf1cad16c900bc6391cf24f305"; :>> judgedAt = "2026-08-23"; :>> judgedBy = "claudeFable5"; }
    verification advisoryInstrumentationImplementGate : Test { :>> id = "db96302b-7b3a-4192-a9cc-b34cb9ae55a8"; :>> title = "Sprint 433 implement gate"; :>> createdAt = "2026-08-23"; :>> createdBy = "claudeFable5"; :>> method = VerificationMethod::test; :>> procedureText = "Verified by running: the double-fire probe (a command shellcheck provably flags, per its own test fixture) read back issued 2 / repeated 1 / heedPct 50 from enforcement-report; guard 45 (control-event-coverage) green with both events declared and emitted; full workspace suite 10/10 result-ok; clippy pedantic+nursery clean; validate + all 47 guards green."; }
    part advisoryInstrumentationImplementGateR1 : TestResult { :>> id = "8a5e3cb9-c416-446e-b698-3d94bb89463b"; :>> outcome = VerdictKind::pass; :>> judgedAgainst = "d6c341701aefa9bf1cad16c900bc6391cf24f305"; :>> judgedAt = "2026-08-23"; :>> judgedBy = "claudeFable5"; }
    verification advisoryInstrumentationReviewGate : Test { :>> id = "d5b41026-3c4d-4cce-8aef-24c400e1bed3"; :>> title = "Sprint 433 review gate — three passes per D0172"; :>> createdAt = "2026-08-23"; :>> createdBy = "claudeFable5"; :>> method = VerificationMethod::inspect; :>> procedureText = "PASS 1, CLAIMS: probe outputs quoted from this session. PASS 2, BOUNDARY: the heed rate is an UPPER bound - an advisory followed by never re-running the command counts as heeded even if the agent simply moved on; the report's own note says so, and D0197's revisit reads the repeat count (the hard signal), not the rate. PASS 3, OWN DIFF: the first probe used commands the inspector does not flag (silent = no event, correctly) - the lesson is to probe with the control's own positive fixture, which the second attempt did. WHAT A REVIEWER SHOULD ATTACK: per-session last-advice state under .keel/metrics is machine-local, so the repeat signal does not aggregate across machines - the same D0180 named-consumer boundary, inherited, stated."; }
    part advisoryInstrumentationReviewGateR1 : TestResult { :>> id = "eb65e22a-b2e9-4b69-b9a8-f9dc5efdde4f"; :>> outcome = VerdictKind::pass; :>> judgedAgainst = "d6c341701aefa9bf1cad16c900bc6391cf24f305"; :>> judgedAt = "2026-08-23"; :>> judgedBy = "claudeFable5"; }
    verification advisoryInstrumentationCloseOutGate : Test { :>> id = "bcb59fc7-fdc1-46e6-9f55-4f408fbbdf0a"; :>> title = "Sprint 433 closeOut gate (autonomous, D0049)"; :>> createdAt = "2026-08-23"; :>> createdBy = "claudeFable5"; :>> method = VerificationMethod::inspect; :>> procedureText = "Autonomous closeOut (D0049). issue230 resolves - ZERO open issues; the frontier holds only the two items needing the human (control evaluation approval, second model); validate + guards green."; }
    part advisoryInstrumentationCloseOutGateR1 : TestResult { :>> id = "d8ffd616-4bb7-4f4e-9dc9-4bbecec00af5"; :>> outcome = VerdictKind::pass; :>> judgedAgainst = "d6c341701aefa9bf1cad16c900bc6391cf24f305"; :>> judgedAt = "2026-08-23"; :>> judgedBy = "claudeFable5"; }
    verification advisoryInstrumentationRetroGate : Test { :>> id = "297f70df-36ab-40ad-ada7-b721d9ab29bc"; :>> title = "Sprint 433 retro gate (autonomous, D0049)"; :>> createdAt = "2026-08-23"; :>> createdBy = "claudeFable5"; :>> method = VerificationMethod::analyze; :>> procedureText = "Autonomous retro (D0049). AVOIDABLE-ISSUE SCAN under rcRecurrence: the uninstrumented-monitor class (a control whose effect cannot be counted) now has the counting pattern on its dominant instance; stop/pre-write inherit it on demand. WELL: the frozen-schema constraint forced the cleaner design - events over fields - and the D0193 contract absorbed its second extension without a new mechanism. Estimate 1 pt, delivered 1."; }
    part advisoryInstrumentationRetroGateR1 : TestResult { :>> id = "03ab6b37-f58e-41ab-b96c-8061b8438407"; :>> outcome = VerdictKind::pass; :>> judgedAgainst = "d6c341701aefa9bf1cad16c900bc6391cf24f305"; :>> judgedAt = "2026-08-23"; :>> judgedBy = "claudeFable5"; }
}
