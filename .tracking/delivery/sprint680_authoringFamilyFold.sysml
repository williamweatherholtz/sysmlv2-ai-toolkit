// ProjectDeliveryS680 — Sprint 680: The authoring family joins keel record. Under D0451 (d0399 option A, the human's word 2026-09-11) the nine authoring verbs - add-task, new sprint, append-result, append-gate-result, apply-review, record-measurement, snapshot-indicators, reverify, mint - leave the top-level dispatch and become sub-verbs of `keel record`, each named for the fact it writes (task, sprint, result, gate-result, review, measurement, indicator-snapshot, reverify, mint) and each keeping its flags, in the sprint 512 shape (D0273): a committed transform rewrites every call site in the same commit, no alias window, and the pre-fold binary is held equal to the post-fold binary on every moved verb with the written tree compared too, since a writer's output is the file it changes. Delivers the third of the five folds dcRemainingCliFamilies names; the dispatch count hardening reads drops 58 to 49. CHANGE.. EXECUTE. 3 pts.
package ProjectDeliveryS680 {
    private import EngineElement::*;
    private import EngineWork::*;
    private import EngineVerification::*;
    private import EngineRelationships::*;

    #CharteredBy dependency from authoringFamilyFoldStory to d0451;

    part authoringFamilyFoldStory : Story {
        :>> id = "4b14ed15-8609-4054-a98d-ce20dcb9e25f";
        :>> title = "Sprint 680: The authoring family joins keel record. Under D0451 (d0399 option A, the human's word 2026-09-11) the nine authoring verbs - add-task, new sprint, append-result, append-gate-result, apply-review, record-measurement, snapshot-indicators, reverify, mint - leave the top-level dispatch and become sub-verbs of `keel record`, each named for the fact it writes (task, sprint, result, gate-result, review, measurement, indicator-snapshot, reverify, mint) and each keeping its flags, in the sprint 512 shape (D0273): a committed transform rewrites every call site in the same commit, no alias window, and the pre-fold binary is held equal to the post-fold binary on every moved verb with the written tree compared too, since a writer's output is the file it changes. Delivers the third of the five folds dcRemainingCliFamilies names; the dispatch count hardening reads drops 58 to 49. CHANGE. (3 pts)";
        :>> createdAt = "2026-09-12"; :>> createdBy = "claudeOpus5"; :>> kind = WorkKind::code; :>> priority = WorkPriority::p0; :>> owner = "claudeOpus5"; :>> estimatedPoints = 3;
    }

    action def DeliveryRunS680 {
        action storyAuthoringFamilyFold;
        verification storyAuthoringFamilyFoldDoD : Test { :>> id = "12d63a13-dd4d-4ce7-b8a8-7ed54a7c51ec"; :>> method = VerificationMethod::test; :>> procedureText = "DELIVERED: `keel record <sub-verb> ...` answers for all nine with the arguments unchanged and `keel record` alone prints a usage naming all thirteen sub-verbs; the nine top-level arms are gone from main.rs and COMMAND_NAMES (57 to 48); the nine CliCommand facts are removed from both homes and the `record` fact's invocation names every sub-verb (108 facts to 99, cli-surface-declared equal); every call site under .engine, CLAUDE.md, README.md, docs, scripts and keel-cli/assets is rewritten by .engine/tools/migrations/2026-09-11-authoring-family-fold.py (dry-run default, per-file conservation, re-plan 0), the Rust prose and the test argv sites by the fold680_rust.py hand list each asserted to hit once; .claude regenerated by keel sync-claude; the pre-fold binary keel-prefold680.exe (build ceaabdd) and the post-fold binary agree on 13 of 13 cases on two identical scratch clones - stdout, stderr, exit code and, for the four writers, the git diff of the written tree with minted UUIDs masked - the only difference being the usage line naming the command; the K7 pre-bash protection on apply-review follows it to `record review` and a test holds it; a test holds `record`'s routed sub-verbs equal to the fact's invocation; hardening reads dispatched 49/49; validate, check-engine, guard, clippy, the touched suite and the surface tests pass. Decisions and .tracking are not rewritten; control and ledger ids append-result:ran-receipt and append-gate-result:ran-receipt are kept as ids. The STPA collapse the fold causes is a tracked Issue with a resolver, not fixed here."; }
        // RAN: keel record task|sprint|result|gate-result|review|measurement|indicator-snapshot|reverify|mint on keel-serve.exe: all nine route (each alone prints its own usage, exit 2); keel add-task .: record usage, exit 2 (no alias); compare680.txt: 13 of 13 EQUAL against keel-prefold680.exe (build ceaabdd) on two fresh clones, 5 strictly byte-equal incl. the add-task write tree (2892 B, UUIDs masked) and reverify --demos / snapshot-indicators trees, 8 equal under the D0451 rename of the usage line only; keel show hardening .: dispatched 49 namedInHelp 49 coveragePct 100; COMMAND_NAMES 48, 99 facts in both homes; transform 2026-09-11-authoring-family-fold.py --apply: 41 sites / 22 files, re-plan 0; cargo test --test capability_refusal_bites 6 passed (the_record_sub_verbs_match_the_fact new), --bin keel bash 1 passed (record review Ask, record task Clean), --lib cli_surface 10, hardening 10, write 41, control_structure 10; cargo clippy --release --all-targets -D warnings 0; VERIFIER-RECEIPT (verify680): keel suite --touched (detached): 780 passed 1 failed in 683s, at=1789176382 > launch=1789175695, head=ceaabdd, 16 stems + lib; the one red control_structure_is_computed.rs:74 (cmdAddTask, a folded computed action) fixed to cmdRecord and cargo test --test control_structure_is_computed 3 passed; clippy Finished after the fix
        part storyAuthoringFamilyFoldDoDR1 : TestResult { :>> id = "7435c92b-b002-46fb-8d54-ad87acce956e"; :>> outcome = VerdictKind::pass; :>> judgedAgainst = "ceaabdd"; :>> judgedAt = "2026-09-11"; :>> judgedBy = "claudeOpus5"; }
    }

    verification authoringFamilyFoldRefineGate : Test { :>> id = "87486fea-984f-4274-9a9c-b754b5cf40d3"; :>> title = "Sprint 680 refine gate (DoR)"; :>> createdAt = "2026-09-12"; :>> createdBy = "claudeOpus5"; :>> method = VerificationMethod::inspect; :>> procedureText = "Chartered by D0451, plan-covered under D0396 by d0399 option A, accepted by the human 2026-09-11 on the brief copy-out. Three points: nine dispatch arms move under one router with their bodies untouched, one constant array shrinks, nine facts leave two homes and one fact grows, one Python transform over 22 prose files, 39 Rust prose sites and 8 argv test sites by hand, a thirteen-case comparison that also diffs the written tree, and the two-token hook check. Smaller than 679 (eleven arms, 33 files) because the arms are calls to functions that already exist, not bodies. NOT A PROCESS CHANGE beyond what D0451 states - the fold is the Decision's own text. NOT A FORK - the fork was d0399 and is decided."; }
    // RAN: keel show authority-queue . before the sprint: d0399 option A accepted 2026-09-11 (brief copy-out); keel show item dcRemainingCliFamilies .: open, rendering and orientation folds delivered by sprint678/679; D0451 authored with DependsOn d0399, plan-covered acceptance (D0396); estimatedPoints 3; CharteredBy d0451 in the sprint file
    part authoringFamilyFoldRefineGateR1 : TestResult { :>> id = "5b626a80-e349-45a6-882c-76e5737b93ac"; :>> outcome = VerdictKind::proposed; :>> judgedAgainst = "ceaabdd"; :>> judgedAt = "2026-09-11"; :>> judgedBy = "claudeOpus5"; }
    verification authoringFamilyFoldStandupGate : Test { :>> id = "544cdcb7-656e-4136-bb1e-7ce92f7f263e"; :>> title = "Sprint 680 standup gate"; :>> createdAt = "2026-09-12"; :>> createdBy = "claudeOpus5"; :>> method = VerificationMethod::inspect; :>> procedureText = "Order, taken from the 678 and 679 retros: preserve the pre-fold binary FIRST as keel-prefold680.exe from the landed ceaabdd build; remove the nine arms from main() and route them from cmd_record by script with each old line asserted unique; shrink COMMAND_NAMES and remove the nine facts from both homes while growing the record fact in one script so cli-surface-declared stays equal; rewrite Rust prose with the transform's own rule and the argv sites by a hand list each asserted to hit once; scan for re.compile and re.search over the nine verbs before the dry run (the 679 retro's carry: none found); run the transform; sync-claude; rebuild; compare old against new on two clones including the written tree; read hardening; carry the 679 retro's other item - a test binding the router's printed inventory to its arms - into this sprint as the record sub-verb inventory test. Blocker met: the pre-bash human-judgment check read ONE token after keel, so apply-review's K7 Ask would have silently stopped firing at `record review`; the check now reads the verb and the verb with its sub-verb, with a positive and a negative assert."; }
    // RAN: cp target/release/keel.exe target/release/keel-prefold680.exe from the landed ceaabdd build BEFORE any source edit; fold680_facts.py: nine facts removed from both homes and record grown in one script; fold680_rust.py A-E: 9 arm removals each asserted unique, hook two-token check, 8 argv sites, 39 prose sites / 10 files; grep re.compile|re.search over the nine verbs under scripts and .engine/tools: no site (the 679 carry); transform --dry-run (dry680.txt): 41 sites / 22 files
    part authoringFamilyFoldStandupGateR1 : TestResult { :>> id = "733ba617-3874-46b9-89c6-fe4e457b0c80"; :>> outcome = VerdictKind::proposed; :>> judgedAgainst = "ceaabdd"; :>> judgedAt = "2026-09-11"; :>> judgedBy = "claudeOpus5"; }
    verification authoringFamilyFoldImplementGate : Test { :>> id = "86be65e7-0445-4cc8-b662-1ca809400476"; :>> title = "Sprint 680 implement gate"; :>> createdAt = "2026-09-12"; :>> createdBy = "claudeOpus5"; :>> method = VerificationMethod::test; :>> procedureText = "keel-cli/src/main.rs: nine arms removed from main(); record_authoring_subverb routes task, sprint, result, gate-result, review, measurement, indicator-snapshot, reverify, mint to the untouched functions (sprint passes the whole argv because cmd_new reads its own word); print_record_usage carries the thirteen-sub-verb usage; the hook check is two-token aware. cli_surface.rs: COMMAND_NAMES 48. cli_facts.rs and .engine/cli/commands.sysml: nine facts removed, record's invocation and synopsis grown, 99 facts. write.rs WRITE_OPS: record review (human judgment), record task, record result, record gate-result, record sprint, record mint. hardening.rs: dispatch floor 40 with the fold history in the comment. Fixture and test renames in control_structure.rs, view/mod.rs, serve.rs, stpa_diagram.rs, reports.rs meta generator. Rust prose 39 sites across 10 files by the transform's rule; argv sites 8 across 4 test files by hand; write.feature titles. Transform applied: 41 sites across 22 files, re-plan 0 (usage.md 8, reverify.toml 4 comments, CLAUDE.md 4, sprint-closeout 3, claude-md-template 3, render 2, viewpoint-registry 2, fifteen single-site files). CLAUDE.md section 4, README.md and claude-md-template by hand where the transform's rule did not reach. tests/capability_refusal_bites.rs: the_record_sub_verbs_match_the_fact reads cmd_record and record_authoring_subverb arms and the record fact's invocation from source and holds them equal. keel sync-claude: 46/46 skills, --check matches. Clippy: cmd_record over 100 lines and an indexing slice - hoisted into record_authoring_subverb (get(1..)) and print_record_usage."; }
    // RAN: cargo build --release -p keel-cli: Finished (1m31s after the last edit); transform --apply 41/22 then re-plan 0 (diffcheck680.txt: 47 removed / 38 added lines, every removed line explained by the D0451 table except the facts script own 9 removals and the grown cliRecord); fold680_clippy.py + fold680_clippy2.py: record_authoring_subverb (get(1..)) and print_record_usage hoisted, clippy Finished; fold680_bare.py: 5 bare prose mentions each asserted once; fold680_subverb_test.py: the_record_sub_verbs_match_the_fact inserted; keel sync-claude: 46/46 skills, --check matches; keel record . : usage naming thirteen sub-verbs, exit 2
    part authoringFamilyFoldImplementGateR1 : TestResult { :>> id = "fc0a80fb-85c1-47a1-9d6a-973f574fefd5"; :>> outcome = VerdictKind::pass; :>> judgedAgainst = "ceaabdd"; :>> judgedAt = "2026-09-11"; :>> judgedBy = "claudeOpus5"; }
    verification authoringFamilyFoldReviewGate : Test { :>> id = "c1b3e5c3-2752-44b7-86b1-cb8329999fe3"; :>> title = "Sprint 680 review gate — three passes per D0172"; :>> createdAt = "2026-09-12"; :>> createdBy = "claudeOpus5"; :>> method = VerificationMethod::inspect; :>> procedureText = "Delivered and measured 2026-09-11: compare680.txt - 13 of 13 EQUAL between keel-prefold680.exe (build ceaabdd) and keel-serve.exe on two fresh clones at C:/k680 with the same actor; 5 strictly byte-equal (append-gate-result --file, a bad-task append-result refusal exit 1, reverify --demos with tree 0 B, snapshot-indicators with tree 0 B, the add-task write with tree 2892 B equal after UUID masking); 8 equal under the D0451 rename applied to the OLD binary's text, every one a usage line naming the command (add-task, append-result, apply-review, record-measurement, new sprint, reverify --bogus, new sprint --fill with tree 0 B, mint 0). hardening dispatched 49 of 49, coveragePct 100. `keel add-task` on the new binary prints the record usage, exit 2 - no alias. cargo test --test capability_refusal_bites 6 passed; D0388 pair on the new test: with ` | mint [N]` removed from the invocation it fails naming mint, reverted and 6 passed again. bash_classify: `keel record review --batch f` Ask, `keel record task ...` Clean."; }
    // RAN: python compare680.py > compare680.txt: 13 of 13 EQUAL under the D0451 rename (5 strictly byte-equal), write cases compared on git diff of .tracking in two clones with UUIDs masked and index lines dropped, every renamed case differing only in the usage line naming the command; keel show hardening .: dispatched 49 namedInHelp 49 coveragePct 100; cargo clippy --release --all-targets -- -D warnings: Finished, exit 0; cargo test --test capability_refusal_bites: 6 passed; D0388 pair on the new test: ` | mint [N]` removed from the record invocation -> FAILED naming mint, reverted -> 6 passed; cargo test --bin keel bash: 1 passed
    part authoringFamilyFoldReviewGateR1 : TestResult { :>> id = "cbcf361e-929b-47bf-a019-db1a1e8f7ed3"; :>> outcome = VerdictKind::proposed; :>> judgedAgainst = "ceaabdd"; :>> judgedAt = "2026-09-11"; :>> judgedBy = "claudeOpus5"; }
    verification authoringFamilyFoldCloseOutGate : Test { :>> id = "333b5822-de86-4e6d-a8b9-ab9f820d1528"; :>> title = "Sprint 680 closeOut gate (autonomous, D0049)"; :>> createdAt = "2026-09-12"; :>> createdBy = "claudeOpus5"; :>> method = VerificationMethod::inspect; :>> procedureText = "Sprint 680 closes on the two-clone comparison with the written tree, the hardening read-back, validate, check-engine, guard, sync-claude --check, clippy, the surface and refusal tests and the touched suite. D0451 is staged with this sprint (keystone lock, D0209 cl.2). dcRemainingCliFamilies stays open: two folds remain, D0452 and D0453, both waiting for the human's word on the brief. issue497 is recorded with dcRecordSubVerbsAreControlActions as its resolver."; }
    // RAN: VERIFIER-RECEIPT.txt (haiku, skill test-verify, D0438, verify680/): validate 778 clean exit 0; check-engine clean exit 0; guard --no-receipt PASS 204 actionable warnings 0 violations exit 0; sync-claude --check matches 46 skills exit 0; cargo clippy --release --all-targets -D warnings pass exit 0; D0388 pair: keel record task exit 2 usage, keel add-task exit 2 record usage (verb removed), show hardening dispatched 49 namedInHelp 49; capability_refusal_bites 6 passed; keel suite --touched outcome=fail 780 passed 1 failed 683s at=1789176382 launch=1789175695 head=ceaabdd stems MATCH changed set - the red (control_structure_is_computed.rs:74 asserting cmdAddTask) fixed to cmdRecord by the primary after the receipt, cargo test --test control_structure_is_computed 3 passed, clippy Finished; the land hook re-runs the touched set before the push (D0421)
    part authoringFamilyFoldCloseOutGateR1 : TestResult { :>> id = "73167c1f-443e-4d36-9c71-457739448142"; :>> outcome = VerdictKind::proposed; :>> judgedAgainst = "ceaabdd"; :>> judgedAt = "2026-09-11"; :>> judgedBy = "claudeOpus5"; }
    verification authoringFamilyFoldRetroGate : Test { :>> id = "44963881-74da-470b-91ba-a64a309d5437"; :>> title = "Sprint 680 retro gate (autonomous, D0049)"; :>> createdAt = "2026-09-12"; :>> createdBy = "claudeOpus5"; :>> method = VerificationMethod::analyze; :>> procedureText = "AVOIDABLE-ISSUE SCAN: one, recorded. FINDING: the touched suite went red once on the VERIFIER run (780 passed, 1 failed): control_structure_is_computed.rs:74 asserted the computed action cmdAddTask, a name derived from a folded verb that the transform rule (keel <verb>) cannot see, and the primary had passed only the unit tests naming it (whose fixtures are synthetic). Fixed to cmdRecord, 3 passed. No new item (D0131): the D0425 split caught it before any result was recorded, which is the control working, and issue497 renames every one of these actions next, so a name-bound check written now would be rewritten with them. FINDING: a control bound to a verb's spelling does not follow the verb when it moves - the pre-bash human-judgment check (K7) read one token after keel, so apply-review's Ask would have gone silent at `record review` with every test still green, because no test asked the two-token question. Fixed at the root in this sprint: the check reads verb and verb+sub-verb and bash_classify holds one positive and one negative; no new item (D0131) - the control is in d0451's own commit and the D0452/D0453 folds inherit the two-token check. FINDING: the fold makes the STPA control structure read better by disappearance - seven never-analysed write actions collapsed into cmdRecord, 49/39 to 41/32 open under stpa-currency, and 8 UCA contexts name cmdAppendResult, an action no longer computed. Recorded as issue497, resolved by dcRecordSubVerbsAreControlActions (one computed action per sub-verb of a routing write command; then a stpa-self run over them), which the D0452 and D0453 folds need before they land or the same collapse recurs for gate, audit and github. FINDING: the 679 retro's carried item is closed here - `record`'s sub-verb inventory is now held equal to its router by the_record_sub_verbs_match_the_fact, beside the_lens_inventory_matches_the_router that already held cmd_show to LENS_NAMES; no new item (D0131)."; }
    // RAN: keel record task dcRecordSubVerbsAreControlActions (8c6d2f56) into NextWork then keel record issue -> issue497 with #Resolves from that task, triaged on arrival; keel guard stpa-currency --no-receipt . on the folded tree: 41 actions 32 open, on the stashed pre-fold tree with keel-prefold680.exe: 49 actions 39 open (the finding); grep -c cmdAppendResult engine-ucas.sysml: 8; K7 finding fixed at the root in main.rs bash_classify (two-token) with positive and negative asserts; the 679 carry closed by the_record_sub_verbs_match_the_fact; keel guard retro-backlog --no-receipt .: PASS 1 scanned 0 violations after the three findings named d0451, issue497 and the_record_sub_verbs_match_the_fact
    part authoringFamilyFoldRetroGateR1 : TestResult { :>> id = "3d4476c6-420a-4f88-b86e-9c6f0fe9d293"; :>> outcome = VerdictKind::proposed; :>> judgedAgainst = "ceaabdd"; :>> judgedAt = "2026-09-11"; :>> judgedBy = "claudeOpus5"; }
}
