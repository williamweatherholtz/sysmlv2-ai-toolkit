// ProjectDeliveryS179 — Sprint 179: declarativeExpandEvaluator (D0105 migration, EXPAND step 2).
// Build the generic rule EVALUATOR (`keel rules`) that reads declared Rule elements + evaluate the first
// migrated rule (capabilityRootednessRule) to PARITY with guard:requirement-rootedness. Runs ALONGSIDE
// the 14 guards (nothing retired). Walking skeleton: EdgeRule + appliesWhen="all". EXECUTE. 2 pt. AUTONOMOUS (D0049).
package ProjectDeliveryS179 {
    private import EngineElement::*;
    private import EngineWork::*;
    private import EngineVerification::*;
    private import EngineRelationships::*;

    #CharteredBy dependency from declEvalStory to d0105;

    part declEvalStory : Story {
        :>> id = "63940516-2c7d-4e8f-c179-51627384c001";
        :>> title = "Sprint 179: declarativeExpandEvaluator (2 pt) - `keel rules` generic evaluator + first rule at parity (D0105 EXPAND step 2)";
        :>> createdAt = "2026-07-03"; :>> createdBy = "wweatherholtz"; :>> kind = WorkKind::code; :>> priority = WorkPriority::p1; :>> owner = "claudeOpus"; :>> estimatedPoints = 2;
    }

    action def DeliveryRunS179 {
        action storyDeclEval;
        verification storyDeclEvalDoD : Test { :>> id = "63940516-2c7d-4e8f-c179-51627384c002"; :>> method = VerificationMethod::test; :>> procedureText = "D0105 migration EXPAND step 2. (1) view::check + `keel rules [ROOT]` (main.rs): a GENERIC evaluator that loads declared Rule elements (Model gains .engine/rules/) and evaluates each EdgeRule (subject marker/type must carry requiredEdge, at cardinality, to an existing objectType instance); emits JSON {rules:[{rule,severity,scope,evaluated,violations}], total_violations}. Walking skeleton: EdgeRule + appliesWhen='all' (ElementRule/OrderingRule + full scope sub-language = later EXPAND steps, reported evaluated=false). (2) First migrated rule .engine/rules/rules.sysml capabilityRootednessRule (subject #Capability -> derivedFrom -> Need, atLeastOne), #JustifiedBy d0099. (3) PARITY proven: edge_rule_violations == view::capability_root_violations (unit test edge_rule_evaluator_reaches_parity_with_the_rootedness_guard) AND live: `keel rules .` capabilityRootednessRule 0 violations == `keel guard requirement-rootedness` 0 violations. NAME NOTE: D0105 said `keel check` but that is taken by the spec-compat file checker -> evaluator is `keel rules` for now; the name reconciliation is a tracked follow-up. VALIDATION NOTE: the SCHEMA (rules.sysml) is kernel-validated (validate_schema 16/16); the rule INSTANCE (.engine/rules) is RUST-validated (keel validate phase-1 parse) NOT kernel — it carries a cross-file #JustifiedBy edge to a Decision, which the kernel's per-file model can't resolve, exactly the D0048 reason .tracking uses the rust authority. NOTHING retired (guards still run). VERIFY: kernel validate_schema (16/16) PASS; rule instance rust-parsed clean by keel validate; clippy -D warnings clean; cargo test (incl the parity test) green; keel validate (192) + guard all (14) green."; }
        part storyDeclEvalDoDR1 : TestResult { :>> id = "63940516-2c7d-4e8f-c179-51627384c003"; :>> outcome = VerdictKind::pass; :>> judgedAgainst = "12cfebb"; :>> judgedAt = "2026-07-03"; :>> judgedBy = "claudeOpus"; }
    }

    verification declEvalRefineGate : Test { :>> id = "63940516-2c7d-4e8f-c179-51627384c004"; :>> title = "Sprint 179 refine gate (DoR)"; :>> createdAt = "2026-07-03"; :>> createdBy = "claudeOpus"; :>> method = VerificationMethod::inspect; :>> procedureText = "DoR: EXPAND step 1 (schema) landed (sprint178); step 2 = the evaluator + first rule at parity. estimatedPoints=2. #CharteredBy d0105. DoR met."; }
    part declEvalRefineGateR1 : TestResult { :>> id = "63940516-2c7d-4e8f-c179-51627384c005"; :>> outcome = VerdictKind::pass; :>> judgedAgainst = "12cfebb"; :>> judgedAt = "2026-07-03"; :>> judgedBy = "claudeOpus"; }
    verification declEvalStandupGate : Test { :>> id = "63940516-2c7d-4e8f-c179-51627384c006"; :>> title = "Sprint 179 standup gate"; :>> createdAt = "2026-07-03"; :>> createdBy = "claudeOpus"; :>> method = VerificationMethod::inspect; :>> procedureText = "Approach: reuse view::Model (add .engine/rules); write edge_rule_violations + check(); wire `keel rules` (check name taken); author capabilityRootednessRule; prove parity vs the guard (unit + live). No guard retired this step."; }
    part declEvalStandupGateR1 : TestResult { :>> id = "63940516-2c7d-4e8f-c179-51627384c007"; :>> outcome = VerdictKind::pass; :>> judgedAgainst = "12cfebb"; :>> judgedAt = "2026-07-03"; :>> judgedBy = "claudeOpus"; }
    verification declEvalImplementGate : Test { :>> id = "63940516-2c7d-4e8f-c179-51627384c008"; :>> title = "Sprint 179 implement gate"; :>> createdAt = "2026-07-03"; :>> createdBy = "claudeOpus"; :>> method = VerificationMethod::test; :>> procedureText = "check()/edge_rule_violations/rc_matches_subject added; `keel rules` wired; capabilityRootednessRule authored (.engine/rules); .engine/rules added to Model + validate_instances. LIVE parity: keel rules capabilityRootednessRule 0 == guard requirement-rootedness 0. clippy clean; cargo test incl parity test; keel validate + guard green; kernel schema 16/16 PASS; rule instance rust-validated (cross-file #JustifiedBy, D0048)."; }
    part declEvalImplementGateR1 : TestResult { :>> id = "63940516-2c7d-4e8f-c179-51627384c009"; :>> outcome = VerdictKind::pass; :>> judgedAgainst = "12cfebb"; :>> judgedAt = "2026-07-03"; :>> judgedBy = "claudeOpus"; }
    verification declEvalReviewGate : Test { :>> id = "63940516-2c7d-4e8f-c179-51627384c00a"; :>> title = "Sprint 179 review gate"; :>> createdAt = "2026-07-03"; :>> createdBy = "claudeOpus"; :>> method = VerificationMethod::inspect; :>> procedureText = "Reviewed. The evaluator reuses the existing Model substrate (items+edges+markers), so it stays faithful to how guards read the model; the first rule reaches PARITY both in a unit test (edge_rule_violations == capability_root_violations) and live. Pure EXPAND — the guard still runs, so zero risk. The `keel check`->`keel rules` name collision is honestly flagged, not silently resolved. Clean."; }
    part declEvalReviewGateR1 : TestResult { :>> id = "63940516-2c7d-4e8f-c179-51627384c00b"; :>> outcome = VerdictKind::pass; :>> judgedAgainst = "12cfebb"; :>> judgedAt = "2026-07-03"; :>> judgedBy = "claudeOpus"; }
    verification declEvalCloseOutGate : Test { :>> id = "63940516-2c7d-4e8f-c179-51627384c00c"; :>> title = "Sprint 179 closeOut gate (autonomous, D0049)"; :>> createdAt = "2026-07-03"; :>> createdBy = "claudeOpus"; :>> method = VerificationMethod::inspect; :>> procedureText = "Autonomous closeOut (D0049): DoD pass; the generic evaluator exists + one rule is at parity, alongside the guards. clippy + cargo test + keel validate + guard + kernel all green. Self-evidencing (D0051). EXPAND step 2 done."; }
    part declEvalCloseOutGateR1 : TestResult { :>> id = "63940516-2c7d-4e8f-c179-51627384c00d"; :>> outcome = VerdictKind::pass; :>> judgedAgainst = "12cfebb"; :>> judgedAt = "2026-07-03"; :>> judgedBy = "claudeOpus"; }
    verification declEvalRetroGate : Test { :>> id = "63940516-2c7d-4e8f-c179-51627384c00e"; :>> title = "Sprint 179 retro gate (autonomous, D0049)"; :>> createdAt = "2026-07-03"; :>> createdBy = "claudeOpus"; :>> method = VerificationMethod::analyze; :>> procedureText = "Autonomous retro (D0049). WELL: reusing view::Model made the evaluator small + faithful, and proving parity in BOTH a unit test and live gives the migration a real safety gate from rule #1. AVOIDABLE-ISSUE SCAN: two avoidable frictions - (1) `keel check` was already taken (spec-compat checker) so the D0105 name needs reconciling (flagged, not forced); (2) clippy -D caught 5 lints (doc backticks, map_or_else, doc-paragraph length, HashMap indexing) - the usual keel-cli lint set; LESSON: check for command-name collisions before wiring, and run clippy -D early. Estimate 2 pt held. NEXT: MIGRATE - express more guards as EdgeRules (issues, sprint-coverage, process-skill) + add the scope sub-language (newlyAdded/whereStatus) for charter/ceremony; then ElementRule + OrderingRule; each to parity before CONTRACT retires its guard. The `keel check` name reconciliation is a tracked follow-up."; }
    part declEvalRetroGateR1 : TestResult { :>> id = "63940516-2c7d-4e8f-c179-51627384c00f"; :>> outcome = VerdictKind::pass; :>> judgedAgainst = "12cfebb"; :>> judgedAt = "2026-07-03"; :>> judgedBy = "claudeOpus"; }
}
