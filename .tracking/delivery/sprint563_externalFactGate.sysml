// ProjectDeliveryS563 — Sprint 563: the external-fact gate - a ci-run receipt is checked by CI against the run itself, the one pass an agent cannot talk past. EXECUTE. 5 pts.
package ProjectDeliveryS563 {
    private import EngineElement::*;
    private import EngineWork::*;
    private import EngineVerification::*;
    private import EngineRelationships::*;

    #CharteredBy dependency from externalFactGateStory to d0323;

    part externalFactGateStory : Story {
        :>> id = "03481be6-5d04-4163-a535-29085dd07d41";
        :>> title = "Sprint 563: the external-fact gate - a ci-run receipt is checked by CI against the run itself, the one pass an agent cannot talk past (5 pts)";
        :>> createdAt = "2026-09-05"; :>> createdBy = "claudeOpus5"; :>> kind = WorkKind::code; :>> priority = WorkPriority::p0; :>> owner = "claudeOpus5"; :>> estimatedPoints = 5;
    }

    action def DeliveryRunS563 {
        action storyExternalFactGate;
        verification storyExternalFactGateDoD : Test { :>> id = "50d70faf-8579-4182-b40a-2236742858ed"; :>> method = VerificationMethod::test; :>> procedureText = "DELIVERED BACKLOG ITEMS: dcExternalFactGate (D0323; resolves issue374, stpa-self run 1 UCA-A1). DONE: keel audit-ci-runs [ROOT] [--repo O/N] - every `// RAN: ci-run id=<run> workflow=<name>` receipt in .tracking is verified against gh api: the run exists in this repository, concluded success, ran on the result's judgedAgainst SHA, is the named workflow; a fabricated id, another repository, another tree, a failed run or another workflow fails naming the result; zero receipts reports zero and passes. Wired as a ci.yml gate step with GH_TOKEN; CLI facts in all three homes (commands.sysml, CLI_FACTS 104, COMMAND_NAMES 67); CLAUDE.md §4 names the receipt kind and the CI step. The verdict is a pure function with unit tests on every branch; the first live receipt is this sprint's own DoD result naming CI run 33978282844 for 50175b6."; }
        // RAN: ci-run id=33978282844 workflow=ci; suite 521/0 exit 0 before the ci_runs reader fix, ci_runs 5 tests + clippy after; keel audit-ci-runs . PASS 1 receipt
        part storyExternalFactGateDoDR1 : TestResult { :>> id = "662b8d7f-44f9-4e51-83fd-167a2d0b3027"; :>> outcome = VerdictKind::pass; :>> judgedAgainst = "50175b68d8fb95f333b6d66c7806c580ab3d42b2"; :>> judgedAt = "2026-09-05"; :>> judgedBy = "claudeOpus5"; }
    }

    verification externalFactGateRefineGate : Test { :>> id = "532a0410-9143-4641-896e-2063ae56a1a5"; :>> title = "Sprint 563 refine gate (DoR)"; :>> createdAt = "2026-09-05"; :>> createdBy = "claudeOpus5"; :>> method = VerificationMethod::inspect; :>> procedureText = "READY: the DoD named the mechanism (a result class only an external fact satisfies) and the site (CI, not the agent's command). The design question was the receipt grammar - strict, numeric id plus named workflow, so an ordinary receipt can never be read as a run claim - and the local behaviour: the same command runs when gh is available, but the gate is CI's."; }
    verification externalFactGateStandupGate : Test { :>> id = "5d87f101-e4ed-47f5-8413-355d2e2eb7e6"; :>> title = "Sprint 563 standup gate"; :>> createdAt = "2026-09-05"; :>> createdBy = "claudeOpus5"; :>> method = VerificationMethod::inspect; :>> procedureText = "THE FIRST LIVE RUN FOUND A DEFECT THE UNIT TESTS HAD NOT: the result-line reader had an off-by-one and read judgedAgainst as empty, so the real receipt was refused as a run for a different tree. Fixed, pinned with a unit test on the reader, rebuilt, and the live audit then read PASS - 1 receipt checked against the repository. The full suite ran before that fix; the ci_runs tests (5) and clippy ran after it; the fix touches only ci_runs.rs. ONE THING LEFT DELIBERATELY OUT: the verdict proves the run happened on that tree and concluded success, not that the suite was sufficient - a vacuous green still vouches. That is the residual D0323 states, and D0312 (what a pass means by authority) is where the wider question sits."; }
    verification externalFactGateImplementGate : Test { :>> id = "77e64f09-9b70-4b16-b0b6-7fa692efe635"; :>> title = "Sprint 563 implement gate"; :>> createdAt = "2026-09-05"; :>> createdBy = "claudeOpus5"; :>> method = VerificationMethod::test; :>> procedureText = "RAN: cargo test --lib ci_runs 5 passed (grammar strictness; the DoD's three cases - green run for the judged SHA passes, fabricated id fails naming the result, a run for a different tree fails; failed/other-repo/other-workflow refusals; API shape reduction); clippy -D warnings clean; keel audit-ci-runs . live before the receipt: 0 receipts, exit 0, stated; after the DoD receipt landed: PASS, 1 receipt checked against williamweatherholtz/sysmlv2-ai-toolkit; keel guard cli-surface-declared . PASS 104 scanned after COMMAND_NAMES gained the arm; the full suite in the background to completion (receipt on the DoD result, which itself cites the ci-run)."; }
    verification externalFactGateReviewGate : Test { :>> id = "1ab41476-3e8e-4302-bda5-51cd8a2e4b45"; :>> title = "Sprint 563 review gate — three passes per D0172"; :>> createdAt = "2026-09-05"; :>> createdBy = "claudeOpus5"; :>> method = VerificationMethod::inspect; :>> procedureText = "THREE PASSES. (1) IS THE JUDGE OUTSIDE THE AGENT: yes - the check runs in ci.yml with the workflow's token; the agent's local run is a convenience with the same code. (2) CAN THE RECEIPT BE FAKED: the id and SHA can be typed, and CI then finds no such run or the wrong tree - the failure names the result. (3) IS THE FIRST LIVE RECEIPT REAL: run 33978282844 is CI for 50175b6 (gh run list, success, workflow ci), and the DoD result below is judgedAgainst 50175b6."; }
    verification externalFactGateCloseOutGate : Test { :>> id = "c21bddc6-2ca5-4709-bf83-6e51c7fd9717"; :>> title = "Sprint 563 closeOut gate (autonomous, D0049)"; :>> createdAt = "2026-09-05"; :>> createdBy = "claudeOpus5"; :>> method = VerificationMethod::inspect; :>> procedureText = "CLOSED. D0323 accepted under standing consent; issue374 resolved by computation; CC-A1 binds to a control at the next stpa-self run."; }
    verification externalFactGateRetroGate : Test { :>> id = "9622a658-a14e-4ea8-9a90-e85bfec4497d"; :>> title = "Sprint 563 retro gate (autonomous, D0049)"; :>> createdAt = "2026-09-05"; :>> createdBy = "claudeOpus5"; :>> method = VerificationMethod::analyze; :>> procedureText = "no new item - already tracked: the receipt kind exists but nothing yet REQUIRES it for a class of result - that is d0312 option B's replay mechanism (dcVerificationByAuthority), held with the human; the attestation census counting ci-run receipts as their own kind is a lens change that rides on d0312. The lesson: the first receipt of a new kind should land in the same commit as the check that reads it, so the gate's first CI run is not vacuous."; }
}
