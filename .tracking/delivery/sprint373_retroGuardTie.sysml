// ProjectDeliveryS373 — Sprint 373: the retro-backlog guard ties the item to THE FINDING. First
// increment executed under the freshly-accepted D0172. EXECUTE. 3 pts.
package ProjectDeliveryS373 {
    private import EngineElement::*;
    private import EngineWork::*;
    private import EngineVerification::*;
    private import EngineRelationships::*;

    #CharteredBy dependency from retroTieStory to d0172;

    part retroTieStory : Story {
        :>> id = "0d800700-0814-6700-9b3e-000000300700";
        :>> title = "Sprint 373: a retro finding must name its item — the co-staging loophole closes (3 pts)";
        :>> createdAt = "2026-08-20"; :>> createdBy = "claudeOpus5"; :>> kind = WorkKind::code; :>> priority = WorkPriority::p0; :>> owner = "claudeOpus5"; :>> estimatedPoints = 3;
    }

    action def DeliveryRunS373 {
        action storyRetroTie;
        verification storyRetroTieDoD : Test { :>> id = "0d800701-0814-6701-9b3e-000000300701"; :>> method = VerificationMethod::test; :>> procedureText = "DELIVERED BACKLOG ITEMS: dcRetroGuardTiesFinding, dcAuthorViaWriteTool, dcSharedParsedModel (judged on sprint 358's refutation evidence, closing issue142 and issue167). Clears issue189 under the now-ACCEPTED D0172. THE CHANGE: retro_backlog_warnings no longer returns clean because the commit staged issues.sysml or backlog.sysml AT ALL - the exemption that let one failure class reach five retros and zero items. The exemption is now PER RETRO: the retro's own text must NAME a tracked item (dcCamelCase or issueNNN, word-boundary checked without regex per D0048) or carry a no-item justification. VERIFIED BOTH WAYS in unit tests: a co-staged file no longer excuses an unnamed finding; naming the item or justifying none is clean; prose lookalikes (dc motor, tissue42, reproduced) do not count. ONE EXISTING TEST PINNED THE OLD SEMANTICS and was updated to the accepted ones, with the D0172 citation in its comment - a deliberate semantics change edits the test that guarded the old behaviour, visibly, rather than deleting it. validate 405 clean; check-engine clean; 38 guards ALL PASS; 205 tests; clippy clean."; }
        part storyRetroTieDoDR1 : TestResult { :>> id = "0d800702-0814-6702-9b3e-000000300702"; :>> outcome = VerdictKind::pass; :>> judgedAgainst = "f502d20"; :>> judgedAt = "2026-08-20"; :>> judgedBy = "claudeOpus5"; }
    }

    verification rtRefineGate : Test { :>> id = "0d800703-0814-6703-9b3e-000000300703"; :>> title = "Sprint 373 refine gate (DoR)"; :>> createdAt = "2026-08-20"; :>> createdBy = "claudeOpus5"; :>> method = VerificationMethod::inspect; :>> procedureText = "DoR. Top of the frontier after the accept-all: dcSharedParsedModel needed only its judgment (sprint 358 answered its question and no code remained), then dcRetroGuardTiesFinding - the one concrete implement item D0172's acceptance unblocked. dcAuthorViaWriteTool is method=inspect and its DoD is satisfied by the rule now living in the process, the skill and the item itself; judged in this sprint. estimatedPoints=3."; }
    part rtRefineGateR1 : TestResult { :>> id = "0d800704-0814-6704-9b3e-000000300704"; :>> outcome = VerdictKind::pass; :>> judgedAgainst = "f502d20"; :>> judgedAt = "2026-08-20"; :>> judgedBy = "claudeOpus5"; }

    verification rtStandupGate : Test { :>> id = "0d800705-0814-6705-9b3e-000000300705"; :>> title = "Sprint 373 standup gate"; :>> createdAt = "2026-08-20"; :>> createdBy = "claudeOpus5"; :>> method = VerificationMethod::inspect; :>> procedureText = "Approach: change the exemption's SCOPE, not the guard's shape - per-commit becomes per-retro, the markers and justifications stay, and the naming check is a word-boundary scan with no regex so the guard path stays dependency-light (D0048). The signature keeps its `changed` parameter so existing callers and tests keep their shape, with the unused binding documented rather than removed. No blockers."; }
    part rtStandupGateR1 : TestResult { :>> id = "0d800706-0814-6706-9b3e-000000300706"; :>> outcome = VerdictKind::pass; :>> judgedAgainst = "f502d20"; :>> judgedAt = "2026-08-20"; :>> judgedBy = "claudeOpus5"; }

    verification rtImplementGate : Test { :>> id = "0d800707-0814-6707-9b3e-000000300707"; :>> title = "Sprint 373 implement gate"; :>> createdAt = "2026-08-20"; :>> createdBy = "claudeOpus5"; :>> method = VerificationMethod::test; :>> procedureText = "THE OLD TEST FAILING WAS THE CHANGE WORKING: view::retro_backlog_warns_only_when_a_finding_is_neither_tracked_nor_justified pinned the co-staging exemption and went red the moment the exemption died. It was UPDATED to the accepted semantics with the D0172 citation inline - the honest handling of a deliberate behaviour change is to edit the guarding test visibly, never to delete it or loosen it until it passes. TWO SELF-INFLICTED DEFECTS, both caught by the gate: my test insertion duplicated the scan_count_tests module header (an anchor appended twice - once inside the inserted string, once by the replace), which the release build MISSED because cfg(test) code does not compile under cargo build, and clippy caught; and my word-boundary closure indexed bytes[i-1], the same slicing-may-panic clippy has flagged before. AUTHORED VIA THE WRITE TOOL THROUGHOUT, per dcAuthorViaWriteTool - zero shell-mangling incidents this sprint, the first code sprint of the session with none."; }
    part rtImplementGateR1 : TestResult { :>> id = "0d800708-0814-6708-9b3e-000000300708"; :>> outcome = VerdictKind::pass; :>> judgedAgainst = "f502d20"; :>> judgedAt = "2026-08-20"; :>> judgedBy = "claudeOpus5"; }

    verification rtReviewGate : Test { :>> id = "0d800709-0814-6709-9b3e-000000300709"; :>> title = "Sprint 373 review gate — three passes per D0172"; :>> createdAt = "2026-08-20"; :>> createdBy = "claudeOpus5"; :>> method = VerificationMethod::inspect; :>> procedureText = "PASS 1, CLAIMS vs computed output: the guard run at HEAD reports retro-backlog PASS with the new semantics compiled in; the three new unit tests pass; the full suite is 205 with zero failures; clippy zero - all read from the runs, not the diff. PASS 2, BOUNDARY: prose lookalikes probed explicitly (dc motor, tissue42, reproduced/dcFooBar/issue123 boundaries); the empty-changed-list case exercised; the guard is commit-scoped so an EMPTY commit population scans zero, which is legitimate for this guard and stated in sprint 364's LEGITIMATELY_EMPTY list already. PASS 3, THE SPRINT'S OWN DIFF: found the duplicated module header my own insertion created - cfg(test)-gated, so cargo build passed while the test build was broken; the lesson is that a release build is NOT a compile check for test code, and clippy --all-targets is the instrument that covers both. WHAT A REVIEWER SHOULD ATTACK: the naming check accepts ANY dcCamelCase or issueNNN string in the retro text, not specifically the item the finding produced - a retro citing an unrelated item would satisfy it. That is a real gap, accepted deliberately: tying the name to the finding semantically needs the finding to declare its item structurally, which is a schema conversation, and the current check already converts five-retros-zero-items into impossible."; }
    part rtReviewGateR1 : TestResult { :>> id = "0d80070a-0814-670a-9b3e-00000030070a"; :>> outcome = VerdictKind::pass; :>> judgedAgainst = "f502d20"; :>> judgedAt = "2026-08-20"; :>> judgedBy = "claudeOpus5"; }

    verification rtCloseOutGate : Test { :>> id = "0d80070b-0814-670b-9b3e-00000030070b"; :>> title = "Sprint 373 closeOut gate (autonomous, D0049)"; :>> createdAt = "2026-08-20"; :>> createdBy = "claudeOpus5"; :>> method = VerificationMethod::inspect; :>> procedureText = "Autonomous closeOut (D0049). issue189 cleared; issue142 and issue167 closed by dcSharedParsedModel's judgment on sprint 358's evidence; dcAuthorViaWriteTool judged on the rule being in the process, skill and item. Open issues drop to 13, all demo-gated or awaiting their direction. validate 405 clean; check-engine clean; 38 guards ALL PASS; 205 tests; clippy clean."; }
    part rtCloseOutGateR1 : TestResult { :>> id = "0d80070c-0814-670c-9b3e-00000030070c"; :>> outcome = VerdictKind::pass; :>> judgedAgainst = "f502d20"; :>> judgedAt = "2026-08-20"; :>> judgedBy = "claudeOpus5"; }

    verification rtRetroGate : Test { :>> id = "0d80070d-0814-670d-9b3e-00000030070d"; :>> title = "Sprint 373 retro gate (autonomous, D0049)"; :>> createdAt = "2026-08-20"; :>> createdBy = "claudeOpus5"; :>> method = VerificationMethod::analyze; :>> procedureText = "Autonomous retro (D0049) under rcRecurrence. AVOIDABLE-ISSUE SCAN, run as the recurrence check the new process requires: the duplicated-anchor insertion is occurrence THREE of anchor-based edits going wrong (sprint 360 displaced an attribute, sprint 367 displaced a doc comment, this sprint doubled a header) - by the rule that makes it an item, and it is: tracked as part of dcAuthorViaWriteTool's scope, since all three came from mechanical insertion at a text anchor, and the item's rule now reads: an insertion asserts its pattern AND diffs its result. The clippy slicing-may-panic on bytes[i-1] is occurrence TWO of that exact pattern (sprint 360's help_names had it); no new item - already guarded, clippy blocks it at the gate every time, which is a control that exists and works. WELL: (1) the old test failing was read as the change working, and it was edited visibly with the Decision cited rather than deleted; (2) zero shell-mangling incidents in a code sprint, first of the session - the Write-tool rule held; (3) the review gate names the semantic gap in the naming check honestly instead of claiming the tie is complete. Estimate 3 pts, delivered."; }
    part rtRetroGateR1 : TestResult { :>> id = "0d80070e-0814-670e-9b3e-00000030070e"; :>> outcome = VerdictKind::pass; :>> judgedAgainst = "f502d20"; :>> judgedAt = "2026-08-20"; :>> judgedBy = "claudeOpus5"; }
}
