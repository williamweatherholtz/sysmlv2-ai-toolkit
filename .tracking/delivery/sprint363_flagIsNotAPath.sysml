// ProjectDeliveryS363 — Sprint 363: `keel init --help` scaffolded an engine into a directory named
// `--help` and I committed 277 files of it. A flag is not a path. EXECUTE. 5 pts.
package ProjectDeliveryS363 {
    private import EngineElement::*;
    private import EngineWork::*;
    private import EngineVerification::*;
    private import EngineRelationships::*;

    #CharteredBy dependency from flagPathStory to d0169;

    part flagPathStory : Story {
        :>> id = "0d800660-0814-6660-9b3e-000000300660";
        :>> title = "Sprint 363: a flag is not a path — keel init stops scaffolding into --help (5 pts)";
        :>> createdAt = "2026-08-20"; :>> createdBy = "claudeOpus5"; :>> kind = WorkKind::code; :>> priority = WorkPriority::p0; :>> owner = "claudeOpus5"; :>> estimatedPoints = 5;
    }

    action def DeliveryRunS363 {
        action storyFlagPath;
        verification storyFlagPathDoD : Test { :>> id = "0d800661-0814-6661-9b3e-000000300661"; :>> method = VerificationMethod::test; :>> procedureText = "DELIVERED BACKLOG ITEMS: dcFlagIsNotAPath. Clears issue179 under D0169. `keel init --help` took the flag as its DIR positional, scaffolded a complete engine into a directory literally named `--help`, and 277 FILES WERE COMMITTED INTO THIS REPOSITORY before the CRLF warnings scrolling past in the commit output gave it away. Found by accident during the pass-2 robustness sweep, which ran `<cmd> --help` across every subcommand. THE ROOT CAUSE WAS A BYPASS, NOT MISSING PARSING: `root_arg` has rejected unknown flags all along, and `cmd_init` read `args.first()` directly and never reached it. FIXED by `positional_arg`, which refuses any argument beginning with `-` where a path or name is expected, applied to init / cmd_query1 / governing-version, plus guards on view / activation / hook and three `--`-only filters tightened to any leading dash. VERIFIED BOTH WAYS: `keel init --help` exits 2 and creates ZERO entries; `keel init proj` still scaffolds `.engine`; trace / item / governing-version / hook all exit 2 on a flag-shaped name. The stray tree is removed from git. validate 395 clean; check-engine clean; 38 guards ALL PASS; 193 tests; clippy clean."; }
        part storyFlagPathDoDR1 : TestResult { :>> id = "0d800662-0814-6662-9b3e-000000300662"; :>> outcome = VerdictKind::pass; :>> judgedAgainst = "ddfd095"; :>> judgedAt = "2026-08-20"; :>> judgedBy = "claudeOpus5"; }
    }

    verification fpRefineGate : Test { :>> id = "0d800663-0814-6663-9b3e-000000300663"; :>> title = "Sprint 363 refine gate (DoR)"; :>> createdAt = "2026-08-20"; :>> createdBy = "claudeOpus5"; :>> method = VerificationMethod::inspect; :>> procedureText = "DoR. THIS SPRINT EXISTS BECAUSE OF A DEFECT I INTRODUCED WHILE AUDITING. The pass-2 sweep ran `<cmd> --help` over 75 subcommands; `keel init` accepted `--help` as a directory and wrote 277 files into the repo, which I then committed without reading the file list. Severity Critical rather than High for a reason worth stating: the stray tree contained a full copy of `.engine/reference/decisions`, so it entered the corpus that `validate`, the guards and every census walk. It did not break the gate because the scaffold is internally consistent - that is LUCK, not design, and the same accident with a half-written tree would have. estimatedPoints=5."; }
    part fpRefineGateR1 : TestResult { :>> id = "0d800664-0814-6664-9b3e-000000300664"; :>> outcome = VerdictKind::pass; :>> judgedAgainst = "ddfd095"; :>> judgedAt = "2026-08-20"; :>> judgedBy = "claudeOpus5"; }

    verification fpStandupGate : Test { :>> id = "0d800665-0814-6665-9b3e-000000300665"; :>> title = "Sprint 363 standup gate"; :>> createdAt = "2026-08-20"; :>> createdBy = "claudeOpus5"; :>> method = VerificationMethod::inspect; :>> procedureText = "Approach: one helper, applied everywhere a positional is READ, plus a text-level control asserting nothing bypasses it. The control has to be text-level rather than behavioural because the defect WAS a bypass - no single invocation can demonstrate 'nothing anywhere skips the guard', which is exactly the property that failed. No blockers."; }
    part fpStandupGateR1 : TestResult { :>> id = "0d800666-0814-6666-9b3e-000000300666"; :>> outcome = VerdictKind::pass; :>> judgedAgainst = "ddfd095"; :>> judgedAt = "2026-08-20"; :>> judgedBy = "claudeOpus5"; }

    verification fpImplementGate : Test { :>> id = "0d800667-0814-6667-9b3e-000000300667"; :>> title = "Sprint 363 implement gate"; :>> createdAt = "2026-08-20"; :>> createdBy = "claudeOpus5"; :>> method = VerificationMethod::test; :>> procedureText = "THE CONTROL FOUND ELEVEN MORE BYPASSES THAN I HAD FIXED, and that is the whole return on writing it: I fixed three call sites, wrote the test, and it reported eleven raw `args.first()` reads. Most were keyword dispatches where a flag falls through to an unknown-keyword error, but FOUR were genuine - view (a name that resolves to a file under .engine/views), activate/deactivate (a process or viewpoint name), hook (an event name), and three filters that rejected `--x` while accepting `-x`. I would not have found those four by reading. A SILENT NO-OP ALMOST SHIPPED: my `cmd_hook` patch used a string replace WITHOUT asserting the pattern matched, and the real source has a `use std::io::Read as _;` between the signature and the read - so the replace did nothing and reported success. Three of my four replaces that turn asserted; that one did not, and the test caught it. The lesson is narrow and mechanical: an unasserted replace is a claim that something happened, and this session has now had it be false twice. THE TEST WAS ALSO WRONG TWICE and both were instructive: version one counted every read including keyword matches (11 reported, ~4 real), and version two flagged its OWN doc comment for mentioning the pattern it forbids. VERIFIED BY REGRESSION: re-introducing the init bypass fails the test."; }
    part fpImplementGateR1 : TestResult { :>> id = "0d800668-0814-6668-9b3e-000000300668"; :>> outcome = VerdictKind::pass; :>> judgedAgainst = "ddfd095"; :>> judgedAt = "2026-08-20"; :>> judgedBy = "claudeOpus5"; }

    verification fpReviewGate : Test { :>> id = "0d800669-0814-6669-9b3e-000000300669"; :>> title = "Sprint 363 review gate"; :>> createdAt = "2026-08-20"; :>> createdBy = "claudeOpus5"; :>> method = VerificationMethod::inspect; :>> procedureText = "Reviewed. THE FINDING BEHIND THE FINDING: this is the fourth defect in three passes with the same shape - a surface that does not declare or defend its own boundary. Help omitted 35 commands, the router omitted 3 routes, six commands omitted the failure case for an unknown name, and the argument layer omitted the distinction between a flag and a path. In every case the permissive behaviour was the DEFAULT and the strict behaviour was a separate act nobody was forced to perform. That is a design observation about this codebase, not four unrelated bugs. WHAT I WOULD DEFEND: not deleting the accidental commit from history. The 277 files are removed by a follow-up commit rather than by rewriting, because D0129 forbids rewriting history and a passing TestResult counts as done only while its `judgedAgainst` SHA resolves - erasing the mistake would orphan evidence to hide an embarrassment. The commit that added them stays visible. WHAT I AM UNEASY ABOUT: I committed 277 unread files. `git add -A` is the standing instruction, and it is the right one for not breaking CI, but it means the commit's file list is the only place a stray tree shows up - and I did not read it."; }
    part fpReviewGateR1 : TestResult { :>> id = "0d80066a-0814-666a-9b3e-00000030066a"; :>> outcome = VerdictKind::pass; :>> judgedAgainst = "ddfd095"; :>> judgedAt = "2026-08-20"; :>> judgedBy = "claudeOpus5"; }

    verification fpCloseOutGate : Test { :>> id = "0d80066b-0814-666b-9b3e-00000030066b"; :>> title = "Sprint 363 closeOut gate (autonomous, D0049)"; :>> createdAt = "2026-08-20"; :>> createdBy = "claudeOpus5"; :>> method = VerificationMethod::inspect; :>> procedureText = "Autonomous closeOut (D0049). issue179 cleared; the stray tree removed from git without rewriting history. `every_positional_read_is_flag_guarded` is the permanent control. Pass 3 of the hardening series is complete: 9 findings recorded across three passes, 9 cleared, 4 permanent build-failing controls added. validate 395 clean; check-engine clean; 38 guards ALL PASS; 193 tests; clippy clean."; }
    part fpCloseOutGateR1 : TestResult { :>> id = "0d80066c-0814-666c-9b3e-00000030066c"; :>> outcome = VerdictKind::pass; :>> judgedAgainst = "ddfd095"; :>> judgedAt = "2026-08-20"; :>> judgedBy = "claudeOpus5"; }

    verification fpRetroGate : Test { :>> id = "0d80066d-0814-666d-9b3e-00000030066d"; :>> title = "Sprint 363 retro gate (autonomous, D0049)"; :>> createdAt = "2026-08-20"; :>> createdBy = "claudeOpus5"; :>> method = VerificationMethod::analyze; :>> procedureText = "Autonomous retro (D0049) under D0131's retroTrack. WELL: (1) the accident was recorded as a Critical finding against MYSELF rather than quietly cleaned up, and the commit that caused it stays in history; (2) the control found four bypasses I had missed, which is the second sprint running where a control out-performed my reading; (3) the fix went into one helper rather than six call sites; (4) verified both directions including that `init` still works, because a guard that breaks the happy path is worse than the bug. AVOIDABLE-ISSUE, AND IT IS THE REAL ONE: I committed 277 files without reading the file list. The CRLF warnings were RIGHT THERE in the commit output and I read past them, because I was looking for the success line. A commit's file list is the last place a stray tree is visible before it becomes history, and `git add -A` guarantees there will be one. SECOND AVOIDABLE-ISSUE: an unasserted string replace silently did nothing and reported success - twice now this session. Every mechanical edit asserts its pattern or it is not an edit, it is a hope. THIRD: my own probe caused the defect. A robustness sweep that MUTATES the filesystem should run somewhere disposable; I ran `<cmd> --help` across 75 subcommands inside the live repository. Estimate 5 pts, delivered."; }
    part fpRetroGateR1 : TestResult { :>> id = "0d80066e-0814-666e-9b3e-00000030066e"; :>> outcome = VerdictKind::pass; :>> judgedAgainst = "ddfd095"; :>> judgedAt = "2026-08-20"; :>> judgedBy = "claudeOpus5"; }
}
