// ProjectDeliveryS628 — Sprint 628: A brief's exhibits are measured in a browser before the page can exist, and a page whose text does not fit is removed rather than published (dcExhibitsDoNotHideText, issue390, D0402). EXECUTE. 3 pts.
package ProjectDeliveryS628 {
    private import EngineElement::*;
    private import EngineWork::*;
    private import EngineVerification::*;
    private import EngineRelationships::*;

    #CharteredBy dependency from exhibitsAreMeasuredStory to d0402;

    part exhibitsAreMeasuredStory : Story {
        :>> id = "de2c432a-1fea-41d3-a21a-a5a13f1bf559";
        :>> title = "Sprint 628: A brief's exhibits are measured in a browser before the page can exist, and a page whose text does not fit is removed rather than published (dcExhibitsDoNotHideText, issue390, D0402) (3 pts)";
        :>> createdAt = "2026-09-09"; :>> createdBy = "claudeOpus5"; :>> kind = WorkKind::code; :>> priority = WorkPriority::p0; :>> owner = "claudeOpus5"; :>> estimatedPoints = 3;
    }

    action def DeliveryRunS628 {
        action storyExhibitsAreMeasured;
        verification storyExhibitsAreMeasuredDoD : Test { :>> id = "4f99ac1a-8292-483b-ae46-21066d3eca28"; :>> method = VerificationMethod::test; :>> procedureText = "DELIVERED: scripts/exec_brief/fit_check.py, the geometry sensor: headless Chromium loads the page and every SVG text element reports its rendered box (getBBox) - OVERFLOW past the viewBox, OVERLAP with a sibling, OVERRUN past the drawn box it starts in, and a page that SCROLLS horizontally are findings, each naming figure, kind, pixels and text; 2px tolerance for glyph side bearings at the edge; measured twice, web fonts on and blocked. Four known cases (overflow, overlap, overrun, a fitting figure with a right-anchored label - the false-positive class) run as --probe. assert_fits(out) is the builder's last line: probe, measure, and on any finding remove the page and exit 1, the D0387 shape. The current builder ends in it; the decision-surfacing skill's step 5 names it. The measurement choice and its cost are D0402. VERIFIED: the probe discriminates (4 of 4); the standing brief at 29fb76c measured 12 findings at 0.5px tolerance of which 11 were sub-2px side bearings on edge-set labels and one was real - a box title 7px past its box on the fallback face - so tolerance was set at 2px and the title split, and the rebuilt page measures clean on both passes; a stacked legend with four long labels and a logic note of two lines, built by the shared modules, measure clean and were read as an image with every word present and the legend on two rows."; }
        // RAN: python scripts/exec_brief/fit_check.py --probe: 4 of 4 known cases discriminate (overflow, overlap, overrun, fitting right-anchored); fit_check.py decision-brief.html at 29fb76c: 12 findings at TOL=0.5 (11 sub-2px side bearings, 1 real 7px OVERRUN fig5 fallback face), 1 at TOL=2, 0 after the fig5 title split; legend_verify.py: 4-label stacked legend + two-line note 0 findings, screenshot read; check_templates.py --brief clean, 425 words
        part storyExhibitsAreMeasuredDoDR1 : TestResult { :>> id = "6218de5e-f881-4a60-b591-95e24d668fe9"; :>> outcome = VerdictKind::pass; :>> judgedAgainst = "a651fb3"; :>> judgedAt = "2026-09-09"; :>> judgedBy = "claudeOpus5"; }
    }

    verification exhibitsAreMeasuredRefineGate : Test { :>> id = "e001f0fd-b20f-40d8-ac9a-0750b9cdc8e5"; :>> title = "Sprint 628 refine gate (DoR)"; :>> createdAt = "2026-09-09"; :>> createdBy = "claudeOpus5"; :>> method = VerificationMethod::inspect; :>> procedureText = "READY. Head of keel whats-next at a651fb3. The first half of the DoD (legend and note wrap) was already in the shared modules from issue390; the open half was whether to measure in a browser. Python playwright 1.62 and Chromium are on this host, so the instrument costs one import. D0402 records the choice and auto-accepted as a non-fork; the skill's step 5 edit was first read as needing no process-change marker, and guard process-change refused the commit - SKILL.md is a locked process definition - so the process clause is D0403, marked, proposed, waiting for the human. 3 points: a sensor with probes, builder and skill wiring, the rebuilt page."; }
    // RAN: keel whats-next . at a651fb3: dcExhibitsDoNotHideText at the head; playwright 1.62 + chromium present on host; D0402 recorded and auto-accepted (non-fork); guard process-change refused the SKILL.md edit at commit, so D0403 --process-change was recorded proposed; 3 points
    part exhibitsAreMeasuredRefineGateR1 : TestResult { :>> id = "b5a15e84-af1c-46f4-98c6-1a9bf98c770e"; :>> outcome = VerdictKind::pass; :>> judgedAgainst = "a651fb3"; :>> judgedAt = "2026-09-09"; :>> judgedBy = "claudeOpus5"; }
    verification exhibitsAreMeasuredStandupGate : Test { :>> id = "3b9affaa-3401-4479-8761-6ecba5e94484"; :>> title = "Sprint 628 standup gate"; :>> createdAt = "2026-09-09"; :>> createdBy = "claudeOpus5"; :>> method = VerificationMethod::inspect; :>> procedureText = "Blockers: none. CI carries no browser, so the sensor has no ci-probe marker and CI does not run its probe; the build runs it before every page, and D0402 states the gap and the cost not taken."; }
    // RAN: blockers none; CI has no browser so fit_check carries no ci-probe marker, stated in D0402 and the sensor header
    part exhibitsAreMeasuredStandupGateR1 : TestResult { :>> id = "1534577e-987a-4303-aaab-e3c28be1aca5"; :>> outcome = VerdictKind::pass; :>> judgedAgainst = "a651fb3"; :>> judgedAt = "2026-09-09"; :>> judgedBy = "claudeOpus5"; }
    verification exhibitsAreMeasuredImplementGate : Test { :>> id = "0bf57c44-0529-4347-9fbb-061d35dc9e8b"; :>> title = "Sprint 628 implement gate"; :>> createdAt = "2026-09-09"; :>> createdBy = "claudeOpus5"; :>> method = VerificationMethod::test; :>> procedureText = "The measurement is a page.evaluate over figure svg elements; findings come back as dicts and are formatted once. First real-page run at 0.5px tolerance: 12 findings, 11 of them 1px crossings of the uppercase lane labels set at x=0 and right-anchored counts at x=W-4 - the glyph side bearing, not lost text - and one 7px OVERRUN on the fallback face. Tolerance set to 2px (below a stem width at this size) and the 11 vanished while the 7px finding stayed; the probe's known cases pass at that tolerance. The builder's fig 5 title moved its second clause to the subtitle. The fixture reuses charts.STYLE so the probe measures the brief's own type."; }
    // RAN: fit_check.py --probe 4/4; page at 29fb76c 12 findings at TOL 0.5 -> 1 at TOL 2 (7px OVERRUN, fig5 title, fallback face) -> 0 after title split; builder ends in assert_fits(out_path); rebuilt page fits both passes (fonts on, fonts blocked)
    part exhibitsAreMeasuredImplementGateR1 : TestResult { :>> id = "8b7a8b4f-2510-43e4-849f-8835995a56db"; :>> outcome = VerdictKind::pass; :>> judgedAgainst = "a651fb3"; :>> judgedAt = "2026-09-09"; :>> judgedBy = "claudeOpus5"; }
    verification exhibitsAreMeasuredReviewGate : Test { :>> id = "8a9670db-3058-4540-bac6-174970b18522"; :>> title = "Sprint 628 review gate — three passes per D0172"; :>> createdAt = "2026-09-09"; :>> createdBy = "claudeOpus5"; :>> method = VerificationMethod::inspect; :>> procedureText = "Pass 1 (intent): every VERIFY clause is a measured run - probe 4 of 4, the standing page red then green, the legend and note fixtures green and read as an image. Pass 2 (defects): the tolerance was chosen from the false-positive pattern the first run showed and checked against the one real finding, which survived it; a tolerance chosen to make the page pass would have had to be 8px, and it is 2. The fallback-face pass is the one that found the real defect, which is why it gates rather than warns. Pass 3 (docs): fit_check's header, D0402 and the skill's step 5 state the same rule, the same tolerance and the same CI gap."; }
    // RAN: three passes: every VERIFY clause is a measured run; tolerance 2px chosen from the 11 false positives and checked against the surviving 7px finding; fit_check header, D0402 and SKILL.md step 5 state the same rule and CI gap
    part exhibitsAreMeasuredReviewGateR1 : TestResult { :>> id = "06c2852a-2678-4c17-acb3-ac4eb09e9ef9"; :>> outcome = VerdictKind::pass; :>> judgedAgainst = "a651fb3"; :>> judgedAt = "2026-09-09"; :>> judgedBy = "claudeOpus5"; }
    verification exhibitsAreMeasuredCloseOutGate : Test { :>> id = "d8f897ac-3dea-466a-aee2-609b018667df"; :>> title = "Sprint 628 closeOut gate (autonomous, D0049)"; :>> createdAt = "2026-09-09"; :>> createdBy = "claudeOpus5"; :>> method = VerificationMethod::inspect; :>> procedureText = "A brief now has to fit, measured, or it does not exist to publish. The two defects that were found by looking are the shape a builder can no longer ship, and the third one nobody saw was fixed the day the instrument landed."; }
    // RAN: keel-serve.exe validate . 714 clean; check-engine . clean; guard . --no-receipt ALL PASS after snFitCheck/fbFitCheck were declared in engine-instruments.sysml (instruments-declared had failed on the undeclared script); sync-claude --check matches
    part exhibitsAreMeasuredCloseOutGateR1 : TestResult { :>> id = "d47e5e5f-6716-4f73-83f0-4d026b0e95a6"; :>> outcome = VerdictKind::pass; :>> judgedAgainst = "a651fb3"; :>> judgedAt = "2026-09-09"; :>> judgedBy = "claudeOpus5"; }
    verification exhibitsAreMeasuredRetroGate : Test { :>> id = "a62cf529-ad55-429e-80f8-d858b36fe3f5"; :>> title = "Sprint 628 retro gate (autonomous, D0049)"; :>> createdAt = "2026-09-09"; :>> createdBy = "claudeOpus5"; :>> method = VerificationMethod::analyze; :>> procedureText = "Retro held; avoidable-issue scan: the 7px overrun had passed a screenshot read the same morning, which is the manual-vigilance class D0047 names and the reason this sprint exists - already tracked by issue390 and resolved here. Second finding: the skill edit was committed without a marked Decision on my reading that an instrument is not a process change; guard process-change refused it and D0403 carries the marker - the control held, no new item. One residual stated rather than tracked: the fallback face measured is Chromium's default sans-serif on this host, and another host's fallback may be wider still; the 2px tolerance and the OVERRUN rule leave a margin, and a finding on another host would arrive as an issue with its numbers."; }
    // RAN: avoidable-issue scan: the 7px overrun had passed a screenshot read the same morning - the D0047 manual-vigilance class already tracked by issue390 and resolved here; guard process-change refused the unmarked SKILL.md edit at commit and D0403 now carries the marker - control held, no new item
    part exhibitsAreMeasuredRetroGateR1 : TestResult { :>> id = "6b072b15-cef7-4721-8256-bcbbca1e913b"; :>> outcome = VerdictKind::pass; :>> judgedAgainst = "a651fb3"; :>> judgedAt = "2026-09-09"; :>> judgedBy = "claudeOpus5"; }
}
