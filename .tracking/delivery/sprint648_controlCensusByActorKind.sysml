// ProjectDeliveryS648 — Sprint 648: Deliver dcControlCensusByActorKind: `keel show control-census`, the empirical view of every control by whose act it binds, the ledger's blocks by actor kind, the Issues whose title names it (observed vs code-read) and its evidence class (friction / hypothetical / evidenced), friction and hypothetical first as removal candidates. Chartered by D0426 and the human's words of 2026-09-10 (st116): any guard that has not been abused and gatekeeps them is to be reconsidered or dissolved.. EXECUTE. 3 pts.
package ProjectDeliveryS648 {
    private import EngineElement::*;
    private import EngineWork::*;
    private import EngineVerification::*;
    private import EngineRelationships::*;

    #CharteredBy dependency from controlCensusByActorKindStory to d0426;

    part controlCensusByActorKindStory : Story {
        :>> id = "82dedfc6-b776-4abc-a65d-da02ee3dc5d7";
        :>> title = "Sprint 648: Deliver dcControlCensusByActorKind: `keel show control-census`, the empirical view of every control by whose act it binds, the ledger's blocks by actor kind, the Issues whose title names it (observed vs code-read) and its evidence class (friction / hypothetical / evidenced), friction and hypothetical first as removal candidates. Chartered by D0426 and the human's words of 2026-09-10 (st116): any guard that has not been abused and gatekeeps them is to be reconsidered or dissolved. (3 pts)";
        :>> createdAt = "2026-09-10"; :>> createdBy = "claudeOpus5"; :>> kind = WorkKind::code; :>> priority = WorkPriority::p0; :>> owner = "claudeOpus5"; :>> estimatedPoints = 3;
    }

    action def DeliveryRunS648 {
        action storyControlCensusByActorKind;
        verification storyControlCensusByActorKindDoD : Test { :>> id = "f3626cdc-9298-4a3c-b719-c16923fa9f1e"; :>> method = VerificationMethod::test; :>> procedureText = "The dcControlCensusByActorKindDoD text at HEAD, as amended this sprint (incidents are matched on the Issue TITLE, and a refusal-of-a-correct-act is read from the dissolving Decision's citation, not from the Issue's prose). VERIFY: the unit probe pair in keel-cli/src/view/census.rs (code-read only + zero blocks -> hypothetical; observed -> evidenced), keel-cli/tests/control_census_names_friction.rs on this tree (delegated-words -> friction naming issue397), the CliCommand fact cliControlCensus, CLAUDE.md sec 2 naming the lens."; }
        // RAN: verifier receipt (D0425): validate 736 clean; check-engine clean; guard --no-receipt ALL PASS; gate --fast clean; sync-claude --check matches; control-census summary controls 76 friction 2 hypothetical 65 evidenced 9 unattributedBlocks 1; --help names control-census once; clippy exit 0; cargo test --lib 459 passed 0 failed; control_census_names_friction + reject_has_a_cli_path + capability_refusal_bites + hook_and_push_controls_actually_fire pass
        part storyControlCensusByActorKindDoDR1 : TestResult { :>> id = "64675da4-9f2a-4191-a4ec-de0ba98757fd"; :>> outcome = VerdictKind::pass; :>> judgedAgainst = "c117f35"; :>> judgedAt = "2026-09-10"; :>> judgedBy = "claudeOpus5"; }
    }

    verification controlCensusByActorKindRefineGate : Test { :>> id = "851d7d67-83d7-42a1-8b75-a5f437018fa1"; :>> title = "Sprint 648 refine gate (DoR)"; :>> createdAt = "2026-09-10"; :>> createdBy = "claudeOpus5"; :>> method = VerificationMethod::inspect; :>> procedureText = "Scope: one new lens (view/census.rs) with a pure core (census_rows / classify) so the probe pair runs without a tree; the write-path subject table declared in code; the ledger read directly (D0424 fields); Model reuse from the controls view. Three data corrections in the primary's own Issues: issue397, issue434 and issue447 flagged discoveredInField = true (each reports an act that happened), and write.rs's red-yield obligation records true, since a yield is observed by construction. 3 points (a module with tests)."; }
    part controlCensusByActorKindRefineGateR1 : TestResult { :>> id = "6aa3f790-a50e-4c9e-bef8-acf584215190"; :>> outcome = VerdictKind::pass; :>> judgedAgainst = "c117f35"; :>> judgedAt = "2026-09-10"; :>> judgedBy = "claudeOpus5"; }
    verification controlCensusByActorKindStandupGate : Test { :>> id = "7ceddcd2-4f2d-485c-a464-dbfda3a1511e"; :>> title = "Sprint 648 standup gate"; :>> createdAt = "2026-09-10"; :>> createdBy = "claudeOpus5"; :>> method = VerificationMethod::inspect; :>> procedureText = "Blocker met and resolved in-sprint: two classification rules were tried and read wrong against known cases before the tree was trusted (D0388) - a word-match on `refus` classed issue256 (tool output injected) as friction, and a title+description match credited three controls with issue447 as an observed incident when its description names them as NOT friction. Both rules were replaced: the act is read from the dissolving Decision's citation; the incident is matched on the title."; }
    part controlCensusByActorKindStandupGateR1 : TestResult { :>> id = "ee13bd9f-7966-48ce-8fa6-2a95b31d9c52"; :>> outcome = VerdictKind::pass; :>> judgedAgainst = "c117f35"; :>> judgedAt = "2026-09-10"; :>> judgedBy = "claudeOpus5"; }
    verification controlCensusByActorKindImplementGate : Test { :>> id = "577bc8fd-eb0d-43a1-9044-d3e5eed77a28"; :>> title = "Sprint 648 implement gate"; :>> createdAt = "2026-09-10"; :>> createdBy = "claudeOpus5"; :>> method = VerificationMethod::test; :>> procedureText = "keel-cli/src/view/census.rs (new lens, WRITE_PATH_CHECKS table, probe-pair unit tests), keel-cli/tests/control_census_names_friction.rs, dispatch in main.rs, serve.rs, cli_surface.rs LENS_NAMES (38), cli_facts.rs CLI_FACTS (108), .engine/cli/commands.sysml cliControlCensus, CLAUDE.md sec 2, write.rs obligation discoveredInField = true, backlog DoD amendment, three Issue flags."; }
    // RAN: verifier receipt (D0425): validate 736 clean; check-engine clean; guard --no-receipt ALL PASS; gate --fast clean; sync-claude --check matches; clippy exit 0; cargo test --lib 459 passed 0 failed; control_census_names_friction + reject_has_a_cli_path + capability_refusal_bites + hook_and_push_controls_actually_fire pass
    part controlCensusByActorKindImplementGateR1 : TestResult { :>> id = "8b821bec-06b2-4ebf-9252-054cb6b343d0"; :>> outcome = VerdictKind::pass; :>> judgedAgainst = "c117f35"; :>> judgedAt = "2026-09-10"; :>> judgedBy = "claudeOpus5"; }
    verification controlCensusByActorKindReviewGate : Test { :>> id = "6f689bfc-ed92-4395-8f4d-7c6a999be379"; :>> title = "Sprint 648 review gate — three passes per D0172"; :>> createdAt = "2026-09-10"; :>> createdBy = "claudeOpus5"; :>> method = VerificationMethod::inspect; :>> procedureText = "On this tree: 76 controls, 2 friction (accept:delegated-words naming issue397; tap:unsigned naming issue447), 65 hypothetical, 9 evidenced, 1 unattributed pre-D0424 block. The 65 hypothetical rows are the human's candidate list; each removal is its own Decision (D0303) and is NOT taken here."; }
    part controlCensusByActorKindReviewGateR1 : TestResult { :>> id = "d6231d0a-e0c6-4f1a-bcac-e98832ff1d6b"; :>> outcome = VerdictKind::pass; :>> judgedAgainst = "c117f35"; :>> judgedAt = "2026-09-10"; :>> judgedBy = "claudeOpus5"; }
    verification controlCensusByActorKindCloseOutGate : Test { :>> id = "d9b66847-9f5b-4358-a617-adf72a7e63b0"; :>> title = "Sprint 648 closeOut gate (autonomous, D0049)"; :>> createdAt = "2026-09-10"; :>> createdBy = "claudeOpus5"; :>> method = VerificationMethod::inspect; :>> procedureText = "Recorded by the RECORDER subagent from the verifier's receipt (D0425); the primary wrote no ceremony result."; }
    part controlCensusByActorKindCloseOutGateR1 : TestResult { :>> id = "ed8a5121-d542-4013-b5d1-bdf62e957760"; :>> outcome = VerdictKind::pass; :>> judgedAgainst = "c117f35"; :>> judgedAt = "2026-09-10"; :>> judgedBy = "claudeOpus5"; }
    verification controlCensusByActorKindRetroGate : Test { :>> id = "ddca162c-1e0d-4d25-807d-7ed863b08486"; :>> title = "Sprint 648 retro gate (autonomous, D0049)"; :>> createdAt = "2026-09-10"; :>> createdBy = "claudeOpus5"; :>> method = VerificationMethod::analyze; :>> procedureText = "Avoidable-issue scan: the primary's first two incident rules were stated from the DoD's definition and only found wrong when read back against issue256 and issue447 - D0388's probe-before-statement held only because the read-back was done before any claim was made. Process improvement carried: the two misreads are already tracked in dcControlCensusByActorKind's own DoD text so a successor does not retry them; no new item. The D0425 verifier/recorder split ran as designed."; }
    part controlCensusByActorKindRetroGateR1 : TestResult { :>> id = "2def1705-1ee1-4a4a-8cce-bc8fb4a512e8"; :>> outcome = VerdictKind::pass; :>> judgedAgainst = "c117f35"; :>> judgedAt = "2026-09-10"; :>> judgedBy = "claudeOpus5"; }
}
