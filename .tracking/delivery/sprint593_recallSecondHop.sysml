// ProjectDeliveryS593 — Sprint 593: recall takes a second hop from the row a payload is about, and the benchmark gains the arm that could choose it. EXECUTE. 3 pts.
package ProjectDeliveryS593 {
    private import EngineElement::*;
    private import EngineWork::*;
    private import EngineVerification::*;
    private import EngineRelationships::*;

    #CharteredBy dependency from recallSecondHopStory to d0365;

    part recallSecondHopStory : Story {
        :>> id = "7b873d48-09ad-4b2a-8cc1-4de554a6f04a";
        :>> title = "Sprint 593: recall takes a second hop from the row a payload is about, and the benchmark gains the arm that could choose it (3 pts)";
        :>> createdAt = "2026-09-07"; :>> createdBy = "claudeFable5"; :>> kind = WorkKind::code; :>> priority = WorkPriority::p0; :>> owner = "claudeFable5"; :>> estimatedPoints = 3;
    }

    action def DeliveryRunS593 {
        action storyRecallSecondHop;
        verification storyRecallSecondHopDoD : Test { :>> id = "a6755b9a-21a5-4a5d-974f-902ac1645e95"; :>> method = VerificationMethod::test; :>> procedureText = "DELIVERED BACKLOG ITEMS: recallRanksLinkedRecordsAsWellAsGrepDoes (resolves issue367), open and FAILING since 2026-09-04 across three sprints. Chartered by D0365, layered on D0364. DONE: recall_bench.py takes --hops 2, drawing each query from a record two edges from the target through an intermediate whose words are removed too, sampled by the same seeded mechanical rule as the default arm; and the ranker, after folding its seed-keyed signals, reads its own ranking - when the top row scores at least 1.25 times the second, that row is the source and its neighbours and theirs inherit its score. VERIFIED, both clauses of the criterion: first clause, recall_bench.py seed 20260828, 50 cases - KG 49/50 in a mean 13 ranked rows against grep-plus-one-hop's 47/50 in a mean 14 unranked candidates, median position 3, McNemar p=0.000 on 44 discordant pairs; second clause, recall_ab.py 7/8 against the required 7/8, stable across three consecutive runs, with the rebase question's d0129 arriving at position 8. The mechanism was chosen on the two-hop arm before the hand set was read and no parameter was moved afterwards. Gate: keel suite 570 passed 0 failed (receipt 91238ffbf2c6), validate 674 clean, check-engine clean, guard ALL PASS, clippy -D warnings clean."; }
        // RAN: keel suite 570 passed 0 failed (receipt 91238ffbf2c6); recall_bench.py 49/50 in mean 13 rows vs control+1hop 47/50 in mean 14, median 3, McNemar p=0.000; recall_bench.py --hops 2 22/50 vs control+1hop 8/50; recall_ab.py 7/8 x3 consecutive runs; validate 674; check-engine clean; guard ALL PASS; clippy -D warnings clean
        part storyRecallSecondHopDoDR1 : TestResult { :>> id = "df7901d9-e141-49cf-8f91-a195af75c245"; :>> outcome = VerdictKind::pass; :>> judgedAgainst = "018315ace003b7751ab5cb31f5ab653f2faa58bf"; :>> judgedAt = "2026-09-07"; :>> judgedBy = "claudeOpus5"; }
    }

    verification recallSecondHopRefineGate : Test { :>> id = "8da1e1d1-8a95-4de0-8229-7f35e0489cb0"; :>> title = "Sprint 593 refine gate (DoR)"; :>> createdAt = "2026-09-07"; :>> createdBy = "claudeFable5"; :>> method = VerificationMethod::inspect; :>> procedureText = "READY, and the scope changed once during refine on evidence. The frontier's top item had failed three sprints, so the first act was to diagnose rather than to build: a per-component ranking dump showed the two remaining hand-set misses are not one problem but two. The rebase question's d0129 sits at rank 63, reached at two hops, behind a top row scoring 31.5 against the second's 17.1 - the exact shape of the one mechanism the criterion named and nobody had tried. The obligation question's d0176 is not reached at all, and issue391 already records why and puts the measurement-definition question to the human. So this sprint takes the reachable half and leaves the definition question where it is: 7/8 clears the bar without touching ground truth, which is the outcome issue391 hoped for and could not assume. Sized 3: a research loop with a measurement cycle of several minutes and an unknown number of iterations, which is not a 2."; }
    // RAN: keel suite 570 passed 0 failed (receipt 91238ffbf2c6); recall_bench.py 49/50@13 and --hops 2 22/50; recall_ab.py 7/8 x3; validate 674; guard ALL PASS; clippy clean
    part recallSecondHopRefineGateR1 : TestResult { :>> id = "9bd97536-913f-4c99-91a0-586ec2ecd29b"; :>> outcome = VerdictKind::pass; :>> judgedAgainst = "018315ace003b7751ab5cb31f5ab653f2faa58bf"; :>> judgedAt = "2026-09-07"; :>> judgedBy = "claudeOpus5"; }
    verification recallSecondHopStandupGate : Test { :>> id = "02b2b3b8-c16f-4527-9f40-876c6e93673f"; :>> title = "Sprint 593 standup gate"; :>> createdAt = "2026-09-07"; :>> createdBy = "claudeFable5"; :>> method = VerificationMethod::inspect; :>> procedureText = "NO BLOCKER AND NO SIGNATURE OWED. Both Decisions are non-fork and carry no process-change or safety-change marker, so record-time standing consent applies and neither waits on the human. The four Decisions already in the authority queue (d0360 to d0363) are untouched by this work."; }
    // RAN: keel suite 570 passed 0 failed (receipt 91238ffbf2c6); recall_bench.py 49/50@13 and --hops 2 22/50; recall_ab.py 7/8 x3; validate 674; guard ALL PASS; clippy clean
    part recallSecondHopStandupGateR1 : TestResult { :>> id = "17309615-7a80-4a8e-b786-b863677f50a6"; :>> outcome = VerdictKind::pass; :>> judgedAgainst = "018315ace003b7751ab5cb31f5ab653f2faa58bf"; :>> judgedAt = "2026-09-07"; :>> judgedBy = "claudeOpus5"; }
    verification recallSecondHopImplementGate : Test { :>> id = "30704f34-f295-4b63-8b7b-424c9b1d141d"; :>> title = "Sprint 593 implement gate"; :>> createdAt = "2026-09-07"; :>> createdBy = "claudeFable5"; :>> method = VerificationMethod::test; :>> procedureText = "RAN, in this order, because the order is the method. Diagnosed first with a component dump behind KEEL_RECALL_DEBUG, which is what turned 'not shown' into 'rank 63, own score only'. Wired the KEEL_RECALL_* knobs both harnesses have passed through since D0325 and nothing had read. Swept the mechanism on the default arm: six configurations, all identical to off - the arm cannot see a second hop, which became D0364 and issue405. Built the two-hop arm and swept there against a rule fixed before the sweep; took DOMINANCE 1.25 as the strongest setting that costs the near arm nothing. Only then ran recall_ab.py: 7/8. Extracted the score fold into rank_reached and the dump into dump_ranking when clippy's line limit refused the function, which left it better than it was. Unit test pins both halves of the mechanism - the dominated chain carries its two-hop neighbour, the flat field gets nothing."; }
    // RAN: keel suite 570 passed 0 failed (receipt 91238ffbf2c6); recall_bench.py 49/50@13 and --hops 2 22/50; recall_ab.py 7/8 x3; validate 674; guard ALL PASS; clippy clean
    part recallSecondHopImplementGateR1 : TestResult { :>> id = "523433ba-767e-4064-bc5a-a50a25042f52"; :>> outcome = VerdictKind::pass; :>> judgedAgainst = "018315ace003b7751ab5cb31f5ab653f2faa58bf"; :>> judgedAt = "2026-09-07"; :>> judgedBy = "claudeOpus5"; }
    verification recallSecondHopReviewGate : Test { :>> id = "2d8ea5d8-7d65-40f1-9bd4-13a0db06f0af"; :>> title = "Sprint 593 review gate — three passes per D0172"; :>> createdAt = "2026-09-07"; :>> createdBy = "claudeFable5"; :>> method = VerificationMethod::inspect; :>> procedureText = "THREE PASSES per D0172. (1) IS THE NUMBER HONEST: the 7/8 was read after the choice, not before, and the parameters were not touched afterwards - that sequence is the whole value of the result and it is recorded in D0365 in the order it happened. The one-hop arm's top-three placements fall 30/49 to 28/49, which the pre-stated rule did not cover; it is written into the Decision's consequences rather than left out. (2) DID I FIT ANYTHING TO THE HAND SET: no, and the temptation was concrete - DOMINANCE 1.1 and 1.0 score far better on the two-hop arm and would very likely have carried the hand set higher, and the pre-stated no-regression rule refuses them. Ground truth was not touched. (3) DID THE CONTROLS CATCH ME: twice. The pre-bash hook denied a heredoc carrying backslashes while I was adding an edge to a Decision file, which is D0309 firing exactly as designed; and clippy's too-many-lines refused the function I had grown, which forced the extraction."; }
    // RAN: keel suite 570 passed 0 failed (receipt 91238ffbf2c6); recall_bench.py 49/50@13 and --hops 2 22/50; recall_ab.py 7/8 x3; validate 674; guard ALL PASS; clippy clean
    part recallSecondHopReviewGateR1 : TestResult { :>> id = "a053722b-1618-4d28-88ac-91e338265372"; :>> outcome = VerdictKind::pass; :>> judgedAgainst = "018315ace003b7751ab5cb31f5ab653f2faa58bf"; :>> judgedAt = "2026-09-07"; :>> judgedBy = "claudeOpus5"; }
    verification recallSecondHopCloseOutGate : Test { :>> id = "ef1f84bd-cccd-4e36-a78d-8237101751fa"; :>> title = "Sprint 593 closeOut gate (autonomous, D0049)"; :>> createdAt = "2026-09-07"; :>> createdBy = "claudeFable5"; :>> method = VerificationMethod::inspect; :>> procedureText = "CLOSED. The graph now follows an edge away from the record a payload is about, not only away from the words a prompt used - and the benchmark can see it do so."; }
    // RAN: keel suite 570 passed 0 failed (receipt 91238ffbf2c6); recall_bench.py 49/50@13 and --hops 2 22/50; recall_ab.py 7/8 x3; validate 674; guard ALL PASS; clippy clean
    part recallSecondHopCloseOutGateR1 : TestResult { :>> id = "2d502f35-9b63-4239-8bb9-6724c5d018b6"; :>> outcome = VerdictKind::pass; :>> judgedAgainst = "018315ace003b7751ab5cb31f5ab653f2faa58bf"; :>> judgedAt = "2026-09-07"; :>> judgedBy = "claudeOpus5"; }
    verification recallSecondHopRetroGate : Test { :>> id = "6b79ff58-e49c-45ae-8bd9-5ed218f4162d"; :>> title = "Sprint 593 retro gate (autonomous, D0049)"; :>> createdAt = "2026-09-07"; :>> createdBy = "claudeFable5"; :>> method = VerificationMethod::analyze; :>> procedureText = "AVOIDABLE-ISSUE SCAN HELD. Two new items, both recorded with resolvers. issue405: six configurations returned identical numbers and that neutrality is not a result but the set declining to answer - read as a result it licenses either fitting to the hand set or discarding a working mechanism, and D0325 did the second to the rare-term narrowing on exactly this evidence; a sweep must now state COULD NOT CHOOSE rather than leave a silence the reader fills in. issue406, and this one is mine: I ran recall_ab.py while the linker was still settling the image and got 6/8, one step after refactoring the very function under measurement - the obvious reading was that my refactor had broken it, and the only reasons I did not act on that reading were the latency line and re-running. It is the issue386 family arriving in the measurement harnesses. Already tracked, no new item: issue391 keeps its open definition question, now less urgent because the bar was cleared without it; issue394 keeps its open half. The lesson worth carrying past both: when a benchmark says nothing at every setting, the first hypothesis should be that the benchmark cannot see the thing, not that the thing does nothing."; }
    // RAN: keel suite 570 passed 0 failed (receipt 91238ffbf2c6); recall_bench.py 49/50@13 and --hops 2 22/50; recall_ab.py 7/8 x3; validate 674; guard ALL PASS; clippy clean
    part recallSecondHopRetroGateR1 : TestResult { :>> id = "f90ce742-05ee-4167-a7d6-61401c04a385"; :>> outcome = VerdictKind::pass; :>> judgedAgainst = "018315ace003b7751ab5cb31f5ab653f2faa58bf"; :>> judgedAt = "2026-09-07"; :>> judgedBy = "claudeOpus5"; }
}
