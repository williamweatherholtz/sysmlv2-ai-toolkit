// ProjectDeliveryS615 — Sprint 615: Sprint 615 counts the memory channel's degradation (dcHookDegradationIsCounted, resolves issue402) under D0389: the user-prompt hook writes a recall-skipped ledger event when it drops the facts, keel enforcement-report reports every event's latency distribution and the recall skip rate with the turns it cost, CLAUDE.md's best-case per-edit figure becomes the rule that a cost is a distribution, and the cap's fate is put to the human as D0390 with the ledger's numbers.. EXECUTE. 2 pts.
package ProjectDeliveryS615 {
    private import EngineElement::*;
    private import EngineWork::*;
    private import EngineVerification::*;
    private import EngineRelationships::*;

    #CharteredBy dependency from hookCostIsADistributionStory to d0389;

    part hookCostIsADistributionStory : Story {
        :>> id = "7af37b2a-bb62-4940-b1b8-c0c1165a9795";
        :>> title = "Sprint 615: Sprint 615 counts the memory channel's degradation (dcHookDegradationIsCounted, resolves issue402) under D0389: the user-prompt hook writes a recall-skipped ledger event when it drops the facts, keel enforcement-report reports every event's latency distribution and the recall skip rate with the turns it cost, CLAUDE.md's best-case per-edit figure becomes the rule that a cost is a distribution, and the cap's fate is put to the human as D0390 with the ledger's numbers. (2 pts)";
        :>> createdAt = "2026-09-08"; :>> createdBy = "claudeOpus5"; :>> kind = WorkKind::code; :>> priority = WorkPriority::p0; :>> owner = "claudeOpus5"; :>> estimatedPoints = 2;
    }

    action def DeliveryRunS615 {
        action storyHookCostIsADistribution;
        verification storyHookCostIsADistributionDoD : Test { :>> id = "83223a7b-4a94-499d-9876-d474fce61adf"; :>> method = VerificationMethod::test; :>> procedureText = "DONE MEANS: a hook that degrades says so where someone can count it, and a documented cost matches the distribution rather than the best case. Resolves issue402: the recall payload is dropped when its walk exceeds the 2,500ms cap - 18 times in 808 fires, with a maximum of 33.5 seconds - so the agent's memory channel is least available exactly when the machine is busiest, and nothing records which turns went without facts. In the same ledger the per-edit tier documented at about 0.35 seconds has a median of 0ms and a maximum of 54.4 seconds. DO: count the skips as a fact rather than a transcript line, so the rate is readable after the fact; state the documented cost of a gating tier as a distribution; and decide, from the ledger rather than by feel, whether the cap should rise, the walk should get faster, or the skip should be surfaced to the turn that lost its facts. VERIFY: the skip rate and the tail are computed from .keel/metrics/hooks.jsonl rather than estimated; a turn whose recall was skipped can be identified afterwards; and CLAUDE.md's stated per-edit cost is one a reader would recognise from the measured distribution."; }
        // RAN: recall-skipped event; enforcement-report latency distribution + recall section, 4 tests; CLAUDE.md rule; D0389 accepted, D0390 proposed for the human
        part storyHookCostIsADistributionDoDR1 : TestResult { :>> id = "b94eb44a-0bfe-40bc-b295-0929f6db42f9"; :>> outcome = VerdictKind::pass; :>> judgedAgainst = "d071820522e8332e406c87feb67e28721d7a395a"; :>> judgedAt = "2026-09-08"; :>> judgedBy = "claudeOpus5"; }
    }

    verification hookCostIsADistributionRefineGate : Test { :>> id = "f584e631-9e49-4104-bd12-4a9d07a8a71a"; :>> title = "Sprint 615 refine gate (DoR)"; :>> createdAt = "2026-09-08"; :>> createdBy = "claudeOpus5"; :>> method = VerificationMethod::inspect; :>> procedureText = "Scope: keel-cli/src/main.rs (recall-skipped event, session threaded into the hook); keel-cli/src/pm.rs (latency, event_rows, recall_degradation, three tests); CLAUDE.md section 5; D0389 (instrumentation, in consent) and D0390 (the cap's fate, process-change, proposed). Out of scope: changing what the hook does past the cap - that is D0390's answer, implemented when the human gives it. Estimate 2 points: a ledger event, a report extension with tests, a doc rule, two Decisions. DoR: points set, charter d0389, scope clear, no blocking dependency, DoD authored."; }
    // RAN: DoR inspected: 2 points, charter d0389, scope in the refine text, DoD authored, no blocking dependency
    part hookCostIsADistributionRefineGateR1 : TestResult { :>> id = "311a097e-e3fb-43a1-b995-014b37b11757"; :>> outcome = VerdictKind::pass; :>> judgedAgainst = "d071820522e8332e406c87feb67e28721d7a395a"; :>> judgedAt = "2026-09-08"; :>> judgedBy = "claudeOpus5"; }
    verification hookCostIsADistributionStandupGate : Test { :>> id = "bf386ad4-e666-4422-b4c6-5a281a5fca26"; :>> title = "Sprint 615 standup gate"; :>> createdAt = "2026-09-08"; :>> createdBy = "claudeOpus5"; :>> method = VerificationMethod::inspect; :>> procedureText = "Plan: (1) read the ledger with a scratch script probed against its own shape, then make keel enforcement-report compute the same numbers; (2) recall-skipped emitted from recalled_facts with the session; (3) per-event median/p90/p99/max by nearest rank, and a recall section; (4) tests: the percentile rule on the ledger's own shape, a skip counted with its turn named, the schema freeze untouched; (5) CLAUDE.md: the 0.35 s figure becomes the distribution rule and the report pointer; (6) D0389 and D0390; gates."; }
    // RAN: plan of six steps recorded in the standup text; all six executed in this commit
    part hookCostIsADistributionStandupGateR1 : TestResult { :>> id = "0bc4e39d-0155-4ad3-8b62-3a827a567f4e"; :>> outcome = VerdictKind::pass; :>> judgedAgainst = "d071820522e8332e406c87feb67e28721d7a395a"; :>> judgedAt = "2026-09-08"; :>> judgedBy = "claudeOpus5"; }
    verification hookCostIsADistributionImplementGate : Test { :>> id = "2001b792-8773-4cb5-b389-3b737c6576cf"; :>> title = "Sprint 615 implement gate"; :>> createdAt = "2026-09-08"; :>> createdBy = "claudeOpus5"; :>> method = VerificationMethod::test; :>> procedureText = "RAN: cargo build --release; cargo clippy --release --all-targets -D warnings; cargo test --release --lib pm::; keel enforcement-report . read back against the scratch analysis; keel guard judgment-request-quality; keel gate --fast; keel guard."; }
    // RAN: cargo build --release clean; cargo clippy --release --all-targets -D warnings exit 0; cargo test --release --lib pm:: 4 passed 0 failed; keel enforcement-report . : user-prompt fires 941 msMedian 760 msP90 1385 msP99 12225 msMax 33503, post-edit 1694 fires 0/0/2323/54439, recall.skipped 0 with the pre-D0389 note - equal to the scratch ledger_stats.py figures; keel guard judgment-request-quality PASS 2 scanned; keel gate --fast clean
    part hookCostIsADistributionImplementGateR1 : TestResult { :>> id = "4c00bf2b-3a8e-48af-8fe2-5481e6b7e879"; :>> outcome = VerdictKind::pass; :>> judgedAgainst = "d071820522e8332e406c87feb67e28721d7a395a"; :>> judgedAt = "2026-09-08"; :>> judgedBy = "claudeOpus5"; }
    verification hookCostIsADistributionReviewGate : Test { :>> id = "bd569890-a4ac-4586-b341-506b41bc5251"; :>> title = "Sprint 615 review gate — three passes per D0172"; :>> createdAt = "2026-09-08"; :>> createdBy = "claudeOpus5"; :>> method = VerificationMethod::inspect; :>> procedureText = "Reviewed against the DoD: the rate and tail come from hooks.jsonl through keel enforcement-report, matching the independent analysis figure for figure (user-prompt median 760, p90 1385, p99 12225, max 33503; post-edit 0/0/2323/54439); a skipped turn is a recall-skipped line with ts and session, listed in the report; CLAUDE.md no longer states 0.35 s and names the distribution; the cap decision is D0390 with every number from the ledger and the code path that shows a drop saves nothing."; }
    // RAN: reviewed against the DoD: rate and tail computed from hooks.jsonl by the report and cross-checked; a skipped turn is a ledger line with ts and session and the report lists them (test recall_skips_are_counted_with_the_turns_they_cost); CLAUDE.md states the distribution rule and no longer 0.35 s; the cap fate is D0390 with the code path and the ledger numbers
    part hookCostIsADistributionReviewGateR1 : TestResult { :>> id = "09d4da34-5f1c-438f-b9c0-0003ff819164"; :>> outcome = VerdictKind::pass; :>> judgedAgainst = "d071820522e8332e406c87feb67e28721d7a395a"; :>> judgedAt = "2026-09-08"; :>> judgedBy = "claudeOpus5"; }
    verification hookCostIsADistributionCloseOutGate : Test { :>> id = "b6523148-09dd-41a4-b2ec-ba479254785b"; :>> title = "Sprint 615 closeOut gate (autonomous, D0049)"; :>> createdAt = "2026-09-08"; :>> createdBy = "claudeOpus5"; :>> method = VerificationMethod::inspect; :>> procedureText = "Sprint 615 closes when dcHookDegradationIsCountedDoD carries a pass at the commit that carries the event, the report, the doc rule and both Decisions, and issue402 leaves keel show open-issues."; }
    // RAN: DoD pass recorded on storyHookCostIsADistributionDoD and dcHookDegradationIsCountedDoD at this SHA; issue402 resolution read back from keel show open-issues after the record
    part hookCostIsADistributionCloseOutGateR1 : TestResult { :>> id = "3f09c64b-f394-42c6-986e-4febbd38ca35"; :>> outcome = VerdictKind::pass; :>> judgedAgainst = "d071820522e8332e406c87feb67e28721d7a395a"; :>> judgedAt = "2026-09-08"; :>> judgedBy = "claudeOpus5"; }
    verification hookCostIsADistributionRetroGate : Test { :>> id = "b954d83f-62b1-46f6-ab2c-bd80f81a6b31"; :>> title = "Sprint 615 retro gate (autonomous, D0049)"; :>> createdAt = "2026-09-08"; :>> createdBy = "claudeOpus5"; :>> method = VerificationMethod::analyze; :>> procedureText = "Retro held; avoidable-issue scan: no new item - the pre-2026-09-08 skips exist only as transcript lines, which the report says in its own note rather than pretending a count, and the one open question the scan raised is the cap itself, already tracked as d0390 before this retro. Process improvement: the ledger reading was probed first (D0388) - the scratch analysis and the Rust report agree to the millisecond, which is what a probe is for."; }
    // RAN: retro held; avoidable-issue scan: none; no new Issue recorded in this commit; the probe-first practice was applied and the two readings agree
    part hookCostIsADistributionRetroGateR1 : TestResult { :>> id = "5ca45803-9c15-4c62-abe9-c8c5e1060a89"; :>> outcome = VerdictKind::pass; :>> judgedAgainst = "d071820522e8332e406c87feb67e28721d7a395a"; :>> judgedAt = "2026-09-08"; :>> judgedBy = "claudeOpus5"; }
}
