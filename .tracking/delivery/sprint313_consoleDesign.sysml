// ProjectDeliveryS313 — Sprint 313: the console gets a Business layer and an architecture.
// Business (Brief/Needs/UseCases) -> gate -> Architecture (D0152 + 6 SRs). EXECUTE. 13 pts.
package ProjectDeliveryS313 {
    private import EngineElement::*;
    private import EngineWork::*;
    private import EngineVerification::*;
    private import EngineRelationships::*;

    #CharteredBy dependency from consoleDesignStory to d0152;

    part consoleDesignStory : Story {
        :>> id = "0d800340-0814-6340-9b3e-000000300340";
        :>> title = "Sprint 313: design the keel operator console — Business then Architecture (13 pts)";
        :>> createdAt = "2026-08-16"; :>> createdBy = "claudeOpus5"; :>> kind = WorkKind::modeling; :>> priority = WorkPriority::p0; :>> owner = "claudeOpus5"; :>> estimatedPoints = 13;
    }

    action def DeliveryRunS313 {
        action storyConsoleDesign;
        verification storyConsoleDesignDoD : Test { :>> id = "0d800341-0814-6341-9b3e-000000300341"; :>> method = VerificationMethod::inspect; :>> procedureText = "Ran the business-architecture skill over `keel serve`, which the human opened with 'there are too many tabs... let's define use cases and needs for keel and design it properly'. THE FINDING THAT SET THE SCOPE: the console had NO authored Business layer at all — 56 UseCases existed in this model and not one described it, and its twelve tabs are a hardcoded array at console.html:41 organised by DATA TYPE (Business, Decisions, Processes, Reports, Section, Boundary, History) rather than by anything a person does. It accreted one tab per API endpoint. PHASE 1 delivered a Brief, five Needs and six UseCases, reusing the fifteen existing Personas rather than inventing any. PHASE 2, recorded only after the human's Business gate, delivered D0152 and six SystemRequirements with thresholds that can fail. DELIBERATELY SMALL: merging the console with the planned viewer means the viewer's Needs BECOME the console's, so N-1, N-2, N-6 and N-17 were ADOPTED rather than re-authored, and only what they do not cover was written. Need tier returned to 100%; SR tier fell 83% -> 77% because six new requirements exist that nothing verifies, which is the honest direction. validate 340 clean; check-engine clean; 33 guards green."; }
        part storyConsoleDesignDoDR1 : TestResult { :>> id = "0d800342-0814-6342-9b3e-000000300342"; :>> outcome = VerdictKind::pass; :>> judgedAgainst = "7ac3695"; :>> judgedAt = "2026-08-16"; :>> judgedBy = "claudeOpus5"; }
    }

    verification cdRefineGate : Test { :>> id = "0d800343-0814-6343-9b3e-000000300343"; :>> title = "Sprint 313 refine gate (DoR)"; :>> createdAt = "2026-08-16"; :>> createdBy = "claudeOpus5"; :>> method = VerificationMethod::inspect; :>> procedureText = "DoR. The request was a design request, so the business-architecture skill deploys rather than a conversation producing prose (D0059/issue054). CONSUMER CHECK (dorConsumer, D0144): the consumer of these Needs is the architecture phase that derives requirements from them, so each had to be MEASURABLE and solution-free — a Need naming a tab would have pre-decided the architecture and made the requirement trivial. estimatedPoints=13."; }
    part cdRefineGateR1 : TestResult { :>> id = "0d800344-0814-6344-9b3e-000000300344"; :>> outcome = VerdictKind::pass; :>> judgedAgainst = "7ac3695"; :>> judgedAt = "2026-08-16"; :>> judgedBy = "claudeOpus5"; }

    verification cdStandupGate : Test { :>> id = "0d800345-0814-6345-9b3e-000000300345"; :>> title = "Sprint 313 standup gate"; :>> createdAt = "2026-08-16"; :>> createdBy = "claudeOpus5"; :>> method = VerificationMethod::inspect; :>> procedureText = "Approach: establish ground truth on the actual tabs and the existing Needs BEFORE proposing anything, so the design builds on what is authored rather than duplicating it; brainstorm the Needs with the human rather than presenting a finished set. No blockers."; }
    part cdStandupGateR1 : TestResult { :>> id = "0d800346-0814-6346-9b3e-000000300346"; :>> outcome = VerdictKind::pass; :>> judgedAgainst = "7ac3695"; :>> judgedAt = "2026-08-16"; :>> judgedBy = "claudeOpus5"; }

    verification cdImplementGate : Test { :>> id = "0d800347-0814-6347-9b3e-000000300347"; :>> title = "Sprint 313 implement gate"; :>> createdAt = "2026-08-16"; :>> createdBy = "claudeOpus5"; :>> method = VerificationMethod::test; :>> procedureText = "THE HUMAN'S CORRECTION IMPROVED THE NEEDS MATERIALLY AND IS WHY THERE ARE FIVE. First draft: 'these needs are pretty close to use cases. try and identify things that are more fundamental. for example n-c1 is really two distinct needs. one to know what is pending, and one to not be misled.' Both halves landed. The SPLIT produced N-C2, which turns out not to be about obligations at all — it is the engine's own honest-state doctrine pointed at a HUMAN rather than at a gate, and it constrains every surface the console will ever grow; folded inside a Need about obligations it would have been invisible. The SECOND steer — 'fewer tabs I agree isn't a need, but UX and good human factors design is' — produced N-C5, which is the accurate diagnosis: twelve tabs is bad not for its count but because the surface must be learned and re-learned, and orientation cost grew with every capability. AN ACCEPTANCE WAS DELIBERATELY NOT RECORDED: the human wrote 'accepted' in the same message that directed the rewrite, and that word could not honestly attach to text authored after they said it (§4, D0151, accepted hours earlier). The gate was re-put on the revised set and passed on 'looks great, proceed'. Likewise D0152 was HELD until after that gate — the human's permission to supersede D0114 predated it, but recording an architecture Decision before the Needs it serves is the issue054 defect precisely."; }
    part cdImplementGateR1 : TestResult { :>> id = "0d800348-0814-6348-9b3e-000000300348"; :>> outcome = VerdictKind::pass; :>> judgedAgainst = "7ac3695"; :>> judgedAt = "2026-08-16"; :>> judgedBy = "claudeOpus5"; }

    verification cdReviewGate : Test { :>> id = "0d800349-0814-6349-9b3e-000000300349"; :>> title = "Sprint 313 review gate"; :>> createdAt = "2026-08-16"; :>> createdBy = "claudeOpus5"; :>> method = VerificationMethod::inspect; :>> procedureText = "Reviewed. EVERY THRESHOLD IS ONE THAT CAN FAIL, written deliberately against the sprint-305 finding that srServeLauncherDefinedOnly stated a universal negative no test could demonstrate. So: zero navigation actions on arrival, not 'few'; adding N viewpoints leaves the top-level count UNCHANGED, a delta rather than an arbitrary cap that nesting would game; a forced failure renders distinguishably from an empty result. TWO LIMITS STATED ON THE REQUIREMENTS THEMSELVES rather than discovered later: srConsoleModelScopeResolved cannot be fully verified in THIS repository, because it is the one place the engine and its deliverable coincide — only COINCIDENT and UNSCOPED are demonstrable here, and the ENGINE/DELIVERABLE distinction needs a downstream project, the same limit issue117 recorded for the arch views. And D0152's rationale records the argument it LOST: the merge was first argued on the audience split being a filter rather than a deployment boundary, and the human then deferred audience filtering, so the Decision now rests on shared substrate alone and names itself as the thing that reopens if a stakeholder surface is ever needed."; }
    part cdReviewGateR1 : TestResult { :>> id = "0d80034a-0814-634a-9b3e-00000030034a"; :>> outcome = VerdictKind::pass; :>> judgedAgainst = "7ac3695"; :>> judgedAt = "2026-08-16"; :>> judgedBy = "claudeOpus5"; }

    verification cdCloseOutGate : Test { :>> id = "0d80034b-0814-634b-9b3e-00000030034b"; :>> title = "Sprint 313 closeOut gate (autonomous, D0049)"; :>> createdAt = "2026-08-16"; :>> createdBy = "claudeOpus5"; :>> method = VerificationMethod::inspect; :>> procedureText = "Autonomous closeOut (D0049); both human gates are recorded with verbatim words — the Business gate on the Needs and D0152's acceptance. NOTHING IS BUILT: this sprint produced a Brief, Needs, UseCases, one Decision and six SystemRequirements. No console code changed, and the twelve hardcoded tabs are still there — srConsoleNavigationDerived condemns them but implementing it is delivery work not yet refined into backlog items. validate 340 clean; check-engine clean; 33 guards green; Need tier 100%, SR tier 77%."; }
    part cdCloseOutGateR1 : TestResult { :>> id = "0d80034c-0814-634c-9b3e-00000030034c"; :>> outcome = VerdictKind::pass; :>> judgedAgainst = "7ac3695"; :>> judgedAt = "2026-08-16"; :>> judgedBy = "claudeOpus5"; }

    verification cdRetroGate : Test { :>> id = "0d80034d-0814-634d-9b3e-00000030034d"; :>> title = "Sprint 313 retro gate (autonomous, D0049)"; :>> createdAt = "2026-08-16"; :>> createdBy = "claudeOpus5"; :>> method = VerificationMethod::analyze; :>> procedureText = "Autonomous retro (D0049) under D0131's retroTrack. WELL: (1) establishing ground truth first — reading console.html:41 and enumerating the existing 56 UseCases — turned the scope from 'author a design' into 'author the four things not already authored', which is most of the value here; (2) the human's two corrections were adopted whole rather than partially, and the split they proposed produced the most durable Need in the set; (3) both ordering rules held under pressure to move fast — the acceptance not recorded against rewritten text, and the architecture Decision held until after the gate. AVOIDABLE-ISSUE: my first Needs draft was, as the human said, 'pretty close to use cases'. The cause is identifiable rather than vague — I wrote them by looking at the CONSOLE and asking what it should do, which produces features in a Need's grammar, instead of looking at the SUPERVISOR's situation and asking what is true of it regardless of any surface. The tell to keep: if a Need would change when the UI changes, it is a use case wearing a Need's clothes. NO NEW ITEM: this is a modelling-quality lesson and the critique process already exists to catch it — indeed the requirement-quality canon lens 'necessity' is exactly the check that would have flagged it, and these Needs have not yet been critiqued. Estimate 13 pts, delivered."; }
    part cdRetroGateR1 : TestResult { :>> id = "0d80034e-0814-634e-9b3e-00000030034e"; :>> outcome = VerdictKind::pass; :>> judgedAgainst = "7ac3695"; :>> judgedAt = "2026-08-16"; :>> judgedBy = "claudeOpus5"; }
}
