// ProjectDeliveryS586 — Sprint 586: the executive brief becomes the contract the skill enforces, and the push gate is withdrawn on the owner's instruction. EXECUTE. 5 pts.
package ProjectDeliveryS586 {
    private import EngineElement::*;
    private import EngineWork::*;
    private import EngineVerification::*;
    private import EngineRelationships::*;

    #CharteredBy dependency from briefContractStory to d0355;

    part briefContractStory : Story {
        :>> id = "587c6a0e-7279-447f-aea5-dc9910c153d3";
        :>> title = "Sprint 586: the executive brief becomes the contract the skill enforces, and the push gate is withdrawn on the owner's instruction (5 pts)";
        :>> createdAt = "2026-09-06"; :>> createdBy = "claudeOpus5"; :>> kind = WorkKind::code; :>> priority = WorkPriority::p0; :>> owner = "claudeOpus5"; :>> estimatedPoints = 5;
    }

    action def DeliveryRunS586 {
        action storyBriefContract;
        verification storyBriefContractDoD : Test { :>> id = "84cc29e6-6323-4ebd-b386-97bc3d87c82f"; :>> method = VerificationMethod::test; :>> procedureText = "DELIVERED BACKLOG ITEMS: dcDecisionReportIsArguable (D0355, accepted by the owner: 'process accepted. formalize and change ai skills.'; resolves issue382 and issue383) and the withdrawal recorded as D0356. DONE: the asi-templates skill's exec-summary section is replaced by the executive-brief contract - answer first, one page, no record id in anything the reader reads, every number computed, per ask two mandatory logic exhibits (today versus changed; what lands downstream), figures titled with claims, a do-nothing course, and the state of each item so a ratification says so; the routing description an agent reads now names that surface. check_templates.py gains --brief, enforcing the mechanical half, and it BITES on a falsified page. The brief itself is rebuilt on those rules and published. keel land no longer consults the suite receipt; keel suite keeps writing it as the measurement that convicted the gate; keel suite --help prints usage instead of running 562 tests. VERIFIED: brief contract clean on the real page and 2 violations on a probe carrying one id and one untitled figure; push_gate_is_withdrawn 2/2; template contract clean; validate 665; guards ALL PASS; clippy -D warnings clean; the page read as an image at each step."; }
        // RAN: dcDecisionReportIsArguable DoD pass; D0356 recorded with its supersede edge to the withdrawn gate; the implement section names each run
        part storyBriefContractDoDR1 : TestResult { :>> id = "43992f9e-d6b6-4ef2-93b0-5a20bf23242e"; :>> outcome = VerdictKind::pass; :>> judgedAgainst = "2091b10dd28190347ee99cf7a2bacb7ee2d26466"; :>> judgedAt = "2026-09-06"; :>> judgedBy = "claudeOpus5"; }
    }

    verification briefContractRefineGate : Test { :>> id = "c90d856d-a3ae-4b60-bed5-6d07e929c49d"; :>> title = "Sprint 586 refine gate (DoR)"; :>> createdAt = "2026-09-06"; :>> createdBy = "claudeOpus5"; :>> method = VerificationMethod::inspect; :>> procedureText = "READY: the owner accepted the process and asked for two things - formalize it, change the AI skills. The one design question was where identity goes now that no id may face the reader: it rides in the digest, because an answer that cannot be attached to a record cannot be recorded, which is exactly what happened to their first paste."; }
    verification briefContractStandupGate : Test { :>> id = "d53f49bd-2d1a-4dae-bc9e-ffd60b870948"; :>> title = "Sprint 586 standup gate"; :>> createdAt = "2026-09-06"; :>> createdBy = "claudeOpus5"; :>> method = VerificationMethod::inspect; :>> procedureText = "THE CONTROL REFUSED MY RECORDING AND WAS RIGHT. Their answer said 'Keep five, revert the push gate, switch the pull on' without naming which five, so the read-back check refused all eight acceptances and nothing was written. That is the guard they accepted working; the fix is in the page, not in the guard."; }
    verification briefContractImplementGate : Test { :>> id = "c5d121a8-080d-4a7d-a4f4-e57ee9179ac3"; :>> title = "Sprint 586 implement gate"; :>> createdAt = "2026-09-06"; :>> createdBy = "claudeOpus5"; :>> method = VerificationMethod::test; :>> procedureText = "RAN: the skill rewritten and redeployed (46/46 skills); check_templates.py --brief against the brief (clean) and against a probe with an injected id and a stripped figure title (2 violations, both named); cargo test push_gate_is_withdrawn 2/2; cargo clippy -D warnings clean; keel validate 665; keel guard ALL PASS; the facts script extended with a same-scope pair after the page published '72 of 69'."; }
    verification briefContractReviewGate : Test { :>> id = "36a3d82a-c26c-4f1a-9654-78086c046e30"; :>> title = "Sprint 586 review gate — three passes per D0172"; :>> createdAt = "2026-09-06"; :>> createdBy = "claudeOpus5"; :>> method = VerificationMethod::inspect; :>> procedureText = "THREE PASSES. (1) DOES THE SKILL DESCRIBE WHAT THE TEMPLATE DOES: the description and section 2 now name the brief, its two mandatory exhibits and the no-id rule. (2) DOES THE CHECKER BITE: shown, on a falsified copy. (3) IS ANY CLAIM ABOUT THE WITHDRAWN GATE STILL STANDING: the module header, the receipt comment and the engine handbook all corrected in the same commit."; }
    verification briefContractCloseOutGate : Test { :>> id = "41c80f86-07ad-408b-9805-a5265165e391"; :>> title = "Sprint 586 closeOut gate (autonomous, D0049)"; :>> createdAt = "2026-09-06"; :>> createdBy = "claudeOpus5"; :>> method = VerificationMethod::inspect; :>> procedureText = "CLOSED. The contract is enforced rather than described; the push gate is gone; the acceptances wait on one line from the owner naming what they accepted."; }
    verification briefContractRetroGate : Test { :>> id = "fd025d23-4b4c-42cc-9d70-b2f06232192a"; :>> title = "Sprint 586 retro gate (autonomous, D0049)"; :>> createdAt = "2026-09-06"; :>> createdBy = "claudeOpus5"; :>> method = VerificationMethod::analyze; :>> procedureText = "no new item - already tracked: issue382 and issue383 are the two defects this closes, and the DoD was amended before any result rather than after one, which is the D0307 line. The lesson: a measurement I never took carried a recommendation for a day - the four-minute estimate - and the receipt that could have measured it was already on disk."; }
}
