// ProjectDeliveryS378 — Sprint 378: the fallback's `saved` was the runtime marking its own homework.
// Labels now claim only what the receiver can verify. EXECUTE. 2 pts.
package ProjectDeliveryS378 {
    private import EngineElement::*;
    private import EngineWork::*;
    private import EngineVerification::*;
    private import EngineRelationships::*;

    #CharteredBy dependency from honestLabelStory to d0171;

    part honestLabelStory : Story {
        :>> id = "0d800750-0814-6750-9b3e-000000300750";
        :>> title = "Sprint 378: a save label the receiver cannot verify is not a save label (2 pts)";
        :>> createdAt = "2026-08-21"; :>> createdBy = "claudeOpus5"; :>> kind = WorkKind::code; :>> priority = WorkPriority::p0; :>> owner = "claudeOpus5"; :>> estimatedPoints = 2;
    }

    action def DeliveryRunS378 {
        action storyHonestLabel;
        verification storyHonestLabelDoD : Test { :>> id = "0d800751-0814-6751-9b3e-000000300751"; :>> method = VerificationMethod::test; :>> procedureText = "DELIVERED BACKLOG ITEMS: dcHonestSaveLabel. Clears issue193. THE MEASUREMENT USED THE HUMAN AS THE FAR INSTRUMENT - the only end-to-end test the artifact transport permits: their phone showed transport=fallback and `saved` per tap; a fresh fetch of the served document AFTER their taps showed every verdict empty. TWO FACTS FOLLOW: sync() resolving proves only that the runtime accepted the write; and no read path available to this session returns viewer appends - so the artifact transport is WRITE-ONLY from the receiver's perspective, and `saved` was an overclaim. Their question named the principle: if we cannot tell whether it saved properly, why indicate saved at all. FIXED: the fallback per-tap label reads `marked in page - NOT confirmed in keel`; its transport line states judgments marked there do not reach keel and points to the local deck or telling Claude; `saved` is reserved for the LOCAL transport, where a write-API 200 and a computed-view read-back make it TRUE (e2e-verified). Their phone-recorded verdicts are stranded in the unreadable layer - stated as a cost, not recovered by pretending. validate clean; 38 guards ALL PASS; 209 tests; e2e 13/13; clippy clean."; }
        part storyHonestLabelDoDR1 : TestResult { :>> id = "0d800752-0814-6752-9b3e-000000300752"; :>> outcome = VerdictKind::pass; :>> judgedAgainst = "02d78ae"; :>> judgedAt = "2026-08-21"; :>> judgedBy = "claudeOpus5"; }
    }

    verification hlRefineGate : Test { :>> id = "0d800753-0814-6753-9b3e-000000300753"; :>> title = "Sprint 378 refine gate (DoR)"; :>> createdAt = "2026-08-21"; :>> createdBy = "claudeOpus5"; :>> method = VerificationMethod::inspect; :>> procedureText = "DoR. Their two questions decompose exactly: CAN we tell if it saved properly - on the artifact transport, NO, structurally: confirmation requires the receiver, and the receiver has no read path. WHY indicate saved at all - because I accepted the runtime's resolved promise as proof of delivery, which is sender-side evidence for a receiver-side claim. The fix is labeling, not machinery: claim what is known, exactly. estimatedPoints=2."; }
    part hlRefineGateR1 : TestResult { :>> id = "0d800754-0814-6754-9b3e-000000300754"; :>> outcome = VerdictKind::pass; :>> judgedAgainst = "02d78ae"; :>> judgedAt = "2026-08-21"; :>> judgedBy = "claudeOpus5"; }

    verification hlStandupGate : Test { :>> id = "0d800755-0814-6755-9b3e-000000300755"; :>> title = "Sprint 378 standup gate"; :>> createdAt = "2026-08-21"; :>> createdBy = "claudeOpus5"; :>> method = VerificationMethod::inspect; :>> procedureText = "Approach: two label changes and a recorded limitation - no new machinery, because no machinery on the page can manufacture receiver-side confirmation. The STRUCTURAL answer for mobile is routing the phone to the TESTED transport (keel serve over their remote-control or a tunnel), which is their infrastructure decision and is recorded in issue193 rather than assumed. No blockers."; }
    part hlStandupGateR1 : TestResult { :>> id = "0d800756-0814-6756-9b3e-000000300756"; :>> outcome = VerdictKind::pass; :>> judgedAgainst = "02d78ae"; :>> judgedAt = "2026-08-21"; :>> judgedBy = "claudeOpus5"; }

    verification hlImplementGate : Test { :>> id = "0d800757-0814-6757-9b3e-000000300757"; :>> title = "Sprint 378 implement gate"; :>> createdAt = "2026-08-21"; :>> createdBy = "claudeOpus5"; :>> method = VerificationMethod::test; :>> procedureText = "THE GENERAL RULE THIS INSTANCE PROVES, now in the record: a confirmation is a statement by the RECEIVER. The runtime's sync() resolution, the write-API's 200, and keel's computed view form a LADDER of confirmation strength, and each label must sit on the rung it actually earned: sync-resolved earns `marked in page`; a 200 from keel's own API earns `saved to keel`; only the computed view earns done. This is D0018 (state is computed, never asserted) applied to a BUTTON LABEL, and the session's verify-don't-assert rule applied to the page itself. Same ladder, same words, in the skill and the module doc."; }
    part hlImplementGateR1 : TestResult { :>> id = "0d800758-0814-6758-9b3e-000000300758"; :>> outcome = VerdictKind::pass; :>> judgedAgainst = "02d78ae"; :>> judgedAt = "2026-08-21"; :>> judgedBy = "claudeOpus5"; }

    verification hlReviewGate : Test { :>> id = "0d800759-0814-6759-9b3e-000000300759"; :>> title = "Sprint 378 review gate — three passes per D0172"; :>> createdAt = "2026-08-21"; :>> createdBy = "claudeOpus5"; :>> method = VerificationMethod::inspect; :>> procedureText = "PASS 1, CLAIMS: labels verified in the emitted HTML; e2e 13/13 (the LOCAL `saved to keel` label is the one the e2e's view read-backs actually earn); node --check green. PASS 2, BOUNDARY: the human-as-instrument measurement is the boundary case itself - sender says saved, receiver sees nothing - and both halves are recorded verbatim in issue193. PASS 3, OWN DIFF: the readback I added last sprint (REVERTED detection) survives and is now honest too - it detects the runtime undoing a write, which is a DIFFERENT failure from the receiver never seeing it, and the labels no longer conflate them. WHAT A REVIEWER SHOULD ATTACK: the fallback is now honest but nearly useless - it marks a page keel never reads. Kept anyway, deliberately: the marks survive on the page for the human's own reference, and deleting the buttons would make the mobile page a brochure. The real fix is the tunnel, and it is theirs to choose."; }
    part hlReviewGateR1 : TestResult { :>> id = "0d80075a-0814-675a-9b3e-00000030075a"; :>> outcome = VerdictKind::pass; :>> judgedAgainst = "02d78ae"; :>> judgedAt = "2026-08-21"; :>> judgedBy = "claudeOpus5"; }

    verification hlCloseOutGate : Test { :>> id = "0d80075b-0814-675b-9b3e-00000030075b"; :>> title = "Sprint 378 closeOut gate (autonomous, D0049)"; :>> createdAt = "2026-08-21"; :>> createdBy = "claudeOpus5"; :>> method = VerificationMethod::inspect; :>> procedureText = "Autonomous closeOut (D0049). issue193 recorded and cleared; the artifact republished with honest labels; the stranded-verdict cost stated in the issue rather than smoothed over. The mobile-transport decision (tunnel keel serve to the phone) is recorded as theirs. validate clean; 38 guards ALL PASS; 209 tests; e2e 13/13."; }
    part hlCloseOutGateR1 : TestResult { :>> id = "0d80075c-0814-675c-9b3e-00000030075c"; :>> outcome = VerdictKind::pass; :>> judgedAgainst = "02d78ae"; :>> judgedAt = "2026-08-21"; :>> judgedBy = "claudeOpus5"; }

    verification hlRetroGate : Test { :>> id = "0d80075d-0814-675d-9b3e-00000030075d"; :>> title = "Sprint 378 retro gate (autonomous, D0049)"; :>> createdAt = "2026-08-21"; :>> createdBy = "claudeOpus5"; :>> method = VerificationMethod::analyze; :>> procedureText = "Autonomous retro (D0049). AVOIDABLE-ISSUE SCAN under rcRecurrence: trusting sender-side evidence for a receiver-side claim is occurrence THREE of the verify-the-wrong-surface family (file-for-screen, strings-for-syntax, now sender-for-receiver) - the family rule tightens to its final form and lives in dcEmittedJsMustParse's sibling dcHonestSaveLabel: A CLAIM IS VERIFIED AT THE SURFACE THAT CONSUMES IT, and every rung of a delivery chain gets a label matching its own rung, never the rung above. WELL: (1) the human's four-word question was treated as the design principle it is; (2) the measurement used the only end-to-end instrument available - them - and both halves are recorded verbatim; (3) the stranded verdicts are stated as a cost instead of recovered by fabrication, which would have been the worst possible response available; (4) the fix claims nothing new - it un-claims, which is the rarer and more valuable edit. Estimate 2 pts, delivered."; }
    part hlRetroGateR1 : TestResult { :>> id = "0d80075e-0814-675e-9b3e-00000030075e"; :>> outcome = VerdictKind::pass; :>> judgedAgainst = "02d78ae"; :>> judgedAt = "2026-08-21"; :>> judgedBy = "claudeOpus5"; }
}
