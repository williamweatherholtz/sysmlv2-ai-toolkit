// ProjectDeliveryS450 — Sprint 450: the frontier fails CLOSED and every computed answer names its basis - the honest-surface invariant reaches the CLI authority (issue239, issue247). EXECUTE. 3 pts.
package ProjectDeliveryS450 {
    private import EngineElement::*;
    private import EngineWork::*;
    private import EngineVerification::*;
    private import EngineRelationships::*;

    #CharteredBy dependency from honestSurfaceEverywhereStory to d0209;

    part honestSurfaceEverywhereStory : Story {
        :>> id = "a2e6fca4-cc1d-414c-bf92-d1c849515896";
        :>> title = "Sprint 450: a computation that could not run no longer answers confidently (3 pts)";
        :>> createdAt = "2026-08-24"; :>> createdBy = "claudeFable5"; :>> kind = WorkKind::code; :>> priority = WorkPriority::p0; :>> owner = "claudeFable5"; :>> estimatedPoints = 3;
    }

    action def DeliveryRunS450 {
        action storyHonestSurfaceEverywhere;
        verification storyHonestSurfaceEverywhereDoD : Test { :>> id = "3d5fbbe0-bb97-440d-bfbe-7432c9ff0ebd"; :>> method = VerificationMethod::test; :>> procedureText = "DELIVERED: dcHonestSurfaceEverywhere (resolves issue239 HIGH and issue247 HIGH). THE PANEL'S REFRAMING (systems-engineer lens, the most valuable single output of the review): three of the four drift mechanisms I had proposed were not independent mechanisms at all but three violations of ONE already-accepted invariant. nConsoleNeverMisleads (N-C2, human-accepted 2026-08-16) already requires that absence be distinguishable from information ABOUT absence, that a view which could not be computed never render as a negative result, and that stale never show as current - but its only satisfying requirement, srConsoleViewStatusExplicit, is scoped to 'every view the surface renders', the HTML console, while CLAUDE.md section 1.8/D0093 make CLI/JSON the AUTHORITY and the automation substrate. Every violation the panel found was CLI-side. So the answer to the human's question about reports drifting from truth is not 'add a drift control' but 'an invariant you already signed is bound to the wrong surface'. AUTHORED: srAuthorityAnswerStatesItsBasis (must, verificationMethod test) with a satisfy edge to nConsoleNeverMisleads - every computed answer on ANY surface states which of COMPUTED-WITH-CONTENT / COMPUTED-EMPTY / COULD-NOT-COMPUTE / TRUE-AS-OF it is and the population it covered, and where a NARROWING filter cannot be computed the answer fails closed and says so. The Need is owned by another actor, so a non-owner ADDS a requirement and a typed edge rather than editing its statement (D0108). THE DEFECT THIS FOUND (issue247, and the worst of the eight): orient's ready computation filtered out SUPERSEDED tasks (issue100) and tasks BLOCKED on a proposed Decision (issue112) using `.unwrap_or_default()` at both sites - directly beneath a comment reading, verbatim, 'Conservative on error: failing to read the model must not silently make everything ready again'. An Err yields an EMPTY filter set, so nothing is filtered and every retired and every human-blocked task RETURNS TO THE FRONTIER - which the AI auto-follows (D0052). The code did precisely what its own comment forbade, and a transient parse error could therefore schedule work a Decision had explicitly retired. Compounding it, keel whats-next printed nothing and exited 0 whether the frontier was genuinely empty or a filter had failed, making COMPUTED-EMPTY and COULD-NOT-COMPUTE byte-identical on the single most load-bearing answer in the engine. THE FIX: narrowing_filters() gathers the three narrowing filters in one place and RECORDS failures; claimed_by_others keeps its deliberate empty-on-error and is explicitly NOT counted a failure, because a claim must never make work invisible to someone who cannot be told it is theirs; a recorded failure EMPTIES ready (fail closed); orient emits answerStatus of COMPUTED or COULD-NOT-COMPUTE with readyEmptiedDeliberately and the reasons; whats-next REFUSES with exit 1 on a failure and says COMPUTED-EMPTY out loud when the answer is genuinely empty. VERIFIED by probe in a throwaway git worktree carrying an unparseable tracking file: whats-next exits 1, names both failed filters with their parse errors, and states 'This is NOT an empty frontier'; orient reports the structured COULD-NOT-COMPUTE with both reasons; the clean repo reports COMPUTED. 253 lib tests pass, two new ones pinning both states so they can never again render alike; clippy clean; validate + all 48 guards + check-engine + rules green."; }
        part storyHonestSurfaceEverywhereDoDR1 : TestResult { :>> id = "1dec8528-a86d-43a8-86fe-bb435e9f1d40"; :>> outcome = VerdictKind::pass; :>> judgedAgainst = "26c68ff2c02be662974360d5a34efa9a1a74d5d0"; :>> judgedAt = "2026-08-24"; :>> judgedBy = "claudeFable5"; }
    }

    verification honestSurfaceEverywhereRefineGate : Test { :>> id = "cf28c316-fdca-45ab-b32e-f46e6a457450"; :>> title = "Sprint 450 refine gate (DoR)"; :>> createdAt = "2026-08-24"; :>> createdBy = "claudeFable5"; :>> method = VerificationMethod::inspect; :>> procedureText = "DoR. Resolves issue239 (HIGH, the panel's central reframing) and issue247 (HIGH, discovered during it). Scope: author the missing requirement for the authority substrate, and fix the concrete frontier-widening instance it exposes. Deliberately NOT in scope: retrofitting every CLI view at once - the requirement is the standing contract and views are corrected as touched, which is how the last four sprints already behaved. 3 points."; }
    part honestSurfaceEverywhereRefineGateR1 : TestResult { :>> id = "ec174fc1-8947-409a-a14b-8558e2ecbd90"; :>> outcome = VerdictKind::pass; :>> judgedAgainst = "26c68ff2c02be662974360d5a34efa9a1a74d5d0"; :>> judgedAt = "2026-08-24"; :>> judgedBy = "claudeFable5"; }
    verification honestSurfaceEverywhereStandupGate : Test { :>> id = "09ada960-d7d3-48b9-a5a3-7eee32090898"; :>> title = "Sprint 450 standup gate"; :>> createdAt = "2026-08-24"; :>> createdBy = "claudeFable5"; :>> method = VerificationMethod::inspect; :>> procedureText = "Approach: the Need is accepted and owned elsewhere, so ADD a SystemRequirement plus a satisfy edge rather than widening someone else's statement (D0108). For the code, find one REAL violation rather than shipping paperwork - the frontier turned out to be it, and it was a safety defect rather than a labelling one. Extract the narrowing filters so the fail-closed property is testable and so compute_after_fetch stays under the line limit. orient.rs and main.rs are off the frozen enforcement surface, so no marked Decision is required. No blockers."; }
    part honestSurfaceEverywhereStandupGateR1 : TestResult { :>> id = "7ebdd4ff-33f5-4d75-9a13-76758f69a07e"; :>> outcome = VerdictKind::pass; :>> judgedAgainst = "26c68ff2c02be662974360d5a34efa9a1a74d5d0"; :>> judgedAt = "2026-08-24"; :>> judgedBy = "claudeFable5"; }
    verification honestSurfaceEverywhereImplementGate : Test { :>> id = "17b9f937-bc44-455e-9cb4-3245242c16e7"; :>> title = "Sprint 450 implement gate"; :>> createdAt = "2026-08-24"; :>> createdBy = "claudeFable5"; :>> method = VerificationMethod::test; :>> procedureText = "Verified by running a freshness-checked binary and by a negative probe designed to be capable of failing: in a throwaway worktree with an unparseable .tracking file, whats-next exited 1 listing both failed filters and their parse errors; orient emitted answerStatus COULD-NOT-COMPUTE with readyEmptiedDeliberately true; the clean tree emits answerStatus COMPUTED. cargo test --lib orient -> 3 passed including two new state tests; full lib suite 253 passed; cargo clippy --workspace --all-targets -D warnings clean after extracting narrowing_filters (the function had crossed the 100-line limit) and dropping an unneeded mut."; }
    part honestSurfaceEverywhereImplementGateR1 : TestResult { :>> id = "135299da-3162-414f-b4ea-d07c193927d9"; :>> outcome = VerdictKind::pass; :>> judgedAgainst = "26c68ff2c02be662974360d5a34efa9a1a74d5d0"; :>> judgedAt = "2026-08-24"; :>> judgedBy = "claudeFable5"; }
    verification honestSurfaceEverywhereReviewGate : Test { :>> id = "f85d0ee0-459a-4fb4-9277-db0f84395c07"; :>> title = "Sprint 450 review gate — three passes per D0172"; :>> createdAt = "2026-08-24"; :>> createdBy = "claudeFable5"; :>> method = VerificationMethod::inspect; :>> procedureText = "PASS 1, CLAIMS: the probe output, both exit codes and the answerStatus payloads are quoted read-backs; the pre-fix behaviour is stated as REASONING from the code (unwrap_or_default yields an empty set, so the `!superseded.contains(name)` filter passes everything, so a superseded item such as dcHeterogeneousCritics would have been listed) and is NOT claimed as an observation, because I did not run the old binary against the broken tree. PASS 2, BOUNDARY: (i) the requirement binds every computed answer but only three surfaces have been brought into line so far (this frontier, the process catalogue, the armed-ness report) - the rest are correct-as-touched, stated plainly rather than implied complete; (ii) claimed_by_others still returns empty on error BY DESIGN and that asymmetry is documented at the call site, so a reader does not read it as an oversight; (iii) the fail-closed clause covers filters that NARROW; a filter that WIDENS a result failing open would not be caught by this shape and no such filter exists today. PASS 3, OWN DIFF: the honest finding is that this defect had a correct comment sitting directly above incorrect code for its whole life, and every reader including me read the comment and believed it - which is the prose-versus-computed drift class (issue246) occurring INSIDE the implementation rather than in documentation. WHAT A REVIEWER SHOULD ATTACK: whether emptying `ready` is the right failure mode versus refusing to emit an Output at all; emptying keeps orient's other fields readable, which I judged more useful than a total refusal, but it does mean a caller that reads only `ready` and ignores answerStatus sees a plausible empty - which is exactly why whats-next was changed to check the status rather than the list."; }
    part honestSurfaceEverywhereReviewGateR1 : TestResult { :>> id = "39d2a2f9-ea2f-4e5d-a457-c3916db3d5a4"; :>> outcome = VerdictKind::pass; :>> judgedAgainst = "26c68ff2c02be662974360d5a34efa9a1a74d5d0"; :>> judgedAt = "2026-08-24"; :>> judgedBy = "claudeFable5"; }
    verification honestSurfaceEverywhereCloseOutGate : Test { :>> id = "056434e8-237f-43db-aae6-6ebc3a610785"; :>> title = "Sprint 450 closeOut gate (autonomous, D0049)"; :>> createdAt = "2026-08-24"; :>> createdBy = "claudeFable5"; :>> method = VerificationMethod::inspect; :>> procedureText = "Autonomous closeOut (D0049). issue239 and issue247 resolved; the missing requirement for the authority substrate is authored and satisfy-linked; the frontier fails closed with both states pinned by tests; validate + all 48 guards + check-engine + rules green. Three panel findings remain: issue245, issue243, issue246."; }
    part honestSurfaceEverywhereCloseOutGateR1 : TestResult { :>> id = "5093c390-e132-4375-a7c7-83a055506e4b"; :>> outcome = VerdictKind::pass; :>> judgedAgainst = "26c68ff2c02be662974360d5a34efa9a1a74d5d0"; :>> judgedAt = "2026-08-24"; :>> judgedBy = "claudeFable5"; }
    verification honestSurfaceEverywhereRetroGate : Test { :>> id = "2e0979be-8f58-4c48-a6c5-7a9db23c1dcb"; :>> title = "Sprint 450 retro gate (autonomous, D0049)"; :>> createdAt = "2026-08-24"; :>> createdBy = "claudeFable5"; :>> method = VerificationMethod::analyze; :>> procedureText = "Autonomous retro (D0049). AVOIDABLE-ISSUE SCAN under rcRecurrence: (1) the finding itself is the lesson - a comment asserting a safety property sat above code implementing its opposite, and it survived because comments are not checked; the durable form is that a comment claiming a failure MODE is a claim that needs a test, and both are now pinned. (2) The probe discipline held this time: I built the probe to be capable of failing (an actually-unparseable file) rather than assuming, which is the third-time-learned rule from sprint448 finally applied without a false clean first. WELL: the panel's reframing turned what I had written as four separate drift mechanisms into one scoping error against an invariant the human had already accepted, and following that reframing led directly to a real safety defect in the most load-bearing computation in the engine - which is a far better outcome than the new detector my own brief had proposed. Estimate 3 pts, delivered 3."; }
    part honestSurfaceEverywhereRetroGateR1 : TestResult { :>> id = "8cc5f141-7fea-4b82-84c2-6919fd31af2d"; :>> outcome = VerdictKind::pass; :>> judgedAgainst = "26c68ff2c02be662974360d5a34efa9a1a74d5d0"; :>> judgedAt = "2026-08-24"; :>> judgedBy = "claudeFable5"; }

    // The requirement this sprint authored is VERIFIED by this sprint's own DoD (issue082): work
    // verified without the requirement verified is a traceability lie-of-omission, and the
    // verification-trace guard named the exact edge to author.
    #Verify dependency from storyHonestSurfaceEverywhereDoD to srAuthorityAnswerStatesItsBasis;
}
