// ProjectDeliveryS303 — Sprint 303: D0150 applied — schema vocabulary is DERIVED, and an undeclared
// attribute fails the gate. The holistic hook-vs-schema pass. CHANGE + EXECUTE. 13 pts.
package ProjectDeliveryS303 {
    private import EngineElement::*;
    private import EngineWork::*;
    private import EngineVerification::*;
    private import EngineRelationships::*;

    #CharteredBy dependency from schemaDerivedStory to d0150;

    part schemaDerivedStory : Story {
        :>> id = "0d8002a0-0814-62a0-9b3e-0000003002a0";
        :>> title = "Sprint 303: derive schema vocabulary + the attribute-vocabulary guard (13 pts)";
        :>> createdAt = "2026-08-15"; :>> createdBy = "claudeOpus5"; :>> kind = WorkKind::code; :>> priority = WorkPriority::p0; :>> owner = "claudeOpus5"; :>> estimatedPoints = 13;
    }

    action def DeliveryRunS303 {
        action storySchemaDerived;
        verification storySchemaDerivedDoD : Test { :>> id = "0d8002a1-0814-62a1-9b3e-0000003002a1"; :>> method = VerificationMethod::test; :>> procedureText = "Applies D0150 (accepted by wweatherholtz 2026-08-15, verbatim 'approved') and delivers dcSchemaReconciliation, resolving issue118, issue119 and issue120. THE FINDING THE HUMAN PREDICTED: attribute NAMES were never checked by anything. A CodeElement authored with `codeHsah` and `riskClas` passed `keel validate`, all 32 guards AND the fast edit gate — 329 files reported clean — while silently discarding its risk classification, so the element sat in the `arch criticality` frontier as `correctness` when its author wrote `dataLoss`, and reported UNAUDITED when its author believed a hash was recorded. Markers were checked (D0133) and enum members were checked; attribute names never were. DELIVERED: (1) a `schema` module that parses the `.engine/schema` embedded in the binary by `include_dir!`, exposing edge kinds, enum members IN DECLARATION ORDER, and per-type attributes following `:>` inheritance — reading the EMBEDDED schema and never the project's on-disk copy, because reading the project's is what caused issue090's 566-violation lockout. (2) `KNOWN_EDGES`, `ENGINE_MARKERS` and `RISK_ORDER` DELETED as literals and derived, so that drift is unrepresentable rather than merely detectable. (3) A 33rd hard guard, `attribute-vocabulary`, with a nearest-declared-name hint, which SKIPS project-declared types entirely rather than judging a vocabulary the engine cannot know. VERIFIED: both typos are now refused by name with the right suggestion and the full gate blocks; the corpus scans 40355 assignments with ZERO violations, so no grandfathering was needed and the control is forward-only by construction; a declared view over `derivedFrom` now resolves, reaching 166 edges that were unreachable from the view layer; `arch criticality` still ranks dataLoss first, now from the enum's declaration order rather than a literal. clippy clean; 213 tests; validate 328 clean; 33 guards green; `keel version` reports 33/24/9 matching guards.md."; }
        part storySchemaDerivedDoDR1 : TestResult { :>> id = "0d8002a2-0814-62a2-9b3e-0000003002a2"; :>> outcome = VerdictKind::pass; :>> judgedAgainst = "0f964ae"; :>> judgedAt = "2026-08-15"; :>> judgedBy = "claudeOpus5"; }
    }

    verification sdRefineGate : Test { :>> id = "0d8002a3-0814-62a3-9b3e-0000003002a3"; :>> title = "Sprint 303 refine gate (DoR)"; :>> createdAt = "2026-08-15"; :>> createdBy = "claudeOpus5"; :>> method = VerificationMethod::inspect; :>> procedureText = "DoR. Requested directly: 'we keep being surprised that the new elements aren't being picked up - pass over all existing hooks to make sure they reconcile. we should be throwing errors if there are schema mismatches, or if we're telling on bespoke data hooks instead of intrinsic ones.' The audit ran FIRST and every finding was proven by probe rather than argued, because the same complaint had produced three surprises in one session and a fourth guess would not have helped. The one genuine architectural fork — derive from the schema, or keep the literals and add a reconciliation guard — was put to the human rather than assumed, and they chose derivation. CONSUMER CHECK (dorConsumer, D0144): the consumer of the guard is an author mid-edit, so the message names the TYPE the attribute was authored on and the nearest declared name; 'unknown attribute' alone would leave them grepping the schema. estimatedPoints=13."; }
    part sdRefineGateR1 : TestResult { :>> id = "0d8002a4-0814-62a4-9b3e-0000003002a4"; :>> outcome = VerdictKind::pass; :>> judgedAgainst = "0f964ae"; :>> judgedAt = "2026-08-15"; :>> judgedBy = "claudeOpus5"; }

    verification sdStandupGate : Test { :>> id = "0d8002a5-0814-62a5-9b3e-0000003002a5"; :>> title = "Sprint 303 standup gate"; :>> createdAt = "2026-08-15"; :>> createdBy = "claudeOpus5"; :>> method = VerificationMethod::inspect; :>> procedureText = "Approach: extract the real schema vocabulary, cross-reference every hardcoded literal against it, PROVE each suspected gap with a probe before recording it, then build. No blockers."; }
    part sdStandupGateR1 : TestResult { :>> id = "0d8002a6-0814-62a6-9b3e-0000003002a6"; :>> outcome = VerdictKind::pass; :>> judgedAgainst = "0f964ae"; :>> judgedAt = "2026-08-15"; :>> judgedBy = "claudeOpus5"; }

    verification sdImplementGate : Test { :>> id = "0d8002a7-0814-62a7-9b3e-0000003002a7"; :>> title = "Sprint 303 implement gate"; :>> createdAt = "2026-08-15"; :>> createdBy = "claudeOpus5"; :>> method = VerificationMethod::test; :>> procedureText = "MY FIRST CUT OF THE GUARD HAD THE EXACT DEFECT THE GUARD EXISTS TO CATCH, and it is the most useful thing in this sprint. It credited a `:>>` assignment only to a stack frame pushed on an EARLIER line, but this repo authors records overwhelmingly on ONE line — `verification x : Test { :>> id = ...; :>> method = ...; }` — so it scanned 8088 of 41036 assignments and reported PASS over the 80% it never read. A clean PASS from a control that is blind to four fifths of its corpus is worse than no control, because it actively certifies. Caught by comparing the scanned count against a raw `grep -c` of the corpus, which is the same check that caught the arch views' empty registry and the audit's all-UNKNOWN verdicts: COMPARE THE TOOL'S COUNT TO A NUMBER YOU ALREADY KNOW. Now 40355 scanned, and the remainder is accounted for as non-usage contexts rather than assumed away. SECOND: the throwaway python used for the audit itself produced TWO false findings before it was right — an allow-list of five `def` kinds silently missed `occurrence def TestResult` and `verification def Test`, reporting the engine's most-used types as undefined; then enum bodies keyed by a first-line match made `RiskClass` report `InvariantSafety`'s values, manufacturing a mismatch that did not exist. Both are encoded as tests in the shipped module, and the module matches any lowercase word before `def` rather than an allow-list."; }
    part sdImplementGateR1 : TestResult { :>> id = "0d8002a8-0814-62a8-9b3e-0000003002a8"; :>> outcome = VerdictKind::pass; :>> judgedAgainst = "0f964ae"; :>> judgedAt = "2026-08-15"; :>> judgedBy = "claudeOpus5"; }

    verification sdReviewGate : Test { :>> id = "0d8002a9-0814-62a9-9b3e-0000003002a9"; :>> title = "Sprint 303 review gate"; :>> createdAt = "2026-08-15"; :>> createdBy = "claudeOpus5"; :>> method = VerificationMethod::inspect; :>> procedureText = "Reviewed. The guard SKIPS types the engine schema does not declare rather than judging them, which is the single most important restraint in it: a binary with opinions about a project's own vocabulary is precisely what blocked every commit in issue090, and the temptation to flag an unknown type as suspicious would have recreated that. Zero violations across 40355 assignments meant no grandfathering, no baseline file and no exemption list — the cleanest possible form of issue068 compliance, and it was verified rather than hoped for. Doc-sync rode the change: guards.md 32->33 and 23->24 hard-blocking with a full catalogue row, CLAUDE.md §5, and the D0150 header, whose PROPOSED wording contradicted its own accepted status the moment the acceptance landed — the same dual truth sprint 299's retro caught, so it was checked for deliberately this time."; }
    part sdReviewGateR1 : TestResult { :>> id = "0d8002aa-0814-62aa-9b3e-0000003002aa"; :>> outcome = VerdictKind::pass; :>> judgedAgainst = "0f964ae"; :>> judgedAt = "2026-08-15"; :>> judgedBy = "claudeOpus5"; }

    verification sdCloseOutGate : Test { :>> id = "0d8002ab-0814-62ab-9b3e-0000003002ab"; :>> title = "Sprint 303 closeOut gate (autonomous, D0049)"; :>> createdAt = "2026-08-15"; :>> createdBy = "claudeOpus5"; :>> method = VerificationMethod::inspect; :>> procedureText = "Autonomous closeOut (D0049); the gate change it applies carries wweatherholtz's explicit sign-off as D0150, recorded through `keel accept` with their verbatim word. issue118, issue119 and issue120 resolve through dcSchemaReconciliation. clippy clean; 213 tests; validate 328 clean; check-engine clean; 33 guards green; `keel version` reports 33/24/9 computed from the enforced set, matching guards.md. No gate bypassed, and `keel audit-history` can now check that claim rather than requiring it be taken on my word."; }
    part sdCloseOutGateR1 : TestResult { :>> id = "0d8002ac-0814-62ac-9b3e-0000003002ac"; :>> outcome = VerdictKind::pass; :>> judgedAgainst = "0f964ae"; :>> judgedAt = "2026-08-15"; :>> judgedBy = "claudeOpus5"; }

    verification sdRetroGate : Test { :>> id = "0d8002ad-0814-62ad-9b3e-0000003002ad"; :>> title = "Sprint 303 retro gate (autonomous, D0049)"; :>> createdAt = "2026-08-15"; :>> createdBy = "claudeOpus5"; :>> method = VerificationMethod::analyze; :>> procedureText = "Autonomous retro (D0049) under D0131's retroTrack. WELL: (1) EVERY finding was proven by probe before being recorded, and that discipline paid immediately — two suspected mismatches evaporated under the probe and were my own tooling's bugs, so recording them would have sent a reader chasing defects that did not exist; (2) the human's diagnosis was correct and more general than the instances that prompted it, and taking 'bespoke data hooks instead of intrinsic ones' literally is what turned a bug-fix into deleting three constants; (3) the architectural fork was ASKED rather than assumed, and the answer (derive) produced a materially different and better result than the reconciliation guard I would otherwise have built. AVOIDABLE-ISSUE, AND IT IS THE THEME OF THIS ENTIRE SESSION: for the fourth time in a row, a tool of mine reported a CONFIDENT WRONG ANSWER rather than an error — 8088 assignments scanned reported as PASS, an empty registry for a nonexistent path, every commit UNKNOWN from a partial worktree, 0 of 10 edges from a case-mismatched kind. The pattern is now unmistakable and the counter-check is always the same: compare the tool's own count against a number established independently, BEFORE reading its verdict. That is now encoded three ways — the guard asserts its scanned count in a test, `arch` refuses a root with no `.tracking/`, and the audit reports UNKNOWN rather than PASS. NO NEW ITEM: the control exists in each place it bit. Estimate 13 pts, delivered."; }
    part sdRetroGateR1 : TestResult { :>> id = "0d8002ae-0814-62ae-9b3e-0000003002ae"; :>> outcome = VerdictKind::pass; :>> judgedAgainst = "0f964ae"; :>> judgedAt = "2026-08-15"; :>> judgedBy = "claudeOpus5"; }
}
