// ProjectDeliveryS245 — Sprint 245: computed relationship grammar + scope-aware creation
// (srViewerRelationshipGrammar + srViewerScopedAuthoring, D0126/D0127). keel /api/grammar + the viewer's
// scope-aware New-item picker + grammar-constrained Connect. EXECUTE. 3 pts.
package ProjectDeliveryS245 {
    private import EngineElement::*;
    private import EngineWork::*;
    private import EngineVerification::*;
    private import EngineRelationships::*;

    #CharteredBy dependency from scopeAwareAuthoringStory to d0127;

    part scopeAwareAuthoringStory : Story {
        :>> id = "63940516-2c7d-4e8f-c245-51627384c001";
        :>> title = "Sprint 245: scopeAwareAuthoring (3 pts) - computed relationship grammar + scope-aware creation + grammar-constrained connect";
        :>> createdAt = "2026-07-17"; :>> createdBy = "wweatherholtz"; :>> kind = WorkKind::code; :>> priority = WorkPriority::p2; :>> owner = "claudeOpus"; :>> estimatedPoints = 3;
    }

    action def DeliveryRunS245 {
        action storyScopeAwareAuthoring;
        verification storyScopeAwareAuthoringDoD : Test { :>> id = "63940516-2c7d-4e8f-c245-51627384c002"; :>> method = VerificationMethod::demo; :>> procedureText = "Delivers srViewerRelationshipGrammar + srViewerScopedAuthoring (D0126, governed by D0127) — the human's (2026-07-17) scope/process-aware creation. KEEL (v1.16.0, fe54cc7): view::grammar_json / GET /api/grammar computes the relationship grammar as a VIEW — the distinct (sourceType, edge, targetType) triples OBSERVED in the model + a per-type up/down summary (48 triples). No authored metamodel, no schema/core change; read per-connected-project so it is generic across domains (deliverable vocab stays downstream, §1). VIEWER (f860b5f): (1) SCOPE-AWARE New-item — when the view is scoped (a solo'd register type, else the types present in the graph), the type picker offers ONLY in-scope types + the types they interface with (grammar up/down), with a 'show all types' escape; unscoped shows the full list. (2) GRAMMAR-CONSTRAINED Connect — the edge-kind select narrows to the kinds OBSERVED for the (from,to) type pair; an unobserved pair falls back to the full closed algebra (authoring a new-but-valid pattern still allowed). VERIFY (demo, live): scope=SystemRequirement -> picker = {Component, Decision, Need, Story, SubsystemRequirement, SystemRequirement} (SR + its grammar neighbours, NOT all 91); Need->SR connect kinds = [satisfy] (the sole observed pattern), SR->Need falls back to the full algebra. This realises the human's safety/STPA example generically: a safety scope would offer Loss Scenario / up-Loss / down-Requirement, never a bare Need. clippy + validate + guard + check-engine green. NOTE: D0127 is PROPOSED — its acceptance is the human's end-of-sitting per-sitting review."; }
        part storyScopeAwareAuthoringDoDR1 : TestResult { :>> id = "63940516-2c7d-4e8f-c245-51627384c003"; :>> outcome = VerdictKind::pass; :>> judgedAgainst = "fe54cc7"; :>> judgedAt = "2026-07-17"; :>> judgedBy = "claudeOpus"; }
    }

    verification saRefineGate : Test { :>> id = "63940516-2c7d-4e8f-c245-51627384c004"; :>> title = "Sprint 245 refine gate (DoR)"; :>> createdAt = "2026-07-17"; :>> createdBy = "claudeOpus"; :>> method = VerificationMethod::inspect; :>> procedureText = "DoR: D0127 recorded (grammar-as-computed-view). Scope: /api/grammar + scope-aware create picker + grammar-constrained connect. #CharteredBy d0127. estimatedPoints=3. DoR met."; }
    part saRefineGateR1 : TestResult { :>> id = "63940516-2c7d-4e8f-c245-51627384c005"; :>> outcome = VerdictKind::pass; :>> judgedAgainst = "fe54cc7"; :>> judgedAt = "2026-07-17"; :>> judgedBy = "claudeOpus"; }
    verification saStandupGate : Test { :>> id = "63940516-2c7d-4e8f-c245-51627384c006"; :>> title = "Sprint 245 standup gate"; :>> createdAt = "2026-07-17"; :>> createdBy = "claudeOpus"; :>> method = VerificationMethod::inspect; :>> procedureText = "Approach: grammar_json = distinct observed triples + per-type up/down; viewer reads it for the create picker (scope + neighbours) + connect kinds (per pair). Grammar is a pure view. No blockers."; }
    part saStandupGateR1 : TestResult { :>> id = "63940516-2c7d-4e8f-c245-51627384c007"; :>> outcome = VerdictKind::pass; :>> judgedAgainst = "fe54cc7"; :>> judgedAt = "2026-07-17"; :>> judgedBy = "claudeOpus"; }
    verification saImplementGate : Test { :>> id = "63940516-2c7d-4e8f-c245-51627384c008"; :>> title = "Sprint 245 implement gate"; :>> createdAt = "2026-07-17"; :>> createdBy = "claudeOpus"; :>> method = VerificationMethod::demo; :>> procedureText = "Implemented (keel@fe54cc7, viewer@f860b5f). Live-verified: scoped picker limits to SR + neighbours; Need->SR connect = [satisfy]. clippy + validate + guard + check-engine green."; }
    part saImplementGateR1 : TestResult { :>> id = "63940516-2c7d-4e8f-c245-51627384c009"; :>> outcome = VerdictKind::pass; :>> judgedAgainst = "fe54cc7"; :>> judgedAt = "2026-07-17"; :>> judgedBy = "claudeOpus"; }
    verification saReviewGate : Test { :>> id = "63940516-2c7d-4e8f-c245-51627384c00a"; :>> title = "Sprint 245 review gate"; :>> createdAt = "2026-07-17"; :>> createdBy = "claudeOpus"; :>> method = VerificationMethod::inspect; :>> procedureText = "Reviewed. Grammar-as-computed-view keeps the engine invariant (everything derivable is a view) + avoids freezing schema — an elegant fit. Scope-aware creation is honestly gated (scope from the active lens; full-list escape preserved). Connect stays permissive on unobserved pairs (won't block a valid new pattern) while nudging to observed ones. The D0127 acceptance is correctly LEFT for the human (proposed, not fabricated). Clean."; }
    part saReviewGateR1 : TestResult { :>> id = "63940516-2c7d-4e8f-c245-51627384c00b"; :>> outcome = VerdictKind::pass; :>> judgedAgainst = "fe54cc7"; :>> judgedAt = "2026-07-17"; :>> judgedBy = "claudeOpus"; }
    verification saCloseOutGate : Test { :>> id = "63940516-2c7d-4e8f-c245-51627384c00c"; :>> title = "Sprint 245 closeOut gate (autonomous, D0049)"; :>> createdAt = "2026-07-17"; :>> createdBy = "claudeOpus"; :>> method = VerificationMethod::inspect; :>> procedureText = "Autonomous closeOut (D0049): grammar + scope-aware creation delivered + verified. Self-evidencing. This completes the 2026-07-17 direction (create-linkage, system-bound views, grammar, scope-aware authoring). PENDING: the human's end-of-sitting per-sitting review — including accepting D0127 (proposed)."; }
    part saCloseOutGateR1 : TestResult { :>> id = "63940516-2c7d-4e8f-c245-51627384c00d"; :>> outcome = VerdictKind::pass; :>> judgedAgainst = "fe54cc7"; :>> judgedAt = "2026-07-17"; :>> judgedBy = "claudeOpus"; }
    verification saRetroGate : Test { :>> id = "63940516-2c7d-4e8f-c245-51627384c00e"; :>> title = "Sprint 245 retro gate (autonomous, D0049)"; :>> createdAt = "2026-07-17"; :>> createdBy = "claudeOpus"; :>> method = VerificationMethod::analyze; :>> procedureText = "Autonomous retro (D0049). WELL: chose grammar-as-computed-observed-view over an authored metamodel — decision-light, generative, no frozen-schema change, and it auto-reflects real usage; the same /api/grammar drives both scope-aware create + connect constraints. Recorded D0127 as PROPOSED and left acceptance to the human (no fabricated sign-off, D0106). AVOIDABLE-ISSUE: static server dropped again mid-session (restarted) — now a repeat; worth a tiny keep-alive if it recurs once more. LESSON: when a 'grammar/metamodel' is asked for, first check whether it can be COMPUTED from existing structure before authoring one. Estimate 3 pts. The Architect Sure sitting's build work is complete; awaiting per-sitting sign-off."; }
    part saRetroGateR1 : TestResult { :>> id = "63940516-2c7d-4e8f-c245-51627384c00f"; :>> outcome = VerdictKind::pass; :>> judgedAgainst = "fe54cc7"; :>> judgedAt = "2026-07-17"; :>> judgedBy = "claudeOpus"; }
}
