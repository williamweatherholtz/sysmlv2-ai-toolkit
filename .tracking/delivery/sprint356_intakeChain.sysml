// ProjectDeliveryS356 — Sprint 356: intake is built. Statement -> UserStory -> triage, on their
// vocabulary, verified on their own words. CHANGE (§3a, D0166 accepted). 8 pts.
package ProjectDeliveryS356 {
    private import EngineElement::*;
    private import EngineWork::*;
    private import EngineVerification::*;
    private import EngineRelationships::*;

    #CharteredBy dependency from intakeStory to d0166;

    part intakeStory : Story {
        :>> id = "0d8005f0-0814-65f0-9b3e-0000003005f0";
        :>> title = "Sprint 356: the intake chain — record, translate, triage, route, audit (8 pts)";
        :>> createdAt = "2026-08-20"; :>> createdBy = "claudeOpus5"; :>> kind = WorkKind::modeling; :>> priority = WorkPriority::p0; :>> owner = "claudeOpus5"; :>> estimatedPoints = 8;
    }

    action def DeliveryRunS356 {
        action storyIntake;
        verification storyIntakeDoD : Test { :>> id = "0d8005f1-0814-65f1-9b3e-0000003005f1"; :>> method = VerificationMethod::test; :>> procedureText = "Delivered by dcIntakeChain and dcDeckWorkSurface. D0166 is accepted, so this APPLIES it rather than proposing it. `EngineIntake` adds Statement and UserStory to schema/core with `metadata def Implicates`; ImplicationKind carries their nine members verbatim plus five answering their question about others - question, priority, attestation, correction, convention - and none. `keel intake` computes unparsed / unrouted / unsourced. A process and its skill are registered as a pair. VERIFIED ON THEIR OWN WORDS rather than on a fixture: their message became 3 Statements, 3 UserStories triaged bug/process/need with a triageNote each, 7 downstream items linked by #Implicates, and the view reads 0 unparsed, 0 unrouted, 0 stories without a source. THE OTHER HALF OF THEIR REQUEST: the artifact critique's five findings are recorded as issue161-165 against dcDeckWorkSurface, unscoped because two of them need their direction. validate 387 clean; check-engine clean; 36 guards ALL PASS; 191 tests; clippy clean."; }
        part storyIntakeDoDR1 : TestResult { :>> id = "0d8005f2-0814-65f2-9b3e-0000003005f2"; :>> outcome = VerdictKind::pass; :>> judgedAgainst = "a7050c2"; :>> judgedAt = "2026-08-20"; :>> judgedBy = "claudeOpus5"; }
    }

    verification ikRefineGate : Test { :>> id = "0d8005f3-0814-65f3-9b3e-0000003005f3"; :>> title = "Sprint 356 refine gate (DoR)"; :>> createdAt = "2026-08-20"; :>> createdBy = "claudeOpus5"; :>> method = VerificationMethod::inspect; :>> procedureText = "DoR. Three parts: record the critique findings as issues, BUILD the intake chain (D0166 is accepted, so applying is authorized rather than proposed), and answer their question about other implication kinds. The third is the one worth scoping carefully - they asked a question, and inventing categories would be worse than answering from evidence, so the five additions are the kinds this session's own statements actually fell into. estimatedPoints=8."; }
    part ikRefineGateR1 : TestResult { :>> id = "0d8005f4-0814-65f4-9b3e-0000003005f4"; :>> outcome = VerdictKind::pass; :>> judgedAgainst = "a7050c2"; :>> judgedAt = "2026-08-20"; :>> judgedBy = "claudeOpus5"; }

    verification ikStandupGate : Test { :>> id = "0d8005f5-0814-65f5-9b3e-0000003005f5"; :>> title = "Sprint 356 standup gate"; :>> createdAt = "2026-08-20"; :>> createdBy = "claudeOpus5"; :>> method = VerificationMethod::inspect; :>> procedureText = "Approach: prove the chain on THEIR MESSAGE rather than on a fixture. A fixture would have shown the code runs; their words showed that a compound statement needs SEVERAL user stories - the triage verdict is singular, so a statement implicating three things has three implications - which is a design consequence a fixture would have hidden. Also: keep the attribute `implication` distinct from the edge `#Implicates`, because naming both the same would have invited exactly the conflation D0166 was revised to prevent. No blockers."; }
    part ikStandupGateR1 : TestResult { :>> id = "0d8005f6-0814-65f6-9b3e-0000003005f6"; :>> outcome = VerdictKind::pass; :>> judgedAgainst = "a7050c2"; :>> judgedAt = "2026-08-20"; :>> judgedBy = "claudeOpus5"; }

    verification ikImplementGate : Test { :>> id = "0d8005f7-0814-65f7-9b3e-0000003005f7"; :>> title = "Sprint 356 implement gate"; :>> createdAt = "2026-08-20"; :>> createdBy = "claudeOpus5"; :>> method = VerificationMethod::test; :>> procedureText = "THE FIVE ADDITIONS TO THEIR VOCABULARY ARE EVIDENCE, NOT INVENTION, and that is the part I would defend: question (is that in our schema already), priority (defer the hosted service for now), attestation (their sign-off - the LARGEST category by count in this session and absent from the nine), correction (viewer on a single machine is still 1, which corrected a record of mine), convention (use user story instead of story). Plus none, so that implicating nothing is recorded rather than omitted. A statement the vocabulary cannot express is a CHANGE to the vocabulary, never a forced fit - a wrong triage is worse than an absent one because it routes real direction to the wrong place and looks handled. THREE GAPS THE VIEW COMPUTES: unparsed, unrouted, unsourced. Unrouted deserves its own name because triaged-then-dropped LOOKS handled. Unsourced is 472 of 479 today and is labelled a FLOOR on the record's completeness in the payload itself - never a claim that nobody asked for the work, since nothing can force a statement to be written down. FOUR SMALL FIGHTS WITH THE ENGINE'S OWN CONTROLS, each of which was the control being right: the marker guard rejected #Implicates until it was declared as metadata def; process-skill rejected the pair twice because its matcher tokenises on whitespace and quotes, so backticks and then a leading parenthesis around the path each hid it; and clippy required doc backticks and an item hoisted above statements."; }
    part ikImplementGateR1 : TestResult { :>> id = "0d8005f8-0814-65f8-9b3e-0000003005f8"; :>> outcome = VerdictKind::pass; :>> judgedAgainst = "a7050c2"; :>> judgedAt = "2026-08-20"; :>> judgedBy = "claudeOpus5"; }

    verification ikReviewGate : Test { :>> id = "0d8005f9-0814-65f9-9b3e-0000003005f9"; :>> title = "Sprint 356 review gate"; :>> createdAt = "2026-08-20"; :>> createdBy = "claudeOpus5"; :>> method = VerificationMethod::inspect; :>> procedureText = "Reviewed. THE NUMBER THAT MATTERS IS 472 OF 479 UNSOURCED, and it is exactly the uncomfortable figure D0166 predicted. Read honestly it says: this repository holds 479 Needs, SystemRequirements, Issues and Decisions, and 7 of them can point at a human statement. Most of the rest ARE legitimately mine to have raised - defects I found, decisions the process required - and nobody could previously tell the ratio at all. That is why the view labels it a floor on the RECORD rather than a verdict on the human, and why the honest use of it is a TREND rather than a level: it should fall as intake runs, and if it does not, intake is not being used. WHAT I DID NOT DO: retro-record the session's earlier statements. It would improve the number, and it would be me writing their words from memory into a field whose entire value is being verbatim - the one thing this schema exists to prevent. The record starts now and says so."; }
    part ikReviewGateR1 : TestResult { :>> id = "0d8005fa-0814-65fa-9b3e-0000003005fa"; :>> outcome = VerdictKind::pass; :>> judgedAgainst = "a7050c2"; :>> judgedAt = "2026-08-20"; :>> judgedBy = "claudeOpus5"; }

    verification ikCloseOutGate : Test { :>> id = "0d8005fb-0814-65fb-9b3e-0000003005fb"; :>> title = "Sprint 356 closeOut gate (autonomous, D0049)"; :>> createdAt = "2026-08-20"; :>> createdBy = "claudeOpus5"; :>> method = VerificationMethod::inspect; :>> procedureText = "Autonomous closeOut (D0049). Delivered: schema, view, CLI command, computed-view binding, process, skill, registry entry, doc-sync on CLAUDE.md's lens list, and the first real intake records. Recorded but NOT built: issue161-165 against dcDeckWorkSurface, deliberately unscoped - issue164 (three buttons, four meanings) wants a schema conversation and issue165 (judge but not act) wants a write path from an artifact to this machine, which D0158 makes local-only by decision. issue160's engine-wide legibility work is also unscoped. validate 387 clean; check-engine clean; 36 guards ALL PASS; 191 tests; clippy clean."; }
    part ikCloseOutGateR1 : TestResult { :>> id = "0d8005fc-0814-65fc-9b3e-0000003005fc"; :>> outcome = VerdictKind::pass; :>> judgedAgainst = "a7050c2"; :>> judgedAt = "2026-08-20"; :>> judgedBy = "claudeOpus5"; }

    verification ikRetroGate : Test { :>> id = "0d8005fd-0814-65fd-9b3e-0000003005fd"; :>> title = "Sprint 356 retro gate (autonomous, D0049)"; :>> createdAt = "2026-08-20"; :>> createdBy = "claudeOpus5"; :>> method = VerificationMethod::analyze; :>> procedureText = "Autonomous retro (D0049) under D0131's retroTrack. WELL: (1) the chain was proved on their own message rather than a fixture, which surfaced that a compound statement needs several user stories - a fixture would have passed without ever asking the question; (2) the five vocabulary additions came from categories this session actually produced, so the answer is evidence rather than imagination, and attestation being the largest category by count is a fact I would not have guessed; (3) the 472-of-479 number is reported with its meaning attached, as a floor on the record, because an unqualified ratio of AI-invented to human-requested work would be a misleading number about a real question; (4) I did not retro-record earlier statements to improve that number, since writing their words from memory into a verbatim field destroys the one property the field exists for. AVOIDABLE-ISSUE: I fought the process-skill guard twice over punctuation - backticks, then a parenthesis - because its matcher tokenises on whitespace and quotes only. Both times the guard was right that the reference was unreadable, and unhelpful about why. That is a legibility defect of exactly the kind issue160 records, in the guard layer: a control that knows what it wants and will not say. No new item needed - it belongs to issue160, and the example is noted here so it is not lost. SECOND AVOIDABLE-ISSUE: a bash heredoc broke on apostrophes for the fifth time this session, against a remedy recorded twice. Use the Write tool for any content with quotes. Estimate 8 pts, delivered."; }
    part ikRetroGateR1 : TestResult { :>> id = "0d8005fe-0814-65fe-9b3e-0000003005fe"; :>> outcome = VerdictKind::pass; :>> judgedAgainst = "a7050c2"; :>> judgedAt = "2026-08-20"; :>> judgedBy = "claudeOpus5"; }
}
