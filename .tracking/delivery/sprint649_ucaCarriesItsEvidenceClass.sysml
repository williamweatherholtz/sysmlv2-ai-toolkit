// ProjectDeliveryS649 — Sprint 649: Deliver dcUcaCarriesItsEvidenceClass: every UnsafeControlAction's evidence class is computed from its edges, never asserted - `observed` when a dependency edge from the UCA or from a ControllerConstraint bound to it reaches an Issue whose incident happened (discoveredInField = true), `code-read` otherwise - joined into `keel show control-census` as `ucaSummary` / `ucas`, and the stpa-self process gains step stpa2bCensus (D0428, proposed) so the census is read before any UCA is written and the run record carries EVIDENCE and REMOVAL CANDIDATES copied from the lens. Chartered by D0424 (accepted) and the human's words of 2026-09-10 (st115): build evidence around the ways processes are subverted today and integrate it into STPA.. EXECUTE. 3 pts.
package ProjectDeliveryS649 {
    private import EngineElement::*;
    private import EngineWork::*;
    private import EngineVerification::*;
    private import EngineRelationships::*;

    #CharteredBy dependency from ucaCarriesItsEvidenceClassStory to d0424;

    part ucaCarriesItsEvidenceClassStory : Story {
        :>> id = "87855ed0-f61c-416f-804d-e71e2b7bfeec";
        :>> title = "Sprint 649: Deliver dcUcaCarriesItsEvidenceClass: every UnsafeControlAction's evidence class is computed from its edges, never asserted - `observed` when a dependency edge from the UCA or from a ControllerConstraint bound to it reaches an Issue whose incident happened (discoveredInField = true), `code-read` otherwise - joined into `keel show control-census` as `ucaSummary` / `ucas`, and the stpa-self process gains step stpa2bCensus (D0428, proposed) so the census is read before any UCA is written and the run record carries EVIDENCE and REMOVAL CANDIDATES copied from the lens. Chartered by D0424 (accepted) and the human's words of 2026-09-10 (st115): build evidence around the ways processes are subverted today and integrate it into STPA. (3 pts)";
        :>> createdAt = "2026-09-10"; :>> createdBy = "claudeOpus5"; :>> kind = WorkKind::code; :>> priority = WorkPriority::p0; :>> owner = "claudeOpus5"; :>> estimatedPoints = 3;
    }

    action def DeliveryRunS649 {
        action storyUcaCarriesItsEvidenceClass;
        verification storyUcaCarriesItsEvidenceClassDoD : Test { :>> id = "6a307ca0-67bf-4cf4-997b-40a5aef9504d"; :>> method = VerificationMethod::test; :>> procedureText = "The dcUcaCarriesItsEvidenceClassDoD text at HEAD. VERIFY: the unit probe pair in keel-cli/src/view/census.rs (a fixture UCA reaching an in-field Issue classes observed, one reaching none classes code-read; a constraint on a hypothetical control is a removal candidate; a friction control nothing binds is still one), stpa-self run 3 in .tracking/architecture/engine-ucas.sysml carrying `EVIDENCE: 5 observed, 11 code-read` and REMOVAL CANDIDATES naming accept:delegated-words, the process step stpa2bCensus in .engine/processes/stpa-self.sysml, the skill row, CLAUDE.md sec 2 naming ucaSummary."; }
        // RAN: verifier receipt (D0425) sprint649: validate 737 clean; check-engine clean; guard ALL PASS; gate --fast clean; sync-claude --check clean; control-census observed 5 codeRead 11, 9 removal candidates incl. accept:delegated-words; cargo test census 9 passed; clippy 0; control_census_names_friction passed
        part storyUcaCarriesItsEvidenceClassDoDR1 : TestResult { :>> id = "ac25f8f1-88e7-4b5c-84cf-c38b888ce667"; :>> outcome = VerdictKind::pass; :>> judgedAgainst = "7674e12e56a2886094d0849917d7e29bfc9e8627"; :>> judgedAt = "2026-09-10"; :>> judgedBy = "claudeOpus5"; }
    }

    verification ucaCarriesItsEvidenceClassRefineGate : Test { :>> id = "0ab9dde9-53ea-491b-826d-b0d3e7cdd125"; :>> title = "Sprint 649 refine gate (DoR)"; :>> createdAt = "2026-09-10"; :>> createdBy = "claudeOpus5"; :>> method = VerificationMethod::inspect; :>> procedureText = "Scope: the join in view/census.rs (uca_facts / uca_rows / uca_removal_candidates, pure core so the probe pair runs without a tree), the `hook-rule:` title prefix so control-map.sysml can declare a harness hook rule as binding the agent alone, the process step + skill row + D0428 recorded proposed beside them (process-change, D0337), stpa-self run 3 over agentEditsDeliverable (the stpa-currency NEXT TRANCHE) as the first run under the step, and five Issue flags corrected to discoveredInField = true (issue360, issue374, issue375, issue372, issue398 - each title reports an act that happened). 3 points (a module extension with tests plus a process step and an analysis run)."; }
    part ucaCarriesItsEvidenceClassRefineGateR1 : TestResult { :>> id = "7ef0ca1f-e960-44b6-bfe7-c5558911e4ef"; :>> outcome = VerdictKind::pass; :>> judgedAgainst = "7674e12e56a2886094d0849917d7e29bfc9e8627"; :>> judgedAt = "2026-09-10"; :>> judgedBy = "claudeOpus5"; }
    verification ucaCarriesItsEvidenceClassStandupGate : Test { :>> id = "cfbf4c53-de48-4a45-bcee-4a91435ad61e"; :>> title = "Sprint 649 standup gate"; :>> createdAt = "2026-09-10"; :>> createdBy = "claudeOpus5"; :>> method = VerificationMethod::inspect; :>> procedureText = "Blockers met and resolved in-sprint: the insertion of the join block landed between control_census's doc comment and its signature (six clippy errors, fixed by moving the comment); the first removal-candidate rule listed only constraint-bound controls, so the DoD's named candidate (delegated-words, which no constraint binds) was absent - the rule now also lists friction controls nothing binds; heredoc-backslash was an evidenced ledger row no constraint could bind because the control map had no way to declare a hook rule - the `hook-rule:` prefix and ctlHeredocBackslash close that."; }
    part ucaCarriesItsEvidenceClassStandupGateR1 : TestResult { :>> id = "c757eae7-c131-49da-a700-e6fe367367b1"; :>> outcome = VerdictKind::pass; :>> judgedAgainst = "7674e12e56a2886094d0849917d7e29bfc9e8627"; :>> judgedAt = "2026-09-10"; :>> judgedBy = "claudeOpus5"; }
    verification ucaCarriesItsEvidenceClassImplementGate : Test { :>> id = "93fda0fa-cb36-4159-80bc-436751899fdd"; :>> title = "Sprint 649 implement gate"; :>> createdAt = "2026-09-10"; :>> createdBy = "claudeOpus5"; :>> method = VerificationMethod::test; :>> procedureText = "keel-cli/src/view/census.rs (UcaEvidence, UcaFacts, UcaRow, uca_rows, uca_removal_candidates, uca_facts, uca_json, ucaSummary/ucas output, hook-rule declaration, three new unit tests), .engine/processes/stpa-self.sysml (stpa2bCensus, successions, stpa5 text), .engine/skills/stpa-self/SKILL.md + regenerated .claude/skills/stpa-self/SKILL.md, .engine/decisions/0428-stpaSelfReadsTheCensusBeforeAUca.sysml (proposed, #DependsOn d0424, #DerivedFrom st115), .tracking/architecture/engine-ucas.sysml (run 3: three UCAs, three constraints, stpaRun3 + result), .tracking/architecture/control-map.sysml (ctlHeredocBackslash), .tracking/issues-claudeOpus5.sysml (five flags), CLAUDE.md sec 2."; }
    // RAN: verifier receipt (D0425) sprint649: cargo test census 9 passed; clippy 0; validate/check-engine/guard/gate --fast all clean
    part ucaCarriesItsEvidenceClassImplementGateR2 : TestResult { :>> id = "754eb94b-cf71-4923-8bf8-27550d43195f"; :>> outcome = VerdictKind::pass; :>> judgedAgainst = "7674e12e56a2886094d0849917d7e29bfc9e8627"; :>> judgedAt = "2026-09-10"; :>> judgedBy = "claudeOpus5"; }
    verification ucaCarriesItsEvidenceClassReviewGate : Test { :>> id = "5f518cd0-ca4e-4a01-a0fb-85e9ad1ed669"; :>> title = "Sprint 649 review gate — three passes per D0172"; :>> createdAt = "2026-09-10"; :>> createdBy = "claudeOpus5"; :>> method = VerificationMethod::inspect; :>> procedureText = "On this tree: 16 UCAs, 5 observed (issue360, issue375, issue374, issue372, issue398) and 11 code-read; 9 removal candidates - the two friction controls nothing binds and seven constraint-level rows (six constraints, one standing on two controls) on hypothetical controls; evidencedWithoutUca lists eight evidenced controls no analysis stands on, the stpa-currency gap the DoD names. Census 76 controls / 2 friction / 64 hypothetical / 10 evidenced. Each removal is its own Decision (D0303) and none is taken here; D0428 waits for the human (process-change)."; }
    part ucaCarriesItsEvidenceClassReviewGateR1 : TestResult { :>> id = "6f3b79c8-e573-49ab-b1e0-c38ae3462ec8"; :>> outcome = VerdictKind::pass; :>> judgedAgainst = "7674e12e56a2886094d0849917d7e29bfc9e8627"; :>> judgedAt = "2026-09-10"; :>> judgedBy = "claudeOpus5"; }
    verification ucaCarriesItsEvidenceClassCloseOutGate : Test { :>> id = "7bd898a6-b3c4-42b8-a741-11a52cb4787c"; :>> title = "Sprint 649 closeOut gate (autonomous, D0049)"; :>> createdAt = "2026-09-10"; :>> createdBy = "claudeOpus5"; :>> method = VerificationMethod::inspect; :>> procedureText = "Recorded by the RECORDER subagent from the verifier's receipt (D0425); the primary wrote no ceremony result."; }
    part ucaCarriesItsEvidenceClassCloseOutGateR1 : TestResult { :>> id = "193f0b78-c0df-4117-a0ab-45a7fdacfa62"; :>> outcome = VerdictKind::pass; :>> judgedAgainst = "7674e12e56a2886094d0849917d7e29bfc9e8627"; :>> judgedAt = "2026-09-10"; :>> judgedBy = "claudeOpus5"; }
    verification ucaCarriesItsEvidenceClassRetroGate : Test { :>> id = "0bebc368-bb9a-4161-90e8-ef7cb71eae58"; :>> title = "Sprint 649 retro gate (autonomous, D0049)"; :>> createdAt = "2026-09-10"; :>> createdBy = "claudeOpus5"; :>> method = VerificationMethod::analyze; :>> procedureText = "Avoidable-issue scan: the candidate rule was stated from the constraint join and only found incomplete when read against the DoD's named case (delegated-words) - the probe pair now carries that case as a_friction_control_no_constraint_binds_is_still_a_removal_candidate, so the rule cannot regress silently. The anchor slip that put a doc comment on the wrong item was caught by clippy, a control already in the commit path; it is already tracked as the anchor class in issue398, whose resolver dcPatchesFailWhenTheyMiss stands; no new item. The D0425 verifier/recorder split found a control gap: the recorder ran append-gate-result on the method=test Implement gate without --evidence, the write LANDED (the refusal CLAUDE.md names is only guard 52 at the turn boundary), the Stop hook yielded obligationf76e7aba and the recorder improvised a second result - recorded as issue448 (in-field), resolver dcReceiptlessResultIsRefusedAtWrite co-added at the head of the frontier, and the receiptless line removed from this uncommitted record."; }
    part ucaCarriesItsEvidenceClassRetroGateR1 : TestResult { :>> id = "ce926a17-2951-4d26-be4f-1eb17dac3bc3"; :>> outcome = VerdictKind::pass; :>> judgedAgainst = "7674e12e56a2886094d0849917d7e29bfc9e8627"; :>> judgedAt = "2026-09-10"; :>> judgedBy = "claudeOpus5"; }
}
