// ProjectDeliveryS246 — Sprint 246: edit an item's attributes in place (viewerEditItem, D0126) — the EDIT
// half of srViewerAuthoringSurface. keel POST /api/item/attr (owner-of-record; governed → supersede) + a
// viewer Edit dialog. Completes the create/edit/connect/critique authoring surface. EXECUTE. 2 pts.
package ProjectDeliveryS246 {
    private import EngineElement::*;
    private import EngineWork::*;
    private import EngineVerification::*;
    private import EngineRelationships::*;

    #CharteredBy dependency from viewerEditItemStory to d0126;

    part viewerEditItemStory : Story {
        :>> id = "63940516-2c7d-4e8f-c246-51627384c001";
        :>> title = "Sprint 246: viewerEditItem (2 pts) - edit an item's attributes in place; governed types route to supersede";
        :>> createdAt = "2026-07-17"; :>> createdBy = "wweatherholtz"; :>> kind = WorkKind::code; :>> priority = WorkPriority::p2; :>> owner = "claudeOpus"; :>> estimatedPoints = 2;
    }

    action def DeliveryRunS246 {
        action storyViewerEditItem;
        verification storyViewerEditItemDoD : Test { :>> id = "63940516-2c7d-4e8f-c246-51627384c002"; :>> method = VerificationMethod::demo; :>> procedureText = "Delivers the EDIT half of srViewerAuthoringSurface (D0126) — change an existing item's attributes, completing create/edit/connect/critique. KEEL (v1.17.0, fc62b2f): write::set_attr locates an item's declaration across .tracking/ and replaces `:>> attr = ..;` inside its block (or inserts it); POST /api/item/attr REFUSES GOVERNED_TYPES (Decision/Need/SystemRequirement/SubsystemRequirement — those must supersede, §2.4) and edits other types in place (owner-of-record, D0108); string quoted+sanitized, enum -> EnumType::member; never auto-commits. Also fixed AUTHORED_HEADER to import Architecture/Indicator/Computed/Process/Skills so created items of those types RESOLVE (a real gap /api/check caught during verification). VIEWER (d5b3878): right-click -> Edit... -> for owner-of-record types an edit dialog shows current attributes (String -> text, enum -> member select) prefilled, writes only CHANGED fields via /api/item/attr with a D0108 conflict baseline captured on open + inline /api/check; governed types route to the Supersede (superseding Decision) dialog. VERIFY (demo, live): edited a Component + an Issue in place (read-back confirms new value; validates clean); Edit on a Need opens the Supersede dialog (governed routing); a created Component resolves after the import fix; untriaged-Issue + unresolved-type both honestly surfaced by /api/check before the fix. clippy + validate + guard + check-engine green. This COMPLETES srViewerAuthoringSurface (create/edit/connect + critique/disposition)."; }
        part storyViewerEditItemDoDR1 : TestResult { :>> id = "63940516-2c7d-4e8f-c246-51627384c003"; :>> outcome = VerdictKind::pass; :>> judgedAgainst = "fc62b2f"; :>> judgedAt = "2026-07-17"; :>> judgedBy = "claudeOpus"; }
    }

    verification eiRefineGate : Test { :>> id = "63940516-2c7d-4e8f-c246-51627384c004"; :>> title = "Sprint 246 refine gate (DoR)"; :>> createdAt = "2026-07-17"; :>> createdBy = "claudeOpus"; :>> method = VerificationMethod::inspect; :>> procedureText = "DoR: viewerEditItem ready. Scope: in-place attribute set (non-governed) + governed→supersede routing. #CharteredBy d0126. estimatedPoints=2. DoR met."; }
    part eiRefineGateR1 : TestResult { :>> id = "63940516-2c7d-4e8f-c246-51627384c005"; :>> outcome = VerdictKind::pass; :>> judgedAgainst = "fc62b2f"; :>> judgedAt = "2026-07-17"; :>> judgedBy = "claudeOpus"; }
    verification eiStandupGate : Test { :>> id = "63940516-2c7d-4e8f-c246-51627384c006"; :>> title = "Sprint 246 standup gate"; :>> createdAt = "2026-07-17"; :>> createdBy = "claudeOpus"; :>> method = VerificationMethod::inspect; :>> procedureText = "Approach: set_attr (find declaration + block, replace/insert attr line); serve refuses governed types + builds the literal; viewer edit dialog writes only changed fields + captures a conflict baseline. No blockers."; }
    part eiStandupGateR1 : TestResult { :>> id = "63940516-2c7d-4e8f-c246-51627384c007"; :>> outcome = VerdictKind::pass; :>> judgedAgainst = "fc62b2f"; :>> judgedAt = "2026-07-17"; :>> judgedBy = "claudeOpus"; }
    verification eiImplementGate : Test { :>> id = "63940516-2c7d-4e8f-c246-51627384c008"; :>> title = "Sprint 246 implement gate"; :>> createdAt = "2026-07-17"; :>> createdBy = "claudeOpus"; :>> method = VerificationMethod::demo; :>> procedureText = "Implemented (keel@fc62b2f, viewer@d5b3878). Live-verified: in-place edit of Component/Issue; governed→supersede routing; import fix so all created types resolve. clippy + validate + guard + check-engine green."; }
    part eiImplementGateR1 : TestResult { :>> id = "63940516-2c7d-4e8f-c246-51627384c009"; :>> outcome = VerdictKind::pass; :>> judgedAgainst = "fc62b2f"; :>> judgedAt = "2026-07-17"; :>> judgedBy = "claudeOpus"; }
    verification eiReviewGate : Test { :>> id = "63940516-2c7d-4e8f-c246-51627384c00a"; :>> title = "Sprint 246 review gate"; :>> createdAt = "2026-07-17"; :>> createdBy = "claudeOpus"; :>> method = VerificationMethod::inspect; :>> procedureText = "Reviewed. The governed/owner-of-record split is the disciplined core (D0108/§2.4): governed items supersede (auditable), others edit in place with provenance-via-git + inline guards; never auto-committed. The import gap was found honestly by /api/check and fixed at root, not papered over. Only changed fields are written. Clean — completes the authoring surface."; }
    part eiReviewGateR1 : TestResult { :>> id = "63940516-2c7d-4e8f-c246-51627384c00b"; :>> outcome = VerdictKind::pass; :>> judgedAgainst = "fc62b2f"; :>> judgedAt = "2026-07-17"; :>> judgedBy = "claudeOpus"; }
    verification eiCloseOutGate : Test { :>> id = "63940516-2c7d-4e8f-c246-51627384c00c"; :>> title = "Sprint 246 closeOut gate (autonomous, D0049)"; :>> createdAt = "2026-07-17"; :>> createdBy = "claudeOpus"; :>> method = VerificationMethod::inspect; :>> procedureText = "Autonomous closeOut (D0049): edit-in-place + governed routing delivered + verified; srViewerAuthoringSurface COMPLETE (create/edit/connect/critique/disposition). Self-evidencing. The ready frontier for the Architect Sure line is now empty; awaiting the human's per-sitting sign-off (incl. accepting D0126/D0127, proposed)."; }
    part eiCloseOutGateR1 : TestResult { :>> id = "63940516-2c7d-4e8f-c246-51627384c00d"; :>> outcome = VerdictKind::pass; :>> judgedAgainst = "fc62b2f"; :>> judgedAt = "2026-07-17"; :>> judgedBy = "claudeOpus"; }
    verification eiRetroGate : Test { :>> id = "63940516-2c7d-4e8f-c246-51627384c00e"; :>> title = "Sprint 246 retro gate (autonomous, D0049)"; :>> createdAt = "2026-07-17"; :>> createdBy = "claudeOpus"; :>> method = VerificationMethod::analyze; :>> procedureText = "Autonomous retro (D0049). WELL: enforced the governed-vs-owner-of-record distinction at the endpoint (governed types can't be overwritten in place — they supersede), keeping edits disciplined; wrote only changed fields; and when /api/check surfaced an unresolved-type on a created Component, fixed the ROOT (authored.sysml imports) rather than suppressing it — proof the honest-state gate pays off. AVOIDABLE-ISSUE: the create/edit authored.sysml imports were incomplete at first (only caught on a Component) — LESSON: seed the authored-file header with ALL engine schema packages up front. Estimate 2 pts. The Architect Sure sitting is build-complete; awaiting per-sitting sign-off."; }
    part eiRetroGateR1 : TestResult { :>> id = "63940516-2c7d-4e8f-c246-51627384c00f"; :>> outcome = VerdictKind::pass; :>> judgedAgainst = "fc62b2f"; :>> judgedAt = "2026-07-17"; :>> judgedBy = "claudeOpus"; }
}
