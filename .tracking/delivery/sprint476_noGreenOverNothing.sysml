// ProjectDeliveryS476 - Sprint 476: orient returned nothing-to-do for a repository full of work, and called it COMPUTED. EXECUTE. 3 pts.
package ProjectDeliveryS476 {
    private import EngineElement::*;
    private import EngineWork::*;
    private import EngineVerification::*;
    private import EngineRelationships::*;

    #CharteredBy dependency from noGreenStory to d0241;

    part noGreenStory : Story {
        :>> id = "1090fe74-e003-4caf-9b47-a5ca1e2dc0ff";
        :>> title = "Sprint 476: a command that reads a model refuses rather than answering over nothing, and the root search stops at the repository (3 pts)";
        :>> createdAt = "2026-08-27"; :>> createdBy = "claudeOpus5"; :>> kind = WorkKind::code; :>> priority = WorkPriority::p1; :>> owner = "claudeOpus5"; :>> estimatedPoints = 3;
    }

    action def DeliveryRunS476 {
        action storyNoGreen;
        verification storyNoGreenDoD : Test { :>> id = "b4a036da-fcc7-4857-8580-357c125d3eb0"; :>> method = VerificationMethod::test; :>> procedureText = "DELIVERED: dcNoCommandReportsGreenOverNothing (issue281) under D0241. workspace::require_project refuses when a resolved root is not a keel project, naming the projects the repository does hold, and is called from every root-resolution path: root_arg for the 41 commands that take a positional ROOT, cmd_view0 for the zero-argument views, verification's repo_arg site, attestation inside its own module, and indicators. find_repo_root stops ascending at the repository boundary. sync, land, projects and gate --workspace are deliberately NOT covered - they are repository-scoped or workspace-level by design. Held by keel-cli/tests/no_green_over_nothing.rs, which sweeps the set in both directions."; }
    // RAN: cargo test --release => 13 suites 0 failures, incl the new keel-cli/tests/no_green_over_nothing.rs (sweeps 12 model readers, asserts the refusal NAMES the projects, and asserts all 12 still work inside a project) | cargo clippy --release --all-targets => 0 errors | live sweep in C:/kt/w4 (three peer projects, no project at the root): 22 model-reading commands, ALL exit 2 - orient whats-next check-engine validate coverage verification suspect audit open-issues indicators orphans rootedness dispositions attestation controls hardening decisions tier-satisfaction concern-coverage sitting-coverage governing-version intake - and 8 of 8 sampled still exit 0 inside alpha | repo boundary: keel validate with no argument from a SEPARATE git repo nested inside a project => exit 2 naming the boundary, where it previously validated the OUTER repo and reported clean; from a plain subdirectory of the project => exit 0, 1 tracking file clean | indicators: positional root now honoured - <workspace> => exit 2, <a real project> => exit 0.
        part storyNoGreenDoDR1 : TestResult { :>> id = "21716a59-6a5b-4604-9576-38499a872e0c"; :>> outcome = VerdictKind::pass; :>> judgedAgainst = "3bb8e77"; :>> judgedAt = "2026-08-27"; :>> judgedBy = "claudeOpus5"; }
    }

    verification noGreenRefineGate : Test { :>> id = "813e5b6d-7499-4f3a-a745-65f0bb5610c7"; :>> title = "Sprint 476 refine gate (DoR)"; :>> createdAt = "2026-08-27"; :>> createdBy = "claudeOpus5"; :>> method = VerificationMethod::inspect; :>> procedureText = "DoR: dcNoCommandReportsGreenOverNothing ranked first after sprint 475. Reproduced all three named symptoms before designing - orient exit 0 with an empty ready list and answerStatus COMPUTED, whats-next COMPUTED-EMPTY over zero items, check-engine validated-clean over zero files - and confirmed validate already refuses at exit 2, so the fix is EXTENDING one refusal rather than inventing one. Resolver: dcNoCommandReportsGreenOverNothing. estimatedPoints=3. #CharteredBy d0241."; }
    part noGreenRefineGateR1 : TestResult { :>> id = "3f566a37-1f17-49a7-a744-5296b449ceb6"; :>> outcome = VerdictKind::pass; :>> judgedAgainst = "3bb8e77"; :>> judgedAt = "2026-08-27"; :>> judgedBy = "claudeOpus5"; }
    verification noGreenStandupGate : Test { :>> id = "6830f9a9-99b0-46c6-a2d5-a3cf76452440"; :>> title = "Sprint 476 standup gate"; :>> createdAt = "2026-08-27"; :>> createdBy = "claudeOpus5"; :>> method = VerificationMethod::inspect; :>> procedureText = "Approach: one shared precondition rather than a per-command edit, because a per-command edit is a per-command edit to FORGET - and forgetting is precisely how the issue269 refusal came to cover exactly one command. Chose REFUSAL over aggregation deliberately: orient across a workspace is the more useful answer eventually, but merging ranked frontiers needs a declared cross-project order, and declaration order IS priority (D0052) with no declared order ACROSS projects - so aggregating would invent a priority silently, which is worse than refusing. Refusal names the projects and lets the caller choose."; }
    part noGreenStandupGateR1 : TestResult { :>> id = "536dcddc-7f69-40de-a62a-775709033b15"; :>> outcome = VerdictKind::pass; :>> judgedAgainst = "3bb8e77"; :>> judgedAt = "2026-08-27"; :>> judgedBy = "claudeOpus5"; }
    verification noGreenImplementGate : Test { :>> id = "e1212e0b-4467-4e3b-add8-5d1bca238323"; :>> title = "Sprint 476 implement gate"; :>> createdAt = "2026-08-27"; :>> createdBy = "claudeOpus5"; :>> method = VerificationMethod::test; :>> procedureText = "Implemented at what I believed was the single chokepoint - root_arg, which 41 commands already call and which already had an error channel. Nine commands then refused and THREE still exited 0, because they resolve roots elsewhere. Sweeping every model reader by hand found two; the TEST found the third, and the third was a worse defect than the one being fixed: indicators accepted --root only, so a POSITIONAL root was silently IGNORED and the view was computed against whatever project the process was standing in - keel indicators <someWorkspace> reported real numbers about a DIFFERENT project and exited 0. Not a zeroed green; a confident wrong answer. root_arg's own unit test also had to change, because root_arg now validates as well as parses and the test used synthetic non-project paths."; }
    // RAN: cargo test --release => 13 suites 0 failures, incl the new keel-cli/tests/no_green_over_nothing.rs (sweeps 12 model readers, asserts the refusal NAMES the projects, and asserts all 12 still work inside a project) | cargo clippy --release --all-targets => 0 errors | live sweep in C:/kt/w4 (three peer projects, no project at the root): 22 model-reading commands, ALL exit 2 - orient whats-next check-engine validate coverage verification suspect audit open-issues indicators orphans rootedness dispositions attestation controls hardening decisions tier-satisfaction concern-coverage sitting-coverage governing-version intake - and 8 of 8 sampled still exit 0 inside alpha | repo boundary: keel validate with no argument from a SEPARATE git repo nested inside a project => exit 2 naming the boundary, where it previously validated the OUTER repo and reported clean; from a plain subdirectory of the project => exit 0, 1 tracking file clean | indicators: positional root now honoured - <workspace> => exit 2, <a real project> => exit 0.
    part noGreenImplementGateR1 : TestResult { :>> id = "b6ff4511-505c-4e71-906e-b987a0a60fc9"; :>> outcome = VerdictKind::pass; :>> judgedAgainst = "3bb8e77"; :>> judgedAt = "2026-08-27"; :>> judgedBy = "claudeOpus5"; }
    verification noGreenReviewGate : Test { :>> id = "f560658e-aa9b-4ece-85d2-f02d68f83bd1"; :>> title = "Sprint 476 review gate"; :>> createdAt = "2026-08-27"; :>> createdBy = "claudeOpus5"; :>> method = VerificationMethod::inspect; :>> procedureText = "Diff reviewed. D0241 records the criterion this does NOT satisfy: 'can a new command be added without the check' is still only enforced by a test that sweeps, not by construction - four root-resolution paths exist and a fifth could be added tomorrow. Saying so is the point, because the same sentence would have described root_arg an hour ago and I believed it was the chokepoint. Also NOT done and named: aggregation across the discovered project set, which is the better eventual answer and needs a declared cross-project order to be honest."; }
    part noGreenReviewGateR1 : TestResult { :>> id = "3b07e8f6-2649-4f7f-b187-846b33e67678"; :>> outcome = VerdictKind::pass; :>> judgedAgainst = "3bb8e77"; :>> judgedAt = "2026-08-27"; :>> judgedBy = "claudeOpus5"; }
    verification noGreenCloseOutGate : Test { :>> id = "2d2e489f-100e-4801-9d8c-19ddc16a086d"; :>> title = "Sprint 476 closeOut gate (autonomous, D0049)"; :>> createdAt = "2026-08-27"; :>> createdBy = "claudeOpus5"; :>> method = VerificationMethod::inspect; :>> procedureText = "Autonomous closeOut (D0049): the DoD is recorded pass with its RAN receipt; the frontier was read back from keel whats-next. Remaining from the panel: dcOneGateDefinition, dcPanelRecordCorrections and dcEveryAdvertisedViewIsBound. Self-evidencing (D0051): no human confirmation claimed."; }
    part noGreenCloseOutGateR1 : TestResult { :>> id = "54a61a66-71c8-4161-acf8-a27dd9bce237"; :>> outcome = VerdictKind::pass; :>> judgedAgainst = "3bb8e77"; :>> judgedAt = "2026-08-27"; :>> judgedBy = "claudeOpus5"; }
    verification noGreenRetroGate : Test { :>> id = "2e8dca70-330c-4666-86dd-770f81a6640c"; :>> title = "Sprint 476 retro gate (autonomous, D0049)"; :>> createdAt = "2026-08-27"; :>> createdBy = "claudeOpus5"; :>> method = VerificationMethod::analyze; :>> procedureText = "Autonomous retro (D0049). WELL: writing the sweep as a TEST rather than a shell loop found a defect the shell loop had already missed - indicators passed my manual sweep because the shell loop ran with cwd at the workspace root, where find_repo_root correctly failed, while the test ran with cwd inside keel's own repo, where it silently succeeded against the wrong project. The test was more honest than my sweep by accident of where it stood, which is a good argument for tests over sweeps generally. FINDING: I asserted a single chokepoint and was wrong by three - and the belief was reasonable, since root_arg has 41 of the roughly 45 call sites. 'Most commands go through X' is not 'all commands go through X', and the difference was two false greens and one confident wrong answer. AVOIDABLE-ISSUE SCAN: the issue269 refusal was written for validate and nothing recorded that it applied to ONE command, so it read as a property of the engine. A control's SCOPE is as much a fact as its existence, and neither the Decision nor the code said 'validate only'. Candidate forward control, stated not built: when a refusal or precondition is added, require the Decision to name the commands it covers, so the gap is visible in the record rather than discoverable only by sweeping. Estimate 3 pts held."; }
    part noGreenRetroGateR1 : TestResult { :>> id = "42ec7a24-5c3f-4230-a37d-f8ab642421e0"; :>> outcome = VerdictKind::pass; :>> judgedAgainst = "3bb8e77"; :>> judgedAt = "2026-08-27"; :>> judgedBy = "claudeOpus5"; }
}
