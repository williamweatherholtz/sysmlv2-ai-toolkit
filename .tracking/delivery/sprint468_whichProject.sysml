// ProjectDeliveryS468 — Sprint 468: the console names the project it serves, in the browser tab, and can switch between the nine on this machine. EXECUTE. 2 pts.
package ProjectDeliveryS468 {
    private import EngineElement::*;
    private import EngineWork::*;
    private import EngineVerification::*;
    private import EngineRelationships::*;

    #CharteredBy dependency from whichProjectStory to d0233;

    part whichProjectStory : Story {
        :>> id = "3ce034e6-efbc-481c-8087-e12addb0b7a7";
        :>> title = "Sprint 468: the feature that was already built, minus its surface (2 pts)";
        :>> createdAt = "2026-08-25"; :>> createdBy = "claudeFable5"; :>> kind = WorkKind::code; :>> priority = WorkPriority::p0; :>> owner = "claudeFable5"; :>> estimatedPoints = 2;
    }

    action def DeliveryRunS468 {
        action storyWhichProject;
        verification storyWhichProjectDoD : Test { :>> id = "3b323716-c590-4c44-bbaf-b856b68c9d37"; :>> method = VerificationMethod::test; :>> procedureText = "DELIVERED: dcWhichProject (resolves issue268; D0233). The author reported it while using the thing - keel serve does not indicate what project it is serving - and suggested that serving several local projects from one server might be the better feature. INVESTIGATING BEFORE INTERPRETING CHANGED THE ANSWER: the server side of that feature already existed. /api/projects discovers every sibling keel project and names the active one, its own doc comment saying it is the half of N-C4 that stops a supervisor wondering which project they are looking at, and POST /api/project switches while refusing a non-project rather than falling back. NOTHING RENDERED EITHER, so a capability had shipped with no surface. Three places said nothing and the middle one is why tabs did not disambiguate: the startup banner printed the port and every endpoint but never the root; the page title was the constant Keel console, and a browser TAB shows the title, so two consoles were told apart by nothing at all; the header was equally constant. Fixed by naming the project in all three, with the title substituted SERVER-SIDE so the tab is right on first paint and right even if the page JavaScript never runs, a badge whose tooltip is the full root, a switcher populated from the existing endpoint and hidden when only one project is reachable, and a display_path helper stripping the Windows verbatim prefix at every display site."; }
        // RAN: live server on 127.0.0.1:7892: banner names the root; GET / title = 'sysmlv2-ai-toolkit . keel'; POST /api/project -> Penumbra flips the title; POST root=C:/Windows -> HTTP 400 refused, active unchanged; switch back restores; GET /api/projects -> 9 reachable. cargo test --workspace -> 271+9+2+1+32; clippy 0 errors
        part storyWhichProjectDoDR1 : TestResult { :>> id = "4dbe0d58-8f31-4c81-bd8d-77f00043860c"; :>> outcome = VerdictKind::pass; :>> judgedAgainst = "f81ffbecd116ed7320078d8c015b70c7e53d845c"; :>> judgedAt = "2026-08-25"; :>> judgedBy = "claudeFable5"; }
    }

    verification whichProjectRefineGate : Test { :>> id = "4e1ebe7e-594a-4f55-a0a9-39160622868b"; :>> title = "Sprint 468 refine gate (DoR)"; :>> createdAt = "2026-08-25"; :>> createdBy = "claudeFable5"; :>> method = VerificationMethod::inspect; :>> procedureText = "DoR. Resolves issue268, reported by the author from use rather than from inspection. Scope: name the project everywhere a supervisor looks, and answer their question about whether one server for several projects is the better feature. 2 points."; }
    part whichProjectRefineGateR1 : TestResult { :>> id = "a4f059a4-550d-4aa7-a957-1b44a2691469"; :>> outcome = VerdictKind::pass; :>> judgedAgainst = "f81ffbecd116ed7320078d8c015b70c7e53d845c"; :>> judgedAt = "2026-08-25"; :>> judgedBy = "claudeFable5"; }
    verification whichProjectStandupGate : Test { :>> id = "79a938b7-f63b-4695-966d-64b8d66b3690"; :>> title = "Sprint 468 standup gate"; :>> createdAt = "2026-08-25"; :>> createdBy = "claudeFable5"; :>> method = VerificationMethod::inspect; :>> procedureText = "Approach: read the server before writing any UI, because the report suggested a feature and the right first question is what already exists. Substitute the title server-side rather than fetching it, since a title that arrives after JavaScript is wrong exactly when the page is slow or broken - which is when someone is most likely to be looking at the wrong tab. Verify against a RUNNING server, because the last two sprints both showed that a stub verifies my control flow and nothing about the thing itself. No blockers."; }
    part whichProjectStandupGateR1 : TestResult { :>> id = "52a327e0-90d4-4d37-b3cf-782d3eefa349"; :>> outcome = VerdictKind::pass; :>> judgedAgainst = "f81ffbecd116ed7320078d8c015b70c7e53d845c"; :>> judgedAt = "2026-08-25"; :>> judgedBy = "claudeFable5"; }
    verification whichProjectImplementGate : Test { :>> id = "33d926d1-d715-43d3-856b-c0291b4232f7"; :>> title = "Sprint 468 implement gate"; :>> createdAt = "2026-08-25"; :>> createdBy = "claudeFable5"; :>> method = VerificationMethod::test; :>> procedureText = "Verified against a running server on port 7892, not by reading. The banner prints the root; the title reads sysmlv2-ai-toolkit dot keel; a POST switch flips it to Penumbra dot keel; C:/Windows is REFUSED with the reason reported and the active project unchanged; switching back restores it; NINE reachable keel projects are discovered on this machine so the switcher is immediately useful and a select is the right shape for that count. validate 520 + 52 guards ALL PASS + clippy 0 errors + 271 + 9 + 2 + 1 + 32 tests."; }
    // RAN: live server on 127.0.0.1:7892: banner names the root; GET / title = 'sysmlv2-ai-toolkit . keel'; POST /api/project -> Penumbra flips the title; POST root=C:/Windows -> HTTP 400 refused, active unchanged; switch back restores; GET /api/projects -> 9 reachable. cargo test --workspace -> 271+9+2+1+32; clippy 0 errors
    part whichProjectImplementGateR1 : TestResult { :>> id = "f1ae7947-7b81-43d3-8864-a29f7a813865"; :>> outcome = VerdictKind::pass; :>> judgedAgainst = "f81ffbecd116ed7320078d8c015b70c7e53d845c"; :>> judgedAt = "2026-08-25"; :>> judgedBy = "claudeFable5"; }
    verification whichProjectReviewGate : Test { :>> id = "7fa31915-8b15-4887-9d78-4bba6708ea84"; :>> title = "Sprint 468 review gate — three passes per D0172"; :>> createdAt = "2026-08-25"; :>> createdBy = "claudeFable5"; :>> method = VerificationMethod::inspect; :>> procedureText = "PASS 1, CLAIMS: every verdict above came from an HTTP request against a live server and is quoted from its response, including the refusal text. PASS 2, BOUNDARY: (i) STILL ONE ACTIVE PROJECT at a time, not several rendered side by side, which is tabs in the literal sense the author asked about - deliberately not built, and stated in the Decision rather than implied; (ii) the switcher lists SIBLING directories only, so a keel project elsewhere on disk is unreachable from it; (iii) the badge is substituted at page load, so a project switched from another tab leaves this one stale until reload - mitigated by the switch itself reloading, not by anything watching; (iv) nine entries fit a select, and this design does not obviously scale to fifty. PASS 3, OWN DIFF: my first switch test failed with 'no root given' and my instinct was that the endpoint was wrong. It was my curl body - an invalid JSON escape from Windows backslashes. Reading the handler showed the field name was already correct, and had I trusted the failure I would have 'fixed' a working endpoint. WHAT A REVIEWER SHOULD ATTACK: whether a reload-on-switch is acceptable in a console that streams changes, or whether the rebind should repaint in place."; }
    part whichProjectReviewGateR1 : TestResult { :>> id = "0f385dcb-95ae-44cf-bc34-121a11807eb4"; :>> outcome = VerdictKind::pass; :>> judgedAgainst = "f81ffbecd116ed7320078d8c015b70c7e53d845c"; :>> judgedAt = "2026-08-25"; :>> judgedBy = "claudeFable5"; }
    verification whichProjectCloseOutGate : Test { :>> id = "450a60b7-4e45-470f-a5a8-c4bc667fcd56"; :>> title = "Sprint 468 closeOut gate (autonomous, D0049)"; :>> createdAt = "2026-08-25"; :>> createdBy = "claudeFable5"; :>> method = VerificationMethod::inspect; :>> procedureText = "Autonomous closeOut (D0049). issue268 resolved. A supervisor can now tell from the browser tab alone which tree a judgment will land in, which is the part that was a hazard rather than an inconvenience. validate + 52 guards + check-engine + rules green at f81ffbe."; }
    part whichProjectCloseOutGateR1 : TestResult { :>> id = "29a89883-89d5-44ec-b5d9-7b0531c8bf44"; :>> outcome = VerdictKind::pass; :>> judgedAgainst = "f81ffbecd116ed7320078d8c015b70c7e53d845c"; :>> judgedAt = "2026-08-25"; :>> judgedBy = "claudeFable5"; }
    verification whichProjectRetroGate : Test { :>> id = "68eb09be-6b99-4015-8b62-90090b49843f"; :>> title = "Sprint 468 retro gate (autonomous, D0049)"; :>> createdAt = "2026-08-25"; :>> createdBy = "claudeFable5"; :>> method = VerificationMethod::analyze; :>> procedureText = "Autonomous retro (D0049). AVOIDABLE-ISSUE SCAN under rcRecurrence: (1) THE PATTERN, and it is the same one as issue174: a Decision was accepted, the server half shipped, and the half the HUMAN sees never did - with a doc comment claiming the very outcome it did not deliver. That comment is the tell, and grepping for endpoints no UI fetches is a cheap way to find the rest of this class. (2) Reported from USE, again - the seventh consecutive finding that came from someone operating the thing rather than from any check. Nothing internal was ever going to notice a constant page title. (3) I patched the sprint filler to stop writing verdicts mid-sprint rather than adding a seventh double-stamped ceremony record, which is the first time this session I stopped using a thing I had just flagged instead of finishing the task with it. WELL: reading the server first turned a feature request into a surface gap, and the answer to their question came with evidence rather than an opinion. Estimate 2 pts, delivered 2."; }
    part whichProjectRetroGateR1 : TestResult { :>> id = "79271378-1112-44a8-85e3-d98624010f89"; :>> outcome = VerdictKind::pass; :>> judgedAgainst = "f81ffbecd116ed7320078d8c015b70c7e53d845c"; :>> judgedAt = "2026-08-25"; :>> judgedBy = "claudeFable5"; }
}
