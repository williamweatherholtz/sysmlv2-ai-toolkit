// ProjectDeliveryS658 — Sprint 658: Close dcCommitDeltaView (D0282): a computed #View, keel show commit-delta, over a git range - the Needs, Requirements, Decisions, Issues and tasks the range added, the items it retired by a #Supersede edge and the Issues it resolved, each with its type and title, reconciled against the diff's added declarations by count, empty when the range changed no item - and carry it to the surface where the human's authority lives: the published decision brief, through the commitDelta fact in scripts/exec_brief/facts.py over publishedAgainst..HEAD. The item's second surface, the decision-channel comment, is moot since D0291 disconnected the channel; the DoD is narrowed to say so before the pass. The sprint also carries the root fix for the land refusal that ended sprint 657: guard durations become a value run_all_timed returns rather than a process-global static.. EXECUTE. 3 pts.
package ProjectDeliveryS658 {
    private import EngineElement::*;
    private import EngineWork::*;
    private import EngineVerification::*;
    private import EngineRelationships::*;

    #CharteredBy dependency from commitDeltaViewStory to d0282;

    part commitDeltaViewStory : Story {
        :>> id = "4381bd0b-a400-4fd1-abfa-be9a2dfb75fe";
        :>> title = "Sprint 658: Close dcCommitDeltaView (D0282): a computed #View, keel show commit-delta, over a git range - the Needs, Requirements, Decisions, Issues and tasks the range added, the items it retired by a #Supersede edge and the Issues it resolved, each with its type and title, reconciled against the diff's added declarations by count, empty when the range changed no item - and carry it to the surface where the human's authority lives: the published decision brief, through the commitDelta fact in scripts/exec_brief/facts.py over publishedAgainst..HEAD. The item's second surface, the decision-channel comment, is moot since D0291 disconnected the channel; the DoD is narrowed to say so before the pass. The sprint also carries the root fix for the land refusal that ended sprint 657: guard durations become a value run_all_timed returns rather than a process-global static. (3 pts)";
        :>> createdAt = "2026-09-10"; :>> createdBy = "claudeOpus5"; :>> kind = WorkKind::code; :>> priority = WorkPriority::p0; :>> owner = "claudeOpus5"; :>> estimatedPoints = 3;
    }

    action def DeliveryRunS658 {
        action storyCommitDeltaView;
        verification storyCommitDeltaViewDoD : Test { :>> id = "b7125243-abd4-450e-8663-e2d6e24abbd6"; :>> method = VerificationMethod::test; :>> procedureText = "The DoD of dcCommitDeltaView as narrowed (owner edit, D0291 cited): keel show commit-delta . --range a430c387..HEAD names D0431, issue458 and the sprint 657 story - Decision 1, Issue 1, action 1 - and reconciliation matches; over 29fb76c..HEAD (the last published tree) 138 items, 30 Decisions, 37 Issues, 2 Needs, 4 SystemRequirements, 65 tasks, 37 resolutions, reconciled after three counter defects the live run exposed (a #Marker before part, a moved declaration counted as added, a typed action counted as a task); HEAD..HEAD renders empty = true with every list empty; an unknown ref exits 1 naming it and a bare --range exits 2 with usage. facts.py emits commitDelta, commitDeltaAdded, commitDeltaSuperseded, commitDeltaResolved with complete = true, each how naming the command. The three delta unit tests pass; cli-surface-declared holds the three homes equal (109 CliFacts, 39 lenses, commands.sysml); the decision-surfacing skill's step 3 names the section in both renderings and sync-claude --check is clean. VERIFY as the verifier reports: cargo test --release -p keel-cli --lib FULL set (the gate's run, not a filter) 473 passed 0 failed; clippy -D warnings clean; keel validate, check-engine, guard --no-receipt green; run_all_timed_names_every_guard_that_ran holds in the full run where its predecessor failed."; }
        // RAN: verifier receipt 2026-09-10T17:46:45Z: keel show commit-delta a430c387..HEAD names every new Decision, Issue and task with reconciliation matches true; HEAD..HEAD empty true; facts.py commitDelta over 29fb76c..HEAD 138 added 0 retired 37 resolved reconciled true, complete true; keel suite --touched 548 passed 0 failed; clippy clean; validate 749; guard 69 PASS
        part storyCommitDeltaViewDoDR1 : TestResult { :>> id = "17ac8b0e-aacd-4472-9f57-becf983c414b"; :>> outcome = VerdictKind::pass; :>> judgedAgainst = "0e84415a2e0ba806474070f2a10839718c673ae3"; :>> judgedAt = "2026-09-10T17:46:45Z"; :>> judgedBy = "claudeOpus5"; }
    }

    verification commitDeltaViewRefineGate : Test { :>> id = "fb1528e9-2137-43e8-9a16-4500b504b213"; :>> title = "Sprint 658 refine gate (DoR)"; :>> createdAt = "2026-09-10"; :>> createdBy = "claudeOpus5"; :>> method = VerificationMethod::inspect; :>> procedureText = "Three points: a new view module with three pure tests, six wiring sites held equal by a guard, a facts.py section, a skill section in two renderings, a DoD narrowing, and a Decision. Ready: dcCommitDeltaView is head of whats-next after dcGuardPoolDispatchesLongestFirst closed; its charter D0282 is accepted; model_at_commit already builds a model from a commit in a worktree, so the view is a pure comparison of two models plus a git diff count. Known before the tree was read: the reconciliation's positive case is a range that adds a Decision file (counted once) and its negative case is a range that adds none (empty)."; }
    // RAN: verifier receipt 2026-09-10T17:46:45Z (D0425): whats-next head dcCommitDeltaView; charter D0282 accepted; advance reads step Refine, no prior steps passed; validate 749 clean
    part commitDeltaViewRefineGateR1 : TestResult { :>> id = "e9f5d1cc-f53e-4eea-900b-ae5567a14224"; :>> outcome = VerdictKind::pass; :>> judgedAgainst = "0e84415a2e0ba806474070f2a10839718c673ae3"; :>> judgedAt = "2026-09-10T17:46:45Z"; :>> judgedBy = "claudeOpus5"; }
    verification commitDeltaViewStandupGate : Test { :>> id = "7eb568fd-6c5a-4d0b-80d4-f51439c6b26d"; :>> title = "Sprint 658 standup gate"; :>> createdAt = "2026-09-10"; :>> createdBy = "claudeOpus5"; :>> method = VerificationMethod::inspect; :>> procedureText = "Blocker at the start: the previous sprint's commit 0e84415 is local only - the land refused its push because last_durations_names_every_guard_that_ran failed in the full lib run while passing in the verifier's six-test filter. Diagnosed to the DURATIONS static (process-global, cleared per run, interleaved by concurrent run_all in cargo test); fixed at the root in this sprint rather than by serialising the test. The scope defect behind it - the verifier ran a set the primary chose - is issue459, resolved by D0432 (proposed, process-change: the verifier runs keel suite --touched, the gate's own set). No other blocker."; }
    // RAN: verifier receipt 2026-09-10T17:46:45Z: git rev-parse HEAD 0e84415 ahead of origin/main by one (the refused push of sprint 657); keel suite --touched stems guards,receipt outcome pass 548 passed 0 failed - the failure that refused the land is gone from the gate's own run; D0432 status proposed
    part commitDeltaViewStandupGateR1 : TestResult { :>> id = "be071af7-6544-4d81-8fb6-f4ffd7423d07"; :>> outcome = VerdictKind::pass; :>> judgedAgainst = "0e84415a2e0ba806474070f2a10839718c673ae3"; :>> judgedAt = "2026-09-10T17:46:45Z"; :>> judgedBy = "claudeOpus5"; }
    verification commitDeltaViewImplementGate : Test { :>> id = "15706fdb-e412-49ed-aca8-3358afa450dc"; :>> title = "Sprint 658 implement gate"; :>> createdAt = "2026-09-10"; :>> createdBy = "claudeOpus5"; :>> method = VerificationMethod::test; :>> procedureText = "Built: keel-cli/src/view/delta.rs - DELTA_TYPES, DeltaItem, Delta (is_empty, added_by_type), delta(from, to) over two models (added = present at to and absent at from; superseded = new supersede edges; resolved = new resolves edges whose target is an Issue), diff_added_counts over git diff with leading #Marker tokens skipped, names both removed and added treated as a move, action x : Type typed as Type, definitions excluded, parse_range (bare ref means ref~1..ref), commit_delta emitting range, empty, added, superseded, resolved, reconciliation {viewAdded, gitDiffAdded, matches, how}, how. Wired: cliCommitDelta in .engine/cli/commands.sysml, CLI_FACTS 109, LENS_NAMES 39, cmd_commit_delta in main.rs with both Lenses help lines. Live run over a430c387..HEAD first read matches = false: the diff counted no Decision (#ProspectiveChange part d0431) and two actions (a moved line); over 29fb76c..HEAD one more action (action stpa2bCensus : ProcessStep) - each fixed in the counter with its case added to diff_counts_added_declarations_by_delta_type, and both ranges now reconcile. facts.py section 17 emits commitDelta over publishedAgainst..HEAD (29fb76c: 138 added, 0 retired, 37 resolved, reconciled true). decision-surfacing SKILL.md step 3 gains the what-this-range-changed section rule in .claude and .engine. CLAUDE.md section 2 lists the lens; section 4's D0425 rule names keel suite --touched (D0432, proposed). Root fix carried: guards.rs DURATIONS static and last_durations removed, run_in_parallel returns the run's Durations, run_all_timed(root) -> (reports, durations) with run_all = .0, record_green takes durations, callers in main.rs (hook stop, guard) and workspace.rs updated, six receipt tests pass &[]. dcCommitDeltaView's DoD narrowed (channel comment -> facts.py, D0291). issue459 (verifier scope, in-field, resolver D0432) and issue460 (a marker-less draft whose text said process-change auto-accepted; observed on D0432's first recording, file deleted and re-recorded with the marker; resolver dcMarkerTextWithoutMarkerHolds, a new EngineBuild task) recorded."; }
    // RAN: verifier receipt 2026-09-10T17:46:45Z: keel suite --touched . PASS 548 passed 0 failed 454s (lib unit tests + 20 integration tests, receipt head 0e84415); cargo clippy --release -p keel-cli --all-targets -D warnings clean; keel validate 749 clean; check-engine clean; guard --no-receipt 69 PASS 0 FAIL; gate --fast clean; show commit-delta a430c387..HEAD names d0431 Decision, issue458 Issue, storyGuardPoolDispatchesLongestFirst action, resolved issue458 by d0431, reconciliation matches true; HEAD..HEAD empty true; unknown ref exit 1, bare --range exit 2; facts.py exit 0 complete true commitDeltaAdded 138 commitDeltaSuperseded 0 commitDeltaResolved 37 range 29fb76c..HEAD reconciled true; sync-claude --check clean
    part commitDeltaViewImplementGateR1 : TestResult { :>> id = "b2a01709-0457-4255-b97c-b444af697fc5"; :>> outcome = VerdictKind::pass; :>> judgedAgainst = "0e84415a2e0ba806474070f2a10839718c673ae3"; :>> judgedAt = "2026-09-10T17:46:45Z"; :>> judgedBy = "claudeOpus5"; }
    verification commitDeltaViewReviewGate : Test { :>> id = "df82cbfa-b5e8-40fe-8eec-e3d805228a98"; :>> title = "Sprint 658 review gate — three passes per D0172"; :>> createdAt = "2026-09-10"; :>> createdBy = "claudeOpus5"; :>> method = VerificationMethod::inspect; :>> procedureText = "Three passes (D0172). Substance: the view answers the landscape finding it was chartered for - a reader gets the spec of a range before its hunks - and its reconciliation is not decoration: on its first two live runs it found three defects in its own counter, each of which would otherwise have been a silent undercount; that is the D0388 shape working as designed, with the cases now in the test. The D0291 narrowing is an owner's edit before the pass, cited in the DoD text and in the module doc, not a quiet drop. Record: the two Issues this sprint are both in-field and both about the recording process itself - a verifier set narrower than the gate's, and a Decision that accepted itself because a header was missing - and each has a resolver that is a control, not a reminder (D0432's named command; dcMarkerTextWithoutMarkerHolds's classifier shared by write path and guard). Stated plainly: D0432 was first recorded WITHOUT its marker and landed accepted for about a minute in the working tree; the correction was possible only because nothing had been committed. Not delivered by design: no channel comment (D0291), no stored view, no brief republish (the pending set is unchanged and D0407 is still proposed)."; }
    // RAN: verifier receipt 2026-09-10T17:46:45Z: three-pass review recorded in the sprint's review section; DISCREPANCIES none between the primary's claims and the commands' returns; issue459 and issue460 present and triaged in .tracking/issues-claudeOpus5.sysml; dcMarkerTextWithoutMarkerHolds present in backlog
    part commitDeltaViewReviewGateR1 : TestResult { :>> id = "320d2dc4-18af-404e-be39-7a7519537f0f"; :>> outcome = VerdictKind::pass; :>> judgedAgainst = "0e84415a2e0ba806474070f2a10839718c673ae3"; :>> judgedAt = "2026-09-10T17:46:45Z"; :>> judgedBy = "claudeOpus5"; }
    verification commitDeltaViewCloseOutGate : Test { :>> id = "b4aec136-6e32-49eb-9ca2-c2fad9a577eb"; :>> title = "Sprint 658 closeOut gate (autonomous, D0049)"; :>> createdAt = "2026-09-10"; :>> createdBy = "claudeOpus5"; :>> method = VerificationMethod::inspect; :>> procedureText = "Delivered: keel show commit-delta (view/delta.rs, three tests, six wiring sites), facts.py commitDelta over the last published tree, the decision-surfacing section rule, CLAUDE.md sections 2 and 4, run_all_timed and the receipt's per-guard ms from the run's own value, dcCommitDeltaView's DoD narrowed and passed, D0432 (proposed), issue459 and issue460 (in-field, triaged), dcMarkerTextWithoutMarkerHolds added to EngineBuild. Not delivered: dcMarkerTextWithoutMarkerHolds itself - added, not built; the brief's section - the skill names it, the next publish renders it."; }
    // RAN: verifier receipt 2026-09-10T17:46:45Z: every gate above passes on the same receipt; delivered set named in closeOut; keel guard 69 PASS
    part commitDeltaViewCloseOutGateR1 : TestResult { :>> id = "294146f0-845d-448f-8629-f36fc285e09a"; :>> outcome = VerdictKind::pass; :>> judgedAgainst = "0e84415a2e0ba806474070f2a10839718c673ae3"; :>> judgedAt = "2026-09-10T17:46:45Z"; :>> judgedBy = "claudeOpus5"; }
    verification commitDeltaViewRetroGate : Test { :>> id = "8720d259-1c49-4156-b49c-12396c480d57"; :>> title = "Sprint 658 retro gate (autonomous, D0049)"; :>> createdAt = "2026-09-10"; :>> createdBy = "claudeOpus5"; :>> method = VerificationMethod::analyze; :>> procedureText = "Autonomous retro (D0049). AVOIDABLE-ISSUE SCAN: two Issues this sprint, both avoidable. issue459: the verifier's test set was a filter the primary chose - the D0425 text said touched binaries and left the choice to the party whose belief the verifier exists to check; control is D0432's named command (the same set the land runs), and the residual is that the land remains the backstop for a verifier that is not run. issue460: a Decision that said in words it was a process change auto-accepted because the marker header was missing; recurrence of the issue346 class (the marker is the only thing the write path reads) from the other side; control is dcMarkerTextWithoutMarkerHolds - the text classifier the write path and the consent-scope guard share. Finding 3, a pattern across 655, 657 and now 658: a first live run of a new instrument disagrees with its own reconciliation, and the disagreement is a counter defect rather than a model fact - three times here in one sprint; the reconciliation field is doing its job, and the lesson is that a view that reconciles is worth the extra count. Finding 4, hygiene held: no heredoc carried a backslash after the first denial; every patch went through textpatch with an anchor."; }
    // RAN: verifier receipt 2026-09-10T17:46:45Z: retro recorded (D0049) with two avoidable Issues each carrying a resolver (D0432, dcMarkerTextWithoutMarkerHolds); validate 749 clean
    part commitDeltaViewRetroGateR1 : TestResult { :>> id = "125a511f-1ef1-48b2-8e22-4d27fa45aff9"; :>> outcome = VerdictKind::pass; :>> judgedAgainst = "0e84415a2e0ba806474070f2a10839718c673ae3"; :>> judgedAt = "2026-09-10T17:46:45Z"; :>> judgedBy = "claudeOpus5"; }
}
