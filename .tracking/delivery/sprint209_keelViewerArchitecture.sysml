// ProjectDeliveryS209 — Sprint 209: keelViewerArchitecture — Architecture phase for the keel-viewer,
// after the human accepted the Needs + chose shape B. Records D0114 (architecture = B), derives 6
// SystemRequirements (satisfy-linked to the accepted Needs), and creates the keel-side implementation
// backlog (6 actions). Completes the end-to-end business-architecture skill run -> CLOSES issue061
// (proveProcessDeployment: Brief->Needs->accepted->architecture Decisions, all authored). EXECUTE. 2 pt.
package ProjectDeliveryS209 {
    private import EngineElement::*;
    private import EngineWork::*;
    private import EngineVerification::*;
    private import EngineRequirements::*;
    private import EngineRelationships::*;

    #CharteredBy dependency from keelViewerArchStory to d0114;

    part keelViewerArchStory : Story {
        :>> id = "63940516-2c7d-4e8f-c209-51627384c001";
        :>> title = "Sprint 209: keelViewerArchitecture (2 pt) - D0114 (shape B) + 6 SystemRequirements + implementation backlog; closes issue061";
        :>> createdAt = "2026-07-14"; :>> createdBy = "wweatherholtz"; :>> kind = WorkKind::code; :>> priority = WorkPriority::p2; :>> owner = "claudeOpus"; :>> estimatedPoints = 2;
    }

    action def DeliveryRunS209 {
        action storyKeelViewerArchitecture;
        verification storyKeelViewerArchitectureDoD : Test { :>> id = "63940516-2c7d-4e8f-c209-51627384c002"; :>> method = VerificationMethod::inspect; :>> procedureText = "Architecture phase of the business-architecture skill run on the keel-viewer, AFTER the human-accepted Needs gate (keelViewerNeedsAcceptR1) + the A/B/C choice. AUTHORED (needs-before-architecture, tracked facts): (1) keelViewerNeedsAccept gate recorded (human-judged); (2) D0114 — architecture = SHAPE B (separate viewer over a committed, versioned keel read/query/graph/temporal API), accepted (human-judged d0114Accept), #DerivedFrom nViewerSeparation; (3) 6 SystemRequirements (keel-viewer-requirements.sysml: srViewerKeelApi/TemporalState/GraphExpand/VisualViewpoint/ConfigurableSlice [must] + srViewerDatePredicates [should]) with measurable thresholds, satisfy-linked to the accepted Needs; (4) 6 keel-side implementation backlog actions (viewerKeelApi/TemporalState/GraphExpand/VisualViewpoint/ConfigurableSlice/DatePredicates) with DoDs. The viewer app itself is a SEPARATE project (shape B). This completes the END-TO-END skill run (Brief->Needs->accepted->architecture Decisions, all authored, not chat) -> proveProcessDeployment part 1 done; part 2 (researchSpikeCharterRule) was Sprint 200 -> issue061 CLOSED. 6 open questions (Q2-Q6) captured as SR/DoD TBDs, not blockers. VERIFY: keel validate clean (226); guard all + check-engine green; the architecture is authored items (Decision/SRs/satisfy edges/backlog), not a prose doc; issue061 resolves (open issues -> 0)."; }
        part storyKeelViewerArchitectureDoDR1 : TestResult { :>> id = "63940516-2c7d-4e8f-c209-51627384c003"; :>> outcome = VerdictKind::pass; :>> judgedAgainst = "5f82eec"; :>> judgedAt = "2026-07-14"; :>> judgedBy = "claudeOpus"; }
    }

    verification kvaRefineGate : Test { :>> id = "63940516-2c7d-4e8f-c209-51627384c004"; :>> title = "Sprint 209 refine gate (DoR)"; :>> createdAt = "2026-07-14"; :>> createdBy = "claudeOpus"; :>> method = VerificationMethod::inspect; :>> procedureText = "DoR: Needs accepted (keelViewerNeedsAcceptR1) + shape B chosen -> the Business gate is passed, architecture may be recorded. Derive SRs + Decision from the accepted Needs. estimatedPoints=2. #CharteredBy d0114. DoR met."; }
    part kvaRefineGateR1 : TestResult { :>> id = "63940516-2c7d-4e8f-c209-51627384c005"; :>> outcome = VerdictKind::pass; :>> judgedAgainst = "5f82eec"; :>> judgedAt = "2026-07-14"; :>> judgedBy = "claudeOpus"; }
    verification kvaStandupGate : Test { :>> id = "63940516-2c7d-4e8f-c209-51627384c006"; :>> title = "Sprint 209 standup gate"; :>> createdAt = "2026-07-14"; :>> createdBy = "claudeOpus"; :>> method = VerificationMethod::inspect; :>> procedureText = "Approach: record the acceptance gate + D0114 (B); author 6 measurable SRs satisfy-linked to the Needs; create 6 keel-side backlog actions; close issue061. No blockers."; }
    part kvaStandupGateR1 : TestResult { :>> id = "63940516-2c7d-4e8f-c209-51627384c007"; :>> outcome = VerdictKind::pass; :>> judgedAgainst = "5f82eec"; :>> judgedAt = "2026-07-14"; :>> judgedBy = "claudeOpus"; }
    verification kvaImplementGate : Test { :>> id = "63940516-2c7d-4e8f-c209-51627384c008"; :>> title = "Sprint 209 implement gate"; :>> createdAt = "2026-07-14"; :>> createdBy = "claudeOpus"; :>> method = VerificationMethod::inspect; :>> procedureText = "D0114 + 6 SRs + satisfy edges + 6 backlog actions authored; issue061 closed (open issues -> 0). keel validate clean (226); guard all + check-engine green. Architecture is authored items, not prose."; }
    part kvaImplementGateR1 : TestResult { :>> id = "63940516-2c7d-4e8f-c209-51627384c009"; :>> outcome = VerdictKind::pass; :>> judgedAgainst = "5f82eec"; :>> judgedAt = "2026-07-14"; :>> judgedBy = "claudeOpus"; }
    verification kvaReviewGate : Test { :>> id = "63940516-2c7d-4e8f-c209-51627384c00a"; :>> title = "Sprint 209 review gate"; :>> createdAt = "2026-07-14"; :>> createdBy = "claudeOpus"; :>> method = VerificationMethod::inspect; :>> procedureText = "Reviewed. Architecture recorded the disciplined way: needs-before-architecture strictly held (Decision + SRs recorded only AFTER the human accepted the Needs + chose B); the Decision is #DerivedFrom the Need it serves; SRs are measurable + satisfy-linked; the genuinely-open questions (Q2-Q6) are captured as TBDs, not fabricated. The end-to-end skill run on a REAL external brief closed issue061 — the exact thing that issue proved was needed. Honest: the SRs are unverified (implementation not started) — that's true state, shown in tier-satisfaction. Clean."; }
    part kvaReviewGateR1 : TestResult { :>> id = "63940516-2c7d-4e8f-c209-51627384c00b"; :>> outcome = VerdictKind::pass; :>> judgedAgainst = "5f82eec"; :>> judgedAt = "2026-07-14"; :>> judgedBy = "claudeOpus"; }
    verification kvaCloseOutGate : Test { :>> id = "63940516-2c7d-4e8f-c209-51627384c00c"; :>> title = "Sprint 209 closeOut gate (autonomous, D0049)"; :>> createdAt = "2026-07-14"; :>> createdBy = "claudeOpus"; :>> method = VerificationMethod::inspect; :>> procedureText = "Autonomous closeOut (D0049): DoD pass; keel-viewer architecture (D0114 + 6 SRs + backlog) authored; issue061 CLOSED (open issues -> 0). keel validate + guard + check-engine green. Self-evidencing (D0051). NEXT: the implementation backlog (viewerKeelApi first — the enabling versioned API for shape B) + the open questions Q2-Q6, each when the human prioritises; the viewer app is a separate project."; }
    part kvaCloseOutGateR1 : TestResult { :>> id = "63940516-2c7d-4e8f-c209-51627384c00d"; :>> outcome = VerdictKind::pass; :>> judgedAgainst = "5f82eec"; :>> judgedAt = "2026-07-14"; :>> judgedBy = "claudeOpus"; }
    verification kvaRetroGate : Test { :>> id = "63940516-2c7d-4e8f-c209-51627384c00e"; :>> title = "Sprint 209 retro gate (autonomous, D0049)"; :>> createdAt = "2026-07-14"; :>> createdBy = "claudeOpus"; :>> method = VerificationMethod::analyze; :>> procedureText = "Autonomous retro (D0049). WELL: a real external design brief went end-to-end through the business-architecture skill — Brief, accepted Needs, an accepted architecture Decision (B), measurable SRs, and a real implementation backlog — all as authored facts, and it CLOSED issue061 (the very issue that existed to prove the skill works on a genuine task). Open issues hit 0. The human's two decisions (accept Needs, choose B) were the only gates, correctly held. AVOIDABLE-ISSUE SCAN: one enum typo (demonstration->demo) caught by validate before commit — the validator did its job. LESSON: the design workflow is now proven end-to-end on real work, not just the engine's own dogfood. Estimate 2 pt held. NEXT: implementation (viewerKeelApi) + Q2-Q6 as prioritised."; }
    part kvaRetroGateR1 : TestResult { :>> id = "63940516-2c7d-4e8f-c209-51627384c00f"; :>> outcome = VerdictKind::pass; :>> judgedAgainst = "5f82eec"; :>> judgedAt = "2026-07-14"; :>> judgedBy = "claudeOpus"; }
}
