// ProjectDeliveryS616 — Sprint 616: Sprint 616 takes the hooks off the build tree (dcSelfBuildHooksLeaveTheBuildTree, resolves issue408) under D0391: on a self-build tree the hooks run a stable copy at .keel/bin that they refresh from target/release themselves, sync-claude places it and says which binary the hooks will run, and status names the copy's build beside HEAD so the lag it trades for is a fact.. EXECUTE. 3 pts.
package ProjectDeliveryS616 {
    private import EngineElement::*;
    private import EngineWork::*;
    private import EngineVerification::*;
    private import EngineRelationships::*;

    #CharteredBy dependency from selfBuildHooksRunAStableCopyStory to d0391;

    part selfBuildHooksRunAStableCopyStory : Story {
        :>> id = "7d98a69c-f287-4281-9f6d-19f96f0edf30";
        :>> title = "Sprint 616: Sprint 616 takes the hooks off the build tree (dcSelfBuildHooksLeaveTheBuildTree, resolves issue408) under D0391: on a self-build tree the hooks run a stable copy at .keel/bin that they refresh from target/release themselves, sync-claude places it and says which binary the hooks will run, and status names the copy's build beside HEAD so the lag it trades for is a fact. (3 pts)";
        :>> createdAt = "2026-09-08"; :>> createdBy = "claudeOpus5"; :>> kind = WorkKind::code; :>> priority = WorkPriority::p0; :>> owner = "claudeOpus5"; :>> estimatedPoints = 3;
    }

    action def DeliveryRunS616 {
        action storySelfBuildHooksRunAStableCopy;
        verification storySelfBuildHooksRunAStableCopyDoD : Test { :>> id = "61472100-88f8-4b5b-b1d3-e7878b6a7417"; :>> method = VerificationMethod::test; :>> procedureText = "DONE MEANS: a self-build project's hooks do not run the file its build is writing. Resolves issue408. The pin probe's order is KEEL_BIN, then .keel/bin/keel(.exe), then the pin cache, then PATH. In a project whose DELIVERABLE is the engine, nothing writes .keel/bin/keel.exe - init seeds .keel/bin/<version>/<asset> and keelw fetches into the same shape - so the probe falls through to PATH and resolves into target/release, which is the exact file cargo must unlink to relink. DO: on a self-build tree, the surfaces that write hook commands ALSO place or refresh a stable copy at .keel/bin/keel(.exe), and say which binary the hooks will run; and the copy is refreshed by the build path that produces a new binary rather than by a human remembering. The staleness this trades for is real and must be visible, not silent: keel status names the hook binary's build commit beside the engine pin, so a hook set running an older image than the tree is a fact a reader can see rather than an inference from behaviour. VERIFY: on this repository, a cargo build followed by a suite run completes with no `failed to remove file target/release/keel.exe`; the fire-ledger's bin field names the stable copy, not target/release; keel status shows the hook binary's build and flags it when it differs from the tree's HEAD; a non-self-build project is unaffected."; }
        // RAN: hook_binary.rs + wiring; 2 unit + 5 integration tests pass; this repository bootstrapped through sync-claude, ledger shows the stable copy at build cafde85+dirty; D0391
        part storySelfBuildHooksRunAStableCopyDoDR1 : TestResult { :>> id = "2bd2cde3-d053-4c30-b516-aabceafe3e0e"; :>> outcome = VerdictKind::pass; :>> judgedAgainst = "cafde85c5a8d0e08120d41ad7e5412eacc969ad7"; :>> judgedAt = "2026-09-08"; :>> judgedBy = "claudeOpus5"; }
    }

    verification selfBuildHooksRunAStableCopyRefineGate : Test { :>> id = "5816a941-a290-4cff-9975-0cf1d1062314"; :>> title = "Sprint 616 refine gate (DoR)"; :>> createdAt = "2026-09-08"; :>> createdBy = "claudeOpus5"; :>> method = VerificationMethod::inspect; :>> procedureText = "Scope: keel-cli/src/hook_binary.rs (stable_copy, build_output, Stamp, needs_refresh, refresh, describe; unit tests); main.rs hook entry (refresh before dispatch, hook-binary-refreshed ledger event) and sync-claude's report; status.rs hooks section (describe, Attention when a self-build has no copy, the lag line); keel-cli/tests/self_build_hooks_leave_the_build_tree.rs; D0391. Out of scope: the pin probe order, init's seeding and keelw, all unchanged; a build id in the stamp (reading one means running the binary at every fire). Estimate 3 points: a module, three call sites, five integration tests. DoR: points set, charter d0391, scope clear, no blocking dependency, DoD authored."; }
    // RAN: DoR inspected: 3 points, charter d0391, scope in the refine text, DoD authored, no blocking dependency
    part selfBuildHooksRunAStableCopyRefineGateR1 : TestResult { :>> id = "9ffe4942-d210-41bb-993f-a02d9da4ed91"; :>> outcome = VerdictKind::pass; :>> judgedAgainst = "cafde85c5a8d0e08120d41ad7e5412eacc969ad7"; :>> judgedAt = "2026-09-08"; :>> judgedBy = "claudeOpus5"; }
    verification selfBuildHooksRunAStableCopyStandupGate : Test { :>> id = "c6f8a5d8-ef79-4a30-b74e-7ded207c97b5"; :>> title = "Sprint 616 standup gate"; :>> createdAt = "2026-09-08"; :>> createdBy = "claudeOpus5"; :>> method = VerificationMethod::inspect; :>> procedureText = "Plan: (1) hook_binary.rs with a pure refresh decision (output exists, two seconds old, differs from the stamp) and a copy-through-.next-then-rename that works on a running image; (2) the hook entry refreshes before dispatch and writes hook-binary-refreshed; (3) sync-claude places the copy when absent and prints which binary the hooks will run; (4) status prints the same, marks Attention with no copy, and names the commits the last fire's build sits behind HEAD; (5) integration tests on a constructed self-build tree: placed on first fire and recorded, refreshed on a new output, a young output left alone, a plain project untouched, sync-claude places and names; (6) bootstrap this repository through sync-claude and read the ledger's bin and build; gates."; }
    // RAN: plan of six steps recorded in the standup text; all six executed in this commit
    part selfBuildHooksRunAStableCopyStandupGateR1 : TestResult { :>> id = "2cfc2114-0983-457e-a770-e4cb3987d1fd"; :>> outcome = VerdictKind::pass; :>> judgedAgainst = "cafde85c5a8d0e08120d41ad7e5412eacc969ad7"; :>> judgedAt = "2026-09-08"; :>> judgedBy = "claudeOpus5"; }
    verification selfBuildHooksRunAStableCopyImplementGate : Test { :>> id = "6a950ea3-2185-4a97-9c0e-3e673a14155c"; :>> title = "Sprint 616 implement gate"; :>> createdAt = "2026-09-08"; :>> createdBy = "claudeOpus5"; :>> method = VerificationMethod::test; :>> procedureText = "RAN: cargo build --release; cargo clippy --release --all-targets -D warnings; cargo test --release --lib hook_binary; cargo test --release --test self_build_hooks_leave_the_build_tree; keel sync-claude . on this repository; keel status . read back; tail of .keel/metrics/hooks.jsonl; keel gate --fast; keel guard."; }
    // RAN: cargo build --release clean; cargo clippy --release --all-targets -D warnings exit 0; cargo test --release --lib hook_binary 2 passed; cargo test --release --test self_build_hooks_leave_the_build_tree 5 passed 0 failed; keel sync-claude . printed 'hook binary: placed .keel/bin/keel.exe from target/release/keel.exe' then the describe line; keel status . hooks OK with the hook-binary line; hooks.jsonl last fire bin=.keel/bin/keel.exe build cafde85+dirty (was 7a61044+dirty hand copy before); keel gate --fast clean
    part selfBuildHooksRunAStableCopyImplementGateR1 : TestResult { :>> id = "8fb538c0-6750-4bfd-8d08-6a4e2acf0dd1"; :>> outcome = VerdictKind::pass; :>> judgedAgainst = "cafde85c5a8d0e08120d41ad7e5412eacc969ad7"; :>> judgedAt = "2026-09-08"; :>> judgedBy = "claudeOpus5"; }
    verification selfBuildHooksRunAStableCopyReviewGate : Test { :>> id = "452ac4bf-e40f-4b13-804c-ad4b2d325d64"; :>> title = "Sprint 616 review gate — three passes per D0172"; :>> createdAt = "2026-09-08"; :>> createdBy = "claudeOpus5"; :>> method = VerificationMethod::inspect; :>> procedureText = "Reviewed against the DoD: this repository's cargo build followed by the full suite completed today with 601 passed and no remove-file error (suite-1788908104.log) while the hooks ran the stable copy; the ledger's bin names .keel/bin/keel.exe; status shows the hook binary's build and, when it differs from HEAD, the commit count behind; a project without keel-cli/Cargo.toml is untouched (test); the copy is refreshed by the first hook fire after a build, not by anyone remembering (test)."; }
    // RAN: reviewed against the DoD clause by clause: build + full suite today 601 passed with no remove-file error while hooks ran the stable copy; ledger bin names .keel/bin/keel.exe; status shows build and the behind-HEAD count when they differ; non-self-build untouched (test); refresh rides the hook fire after a build (test)
    part selfBuildHooksRunAStableCopyReviewGateR1 : TestResult { :>> id = "fe64ae6a-bb67-41a9-af8a-e0bec035629d"; :>> outcome = VerdictKind::pass; :>> judgedAgainst = "cafde85c5a8d0e08120d41ad7e5412eacc969ad7"; :>> judgedAt = "2026-09-08"; :>> judgedBy = "claudeOpus5"; }
    verification selfBuildHooksRunAStableCopyCloseOutGate : Test { :>> id = "6e7f26ba-a89f-4b8f-96ba-225a9c648ff9"; :>> title = "Sprint 616 closeOut gate (autonomous, D0049)"; :>> createdAt = "2026-09-08"; :>> createdBy = "claudeOpus5"; :>> method = VerificationMethod::inspect; :>> procedureText = "Sprint 616 closes when dcSelfBuildHooksLeaveTheBuildTreeDoD carries a pass at the commit that carries the module, the wiring, the tests and the Decision, and issue408 leaves keel show open-issues."; }
    // RAN: DoD pass recorded on storySelfBuildHooksRunAStableCopyDoD and dcSelfBuildHooksLeaveTheBuildTreeDoD at this SHA; issue408 resolution read back from keel show open-issues after the record
    part selfBuildHooksRunAStableCopyCloseOutGateR1 : TestResult { :>> id = "f1fe4186-8ccc-43a1-8e0e-b264420cd569"; :>> outcome = VerdictKind::pass; :>> judgedAgainst = "cafde85c5a8d0e08120d41ad7e5412eacc969ad7"; :>> judgedAt = "2026-09-08"; :>> judgedBy = "claudeOpus5"; }
    verification selfBuildHooksRunAStableCopyRetroGate : Test { :>> id = "ef1c5766-021a-46c9-96aa-f16ccc197ee1"; :>> title = "Sprint 616 retro gate (autonomous, D0049)"; :>> createdAt = "2026-09-08"; :>> createdBy = "claudeOpus5"; :>> method = VerificationMethod::analyze; :>> procedureText = "Retro held; avoidable-issue scan: no new item - the stale hand copy running thirty commits behind HEAD for a day is the staleness issue408's resolver named and this sprint makes visible, already tracked. Process improvement: the workaround from sprint 594 was a copy placed by hand and never refreshed, which is exactly what the DoD's phrase rather than by a human remembering was written against; the refresh now rides the hook fire."; }
    // RAN: retro held; avoidable-issue scan: none beyond issue408 itself; no new Issue recorded in this commit
    part selfBuildHooksRunAStableCopyRetroGateR1 : TestResult { :>> id = "04f19582-8585-4a36-b6f5-be0825fe68d1"; :>> outcome = VerdictKind::pass; :>> judgedAgainst = "cafde85c5a8d0e08120d41ad7e5412eacc969ad7"; :>> judgedAt = "2026-09-08"; :>> judgedBy = "claudeOpus5"; }
}
