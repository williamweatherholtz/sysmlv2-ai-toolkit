// ProjectDeliveryS545 — Sprint 545: process audit reports every type or constraint a unit references but does not carry - the dependency, named, not judged. EXECUTE. 1 pts.
package ProjectDeliveryS545 {
    private import EngineElement::*;
    private import EngineWork::*;
    private import EngineVerification::*;
    private import EngineRelationships::*;

    #CharteredBy dependency from auditExternalRefsStory to d0222;

    part auditExternalRefsStory : Story {
        :>> id = "14dd9cac-e028-4252-9490-b1ecb6b1ed34";
        :>> title = "Sprint 545: process audit reports every type or constraint a unit references but does not carry - the dependency, named, not judged (1 pts)";
        :>> createdAt = "2026-09-04"; :>> createdBy = "claudeOpus5"; :>> kind = WorkKind::code; :>> priority = WorkPriority::p0; :>> owner = "claudeOpus5"; :>> estimatedPoints = 1;
    }

    action def DeliveryRunS545 {
        action storyAuditExternalRefs;
        verification storyAuditExternalRefsDoD : Test { :>> id = "4dbc1501-7bb3-4d53-8871-f0a5ec6cb9b5"; :>> method = VerificationMethod::test; :>> procedureText = "DELIVERED BACKLOG ITEMS: dcAuditSeesSchemaReferences (resolves issue263). DONE: keel process audit resolves every type, constraint and enum name a unit's carried .sysml files reference against the names the unit itself defines and the base schema (.engine/schema, which init ships) defines; anything else is reported per unit as ~ external: <name> (<kind>; defined in <file>, which the adopter must already have at this vintage), with the penumbra remedy on constraints - an unclaimed guard is CORE, so dropping the assert is usually better than importing it - and a name defined nowhere says so. Imports and comments are not references. VERIFY: live audit - nine units carry one external constraint each, all defined in .engine/rules/guard-constraints.sysml (the issue263 shape; decision-channel's judgmentRequestQuality is gone with the unit, the class is the same); units with no external reference show no line; every unit still TRAVELS-WHOLE, so the clean count did not rise; pure-core unit test covers constraint, type, enum, own-defined, schema-defined, comment and import cases; 480 tests; clippy clean."; }
        // RAN: process audit before/after 0 -> 9 external references; unit test 1/1; suite 480/0; clippy 0
        part storyAuditExternalRefsDoDR1 : TestResult { :>> id = "3ba3aa63-144d-478e-bee1-c2f0e214469a"; :>> outcome = VerdictKind::pass; :>> judgedAgainst = "136b455"; :>> judgedAt = "2026-09-04"; :>> judgedBy = "claudeOpus5"; }
    }

    verification auditExternalRefsRefineGate : Test { :>> id = "6ab4785d-c253-4096-acf9-d37a687d1cdd"; :>> title = "Sprint 545 refine gate (DoR)"; :>> createdAt = "2026-09-04"; :>> createdBy = "claudeOpus5"; :>> method = VerificationMethod::inspect; :>> procedureText = "READY once the audit's four checks were read and the fifth's boundary stated: what the unit defines plus what the schema defines is what an adopter is guaranteed to have; everything else is a dependency the audit can name but cannot judge, because the adopter's schema is not visible from here."; }
    verification auditExternalRefsStandupGate : Test { :>> id = "fa74395e-5cc2-4bef-9cc3-3cab2f2b7d30"; :>> title = "Sprint 545 standup gate"; :>> createdAt = "2026-09-04"; :>> createdBy = "claudeOpus5"; :>> method = VerificationMethod::inspect; :>> procedureText = "ONE CHOICE: a report line under TRAVELS-WHOLE, not a LANDS-RED verdict. The DoD says so and the vintage fixture (D0302) is the place a verdict can be had - the audit names the dependency, adoption-check --vintage tests it against a real older engine. Second: the first run listed every imported package as an external enum because `EngineElement::*` matched the Enum::member scan; imports and package lines are skipped, since an import names where a symbol comes from, not a type the file uses."; }
    verification auditExternalRefsImplementGate : Test { :>> id = "44784119-5375-40fb-aab6-a80d9335fac9"; :>> title = "Sprint 545 implement gate"; :>> createdAt = "2026-09-04"; :>> createdBy = "claudeOpus5"; :>> method = VerificationMethod::test; :>> procedureText = "RAN: keel process audit before and after - 0 then 9 units with external references, all constraints from guard-constraints.sysml; the import-noise fix; two clippy backtick items and a function-length split; the unit test on a fixture text with every reference shape."; }
    verification auditExternalRefsReviewGate : Test { :>> id = "abe4cbd6-10ca-4f8d-8c78-bd47bd0ab4bc"; :>> title = "Sprint 545 review gate — three passes per D0172"; :>> createdAt = "2026-09-04"; :>> createdBy = "claudeOpus5"; :>> method = VerificationMethod::inspect; :>> procedureText = "THREE PASSES. (1) CAN A DEPENDENCY HIDE: a name the unit references only in a comment or an import is not counted, by design; a name defined in the unit's skill registry file counts as carried because the registry travels with the unit (D0222). (2) IS THE CLEAN COUNT PROTECTED: yes - external lines do not change the verdict, and the summary line reads the same nine-of-nine TRAVELS-WHOLE as before. (3) WHAT IT DOES NOT SEE: the ADOPTER's schema - which is why it reports rather than judges, and why the vintage fixture exists."; }
    verification auditExternalRefsCloseOutGate : Test { :>> id = "3a28f072-af4a-441e-beca-f49fd71e9022"; :>> title = "Sprint 545 closeOut gate (autonomous, D0049)"; :>> createdAt = "2026-09-04"; :>> createdBy = "claudeOpus5"; :>> method = VerificationMethod::inspect; :>> procedureText = "CLOSED. issue263 resolves; the audit's own header explains the ~ external line."; }
    verification auditExternalRefsRetroGate : Test { :>> id = "306778e6-cc79-4140-b92e-39465d4e4663"; :>> title = "Sprint 545 retro gate (autonomous, D0049)"; :>> createdAt = "2026-09-04"; :>> createdBy = "claudeOpus5"; :>> method = VerificationMethod::analyze; :>> procedureText = "no new item - already tracked: the nine external constraint references are the D0302 vintage fixture's subject, not a defect in the units - a unit may assert a core guard its adopter's engine has; the audit now says which, and adoption-check --vintage says whether. Nothing this sprint found is outside issue263 and d0302."; }
}
