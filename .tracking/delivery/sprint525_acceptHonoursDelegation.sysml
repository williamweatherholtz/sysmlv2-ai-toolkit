// ProjectDeliveryS525 — Sprint 525: keel accept honours the recording delegation the policy already declares. CHANGE. 2 pts.
package ProjectDeliveryS525 {
    private import EngineElement::*;
    private import EngineWork::*;
    private import EngineVerification::*;
    private import EngineRelationships::*;

    #CharteredBy dependency from acceptHonoursDelegationStory to d0289;

    part acceptHonoursDelegationStory : Story {
        :>> id = "29c68fc6-d5d4-4177-af34-d82426ac8989";
        :>> title = "Sprint 525: the human's quoted chat words record an acceptance from an agent session - the command stops contradicting the declared delegation (2 pts)";
        :>> createdAt = "2026-09-03"; :>> createdBy = "claudeOpus5"; :>> kind = WorkKind::code; :>> priority = WorkPriority::p0; :>> owner = "claudeOpus5"; :>> estimatedPoints = 2;
    }

    action def DeliveryRunS525 {
        action storyAcceptHonoursDelegation;
        verification storyAcceptHonoursDelegationDoD : Test { :>> id = "fcef140d-acd0-4843-848e-282a649d167d"; :>> method = VerificationMethod::test; :>> procedureText = "DELIVERED BACKLOG ITEMS: dcAcceptHonoursDelegation. The human (st074): quoted user text is authoritative for acceptance; they know an AI could misquote them and accept that; the exception stands until a better non-local channel exists. FOUND: the exception was granted on 2026-08-22 (D0192 option A, attestation-policy.toml decisionAcceptance.delegatedRecording) with the substance rule demanding the quote; only cmd_accept's channel layer refused every agent session regardless. DONE: the channel layer reads the declared policy - quoted note recorded citing the delegation, unquoted note refused with QUOTE named, withdrawn delegation refused as before; CLAUDE.md section 4 states the rule and the human's words. VERIFY: three integration tests; clippy; 450 tests pass."; }
        // RAN: cargo test --test accept_honours_delegation 3/3 on a fresh scaffold (quoted -> accepted with the quote in the event and d0192 cited; unquoted -> exit 1 QUOTE; delegation line removed -> exit 1 no recording delegation); full suite 450/0; clippy clean
        part storyAcceptHonoursDelegationDoDR1 : TestResult { :>> id = "58ee7e63-6dba-492c-a96c-cdab609bd3b7"; :>> outcome = VerdictKind::pass; :>> judgedAgainst = "27f6944"; :>> judgedAt = "2026-09-03"; :>> judgedBy = "claudeOpus5"; }
    }

    verification acceptHonoursDelegationRefineGate : Test { :>> id = "c23bbc82-a9c8-491b-944f-0cdcdfe78d62"; :>> title = "Sprint 525 refine gate (DoR)"; :>> createdAt = "2026-09-03"; :>> createdBy = "claudeOpus5"; :>> method = VerificationMethod::inspect; :>> procedureText = "READY the moment the policy file was read: the request was already law, with the same stated limit the human restated today, and the friction was one command ignoring it. That turned a governance question into an alignment fix - the command honours the contract - and set the shape: refuse before writing, with the exact receipt named, rather than let the gate refuse after."; }
    verification acceptHonoursDelegationStandupGate : Test { :>> id = "19864ad6-0bd5-4261-9d86-186c302ea4c9"; :>> title = "Sprint 525 standup gate"; :>> createdAt = "2026-09-03"; :>> createdBy = "claudeOpus5"; :>> method = VerificationMethod::inspect; :>> procedureText = "TWO CHOICES. (1) The quote predicate is the substance rule's own function, exposed - one definition of what counts as a quote, applied before the write and after it. (2) The human's time bound ('until a better non-local channel') is recorded in the Decision and lives operationally in the policy's TO WITHDRAW line, not as an expiry in code - the same rule in two places would be D0105. The uncomfortable part is said plainly in the Decision: this is the one place the rule rests on my discipline to quote exactly, because no control reads chat."; }
    verification acceptHonoursDelegationImplementGate : Test { :>> id = "00fc4acf-02c8-41d9-856b-4b3da849d927"; :>> title = "Sprint 525 implement gate"; :>> createdAt = "2026-09-03"; :>> createdBy = "claudeOpus5"; :>> method = VerificationMethod::test; :>> procedureText = "RAN: three arms on a fresh scaffold, which ships the policy with the delegation and a Person 'you' and an AI 'ai' - the fixture is a downstream project, not this repo. The quoted arm checks the decision file flipped to accepted AND carries the quoted span; the unquoted arm checks nothing was written; the withdrawn arm deletes the policy line and expects the original refusal text."; }
    verification acceptHonoursDelegationReviewGate : Test { :>> id = "66a3684c-1a5b-4cfb-9148-412ef4f8d3b7"; :>> title = "Sprint 525 review gate — three passes per D0172"; :>> createdAt = "2026-09-03"; :>> createdBy = "claudeOpus5"; :>> method = VerificationMethod::inspect; :>> procedureText = "THREE PASSES. (1) DID THE TRUST BOUNDARY MOVE: no - the write layer still refuses an AI judge, the substance rule still demands the quote, the policy still names the delegation; the command stopped refusing what all three permit. (2) COULD THIS ACCEPT SOMETHING THE HUMAN DID NOT SAY: only by my misquoting, which D0192 named as the limit and the human accepted again today in so many words; the record quotes them, so a misquote is visible to them in their own decision file and on the channel. (3) IS THE OLD PATH GONE: no - TTY, console and GitHub still work; this adds a channel the policy already declared."; }
    verification acceptHonoursDelegationCloseOutGate : Test { :>> id = "986adaad-7cb0-45d8-82ad-9ea5deff8095"; :>> title = "Sprint 525 closeOut gate (autonomous, D0049)"; :>> createdAt = "2026-09-03"; :>> createdBy = "claudeOpus5"; :>> method = VerificationMethod::inspect; :>> procedureText = "CLOSED. The pending forks on this project can now be accepted by a sentence in chat, quoted; none has been, because none of the human's words so far named one."; }
    verification acceptHonoursDelegationRetroGate : Test { :>> id = "c6d0245e-6e74-4146-b912-02b0e92a8421"; :>> title = "Sprint 525 retro gate (autonomous, D0049)"; :>> createdAt = "2026-09-03"; :>> createdBy = "claudeOpus5"; :>> method = VerificationMethod::analyze; :>> procedureText = "no new item - already tracked: the finding is a dual-truth defect between a contract and the command that should serve it (D0105), found because the human felt the friction, not because a control saw the contradiction. A guard that checks every command's refusal path against the policy it cites is the general shape; it is the same family as cli-surface-declared and belongs to the verification revamp (dcVerificationByAuthority), where authority-by-method is being redefined anyway."; }
}
