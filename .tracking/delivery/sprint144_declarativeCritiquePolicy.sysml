// ProjectDeliveryS144 — Sprint 144: declarativeCritiquePolicy (D0097) — promote the D0080 "Core-3"
// required-lens-per-type map from a hardcoded Rust function to a DECLARED, downstream-overridable
// `.engine/contracts/critique-policy.toml`, read by the toolchain, shipped with a sound default so
// overriding is OPT-IN. The lens VOCABULARY (generic deficit-classes) stays in schema/core. CHANGE
// (CR): Decision d0097 (accepted by wweatherholtz "implement as described"). 5 pts. AUTONOMOUS ceremony (D0049).
package ProjectDeliveryS144 {
    private import EngineElement::*;
    private import EngineWork::*;
    private import EngineVerification::*;
    private import EngineRelationships::*;

    #CharteredBy dependency from declarativeCritiquePolicyStory to d0097;

    part declarativeCritiquePolicyStory : Story {
        :>> id = "63940516-2c7d-4e8f-c144-51627384c001";
        :>> title = "Sprint 144: declarativeCritiquePolicy (5 pts) — critique-lens policy is DECLARED (critique-policy.toml), not hardcoded; project-overridable, great default (D0097)";
        :>> createdAt = "2026-06-24"; :>> createdBy = "wweatherholtz"; :>> kind = WorkKind::code; :>> priority = WorkPriority::p2; :>> owner = "claudeOpus"; :>> estimatedPoints = 5;
    }

    action def DeliveryRunS144 {
        action storyDeclarativeCritiquePolicy;
        verification storyDeclarativeCritiquePolicyDoD : Test { :>> id = "63940516-2c7d-4e8f-c144-51627384c002"; :>> method = VerificationMethod::test; :>> procedureText = "CHANGE (D0097): the D0080 'Core-3' required-lens-per-type policy was hardcoded in the Rust toolchain (view.rs required_lenses() + the is_target match) — the lone assurance policy not declared like viewpoints/indicators. The question 'can we modularize critique lenses?' resolved to: the lens VOCABULARY (CritiqueLens) is the generic requirement-quality canon (NOT industry-specific) and stays in schema/core; the required-lens POLICY is what varies by project and becomes declarative. IMPLEMENTED: (1) .engine/contracts/critique-policy.toml — the declared default ([lenses] type -> required CritiqueLens list), shipped by `keel init` (verified via init_smoke); (2) a CritiquePolicy loader (view.rs) that reads the file, validates lens names against the canon (fail-loud on unknown), and falls back to a built-in Core-3 IDENTICAL to the shipped file; (3) compute_critique_coverage + critique_gaps + critique_coverage + the report aggregates now read the policy (a type with >=1 declared lens is a target; accepted-only for Decision stays intrinsic); (4) `keel critique-policy` view prints the active policy + source; (5) a `critique-policy` Viewpoint + the viewpoint-renderer guard's known-command list updated. EQUIVALENCE: with the file encoding Core-3, `keel critique-coverage` computes the SAME gap set (0) as the prior hardcoded map — no behavior change. d0097 (the #ProspectiveChange process-change Decision, D0070) accepted + critiqued (Core-3, survived). doc-sync: CLAUDE.md + element-critique process + README. VERIFY: clippy --workspace --all-targets -D warnings green; cargo test 51 lib (+ 2 policy tests) + init_smoke (+ policy assertion) + BDD pass; keel validate 157 + guard all (13) green; kernel validate_instances + validate_schema green (pre-commit, for the .engine changes)."; }
        part storyDeclarativeCritiquePolicyDoDR1 : TestResult { :>> id = "63940516-2c7d-4e8f-c144-51627384c003"; :>> outcome = VerdictKind::pass; :>> judgedAgainst = "5e91069"; :>> judgedAt = "2026-06-24"; :>> judgedBy = "claudeOpus"; }
    }

    verification declarativeCritiquePolicyRefineGate : Test { :>> id = "63940516-2c7d-4e8f-c144-51627384c004"; :>> title = "Sprint 144 refine gate (DoR)"; :>> createdAt = "2026-06-24"; :>> createdBy = "claudeOpus"; :>> method = VerificationMethod::inspect; :>> procedureText = "DoR: human raised 'can we modularize critique lenses?'. Triaged as CHANGE (alters what guard critique/critique-coverage mean + adds a declared-policy surface). Design laid out (lenses=generic deficit-classes in schema/core; required-lens POLICY -> declared TOML, default Core-3, opt-in override) + human acceptance ('implement as described. minimal friction since we're shipping a great default'). Resolver: declarativeCritiquePolicy. estimatedPoints=5. #CharteredBy d0097. DoR met."; }
    part declarativeCritiquePolicyRefineGateR1 : TestResult { :>> id = "63940516-2c7d-4e8f-c144-51627384c005"; :>> outcome = VerdictKind::pass; :>> judgedAgainst = "5e91069"; :>> judgedAt = "2026-06-24"; :>> judgedBy = "claudeOpus"; }
    verification declarativeCritiquePolicyStandupGate : Test { :>> id = "63940516-2c7d-4e8f-c144-51627384c006"; :>> title = "Sprint 144 standup gate"; :>> createdAt = "2026-06-24"; :>> createdBy = "claudeOpus"; :>> method = VerificationMethod::inspect; :>> procedureText = "Approach: TOML policy file (consistent with D0075 .view.toml + existing toml dep, lowest-friction) at .engine/contracts/; CritiquePolicy loader with canon validation + Core-3 fallback; thread through the ~7 compute_critique_coverage callers (load() for Result paths, load_or_core3() for advisory reports); new keel critique-policy + Viewpoint; record + critique d0097 (#ProspectiveChange, D0070); doc-sync. No blockers."; }
    part declarativeCritiquePolicyStandupGateR1 : TestResult { :>> id = "63940516-2c7d-4e8f-c144-51627384c007"; :>> outcome = VerdictKind::pass; :>> judgedAgainst = "5e91069"; :>> judgedAt = "2026-06-24"; :>> judgedBy = "claudeOpus"; }
    verification declarativeCritiquePolicyImplementGate : Test { :>> id = "63940516-2c7d-4e8f-c144-51627384c008"; :>> title = "Sprint 144 implement gate"; :>> createdAt = "2026-06-24"; :>> createdBy = "claudeOpus"; :>> method = VerificationMethod::test; :>> procedureText = "Implemented the policy file + loader + threading + `keel critique-policy` + Viewpoint + guard known-command + d0097 (accepted, #ProspectiveChange, Core-3 critiqued) + doc-sync. VERIFIED (live): `keel critique-policy .` shows source=file + Core-3; `keel critique-coverage .` gaps=0 (equivalence with the old map); unknown-lens fails loud (unit test); init ships the file (init_smoke). clippy green; cargo test 51 + 2 policy + init_smoke + BDD pass; keel validate 157 + guard all (13) PASS."; }
    part declarativeCritiquePolicyImplementGateR1 : TestResult { :>> id = "63940516-2c7d-4e8f-c144-51627384c009"; :>> outcome = VerdictKind::pass; :>> judgedAgainst = "5e91069"; :>> judgedAt = "2026-06-24"; :>> judgedBy = "claudeOpus"; }
    verification declarativeCritiquePolicyReviewGate : Test { :>> id = "63940516-2c7d-4e8f-c144-51627384c00a"; :>> title = "Sprint 144 review gate"; :>> createdAt = "2026-06-24"; :>> createdBy = "claudeOpus"; :>> method = VerificationMethod::inspect; :>> procedureText = "Diff reviewed. The change correctly separates VOCABULARY (generic deficit-classes, frozen in schema/core) from POLICY (project-variable, now declared) — answering the human's question precisely rather than over-building per-industry lens sets. TOML keeps friction low + matches the declared-config pattern (D0075). The Core-3 fallback + the empirical gap-set equivalence (0 == 0) prove no behavior regression. Fail-loud lens validation + the init_smoke ship assertion + the canon-validation unit test guard the new surface. d0097 carries the D0070 #ProspectiveChange marker + is itself Core-3 critiqued. Clean."; }
    part declarativeCritiquePolicyReviewGateR1 : TestResult { :>> id = "63940516-2c7d-4e8f-c144-51627384c00b"; :>> outcome = VerdictKind::pass; :>> judgedAgainst = "5e91069"; :>> judgedAt = "2026-06-24"; :>> judgedBy = "claudeOpus"; }
    verification declarativeCritiquePolicyCloseOutGate : Test { :>> id = "63940516-2c7d-4e8f-c144-51627384c00c"; :>> title = "Sprint 144 closeOut gate (autonomous, D0049)"; :>> createdAt = "2026-06-24"; :>> createdBy = "claudeOpus"; :>> method = VerificationMethod::inspect; :>> procedureText = "Autonomous closeOut (D0049): DoD pass; critique policy is declarative + downstream-overridable with a great default; behavior unchanged on this repo (gaps 0). clippy + 51 tests + 2 policy tests + init_smoke + keel validate 157 + guard all (13) green; kernel validators run in pre-commit for the .engine changes. Self-evidencing (D0051) except the d0097 acceptance (human confirmation, held). CR commit."; }
    part declarativeCritiquePolicyCloseOutGateR1 : TestResult { :>> id = "63940516-2c7d-4e8f-c144-51627384c00d"; :>> outcome = VerdictKind::pass; :>> judgedAgainst = "5e91069"; :>> judgedAt = "2026-06-24"; :>> judgedBy = "claudeOpus"; }
    verification declarativeCritiquePolicyRetroGate : Test { :>> id = "63940516-2c7d-4e8f-c144-51627384c00e"; :>> title = "Sprint 144 retro gate (autonomous, D0049)"; :>> createdAt = "2026-06-24"; :>> createdBy = "claudeOpus"; :>> method = VerificationMethod::analyze; :>> procedureText = "Autonomous retro (D0049). WELL: a design question ('modularize lenses?') was resolved by distinguishing vocabulary from policy — and the policy was the one assurance knob still hardcoded while viewpoints/indicators were already declared, so this closes a consistency gap. The TOML choice kept friction low (D0054). AVOIDABLE-ISSUE SCAN: threading the policy surfaced ~7 hidden callers of compute_critique_coverage (report aggregates) — handled with a lenient load_or_core3 for advisory paths vs fail-loud load for the gate; the new surface is guarded by a canon-validation unit test + the init_smoke ship assertion + the viewpoint-renderer known-command update (D0047 — corrections become guards). LESSON: a 'simple' policy extraction ripples into every aggregate that reads the coverage; check all callers, not just the named view. NON-blocking follow-ups: a future project could declare an extra lens (e.g. safety) + gate a new type by editing one TOML table. Estimate 5 pts held."; }
    part declarativeCritiquePolicyRetroGateR1 : TestResult { :>> id = "63940516-2c7d-4e8f-c144-51627384c00f"; :>> outcome = VerdictKind::pass; :>> judgedAgainst = "5e91069"; :>> judgedAt = "2026-06-24"; :>> judgedBy = "claudeOpus"; }
}
