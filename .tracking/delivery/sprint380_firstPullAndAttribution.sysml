// ProjectDeliveryS380 — Sprint 380: the first real pull through the inbox, and the attribution
// defect it exposed. Their verdicts recorded as THEIRS. EXECUTE. 2 pts.
package ProjectDeliveryS380 {
    private import EngineElement::*;
    private import EngineWork::*;
    private import EngineVerification::*;
    private import EngineRelationships::*;

    #CharteredBy dependency from firstPullStory to d0173;

    part firstPullStory : Story {
        :>> id = "0d800770-0814-6770-9b3e-000000300770";
        :>> title = "Sprint 380: the first inbox pull records their two verdicts, and the recorder learns the actor is data it carries (2 pts)";
        :>> createdAt = "2026-08-21"; :>> createdBy = "claudeOpus5"; :>> kind = WorkKind::code; :>> priority = WorkPriority::p0; :>> owner = "claudeOpus5"; :>> estimatedPoints = 2;
    }

    action def DeliveryRunS380 {
        action storyFirstPull;
        verification storyFirstPullDoD : Test { :>> id = "0d800771-0814-6771-9b3e-000000300771"; :>> method = VerificationMethod::test; :>> procedureText = "DELIVERED BACKLOG ITEMS: dcRecorderForwardsBy. Clears issue197. THE TRANSPORT'S FIRST FIELD RESULT: two rows delivered from their phone (d0173 Sign, issue159 Accept; By=wweatherholtz; deck HEAD c9999aa), pulled with Processed=false, recorded through the write API, and VERIFIED from the computed views - d0173 accepted, issue159 dispositioned act. The pull exposed issue197 pre-commit: the recorder's finding path omitted judged_by, the server resolved the session actor, and a High disposition landed as judgedBy=claudeOpus5 - guard-invisible because D0165's delegation makes an AI judge LEGAL, which is precisely what makes a MISATTRIBUTED one undetectable by policy. Both mis-recorded facts corrected before commit (judge = the human who tapped; attestation text = the event's substance, never a bare row pointer); the recorder now forwards By on every path and composes substantial attestation text; rehearsed green on a served COPY."; }
        part storyFirstPullDoDR1 : TestResult { :>> id = "0d800772-0814-6772-9b3e-000000300772"; :>> outcome = VerdictKind::pass; :>> judgedAgainst = "d24d52d"; :>> judgedAt = "2026-08-21"; :>> judgedBy = "claudeOpus5"; }
    }

    verification fpRefineGate : Test { :>> id = "0d800773-0814-6773-9b3e-000000300773"; :>> title = "Sprint 380 refine gate (DoR)"; :>> createdAt = "2026-08-21"; :>> createdBy = "claudeOpus5"; :>> method = VerificationMethod::inspect; :>> procedureText = "DoR. Their question - did it work - is answered by the store and the computed views, not by assertion: two rows in the inbox, two facts verified after recording. The defect found during the pull routes as EXECUTE under D0173 (the transport's own charter): a write-path correction plus the two records it mis-wrote, caught before commit by the standing diff review. estimatedPoints=2."; }
    part fpRefineGateR1 : TestResult { :>> id = "0d800774-0814-6774-9b3e-000000300774"; :>> outcome = VerdictKind::pass; :>> judgedAgainst = "d24d52d"; :>> judgedAt = "2026-08-21"; :>> judgedBy = "claudeOpus5"; }

    verification fpStandupGate : Test { :>> id = "0d800775-0814-6775-9b3e-000000300775"; :>> title = "Sprint 380 standup gate"; :>> createdAt = "2026-08-21"; :>> createdBy = "claudeOpus5"; :>> method = VerificationMethod::inspect; :>> procedureText = "Approach: fix the RECORDS first (truth), then the TOOL (recurrence), then re-rehearse. The records were editable because they had not been committed - this is correction of an unlanded write, not history rewrite. The recorder change is one principle applied three times: the actor is data the row carries, forwarded on every path, never ambient session state the server resolves. No blockers."; }
    part fpStandupGateR1 : TestResult { :>> id = "0d800776-0814-6776-9b3e-000000300776"; :>> outcome = VerdictKind::pass; :>> judgedAgainst = "d24d52d"; :>> judgedAt = "2026-08-21"; :>> judgedBy = "claudeOpus5"; }

    verification fpImplementGate : Test { :>> id = "0d800777-0814-6777-9b3e-000000300777"; :>> title = "Sprint 380 implement gate"; :>> createdAt = "2026-08-21"; :>> createdBy = "claudeOpus5"; :>> method = VerificationMethod::test; :>> procedureText = "WHY NO GUARD FIRED, verified against the policy contract rather than assumed: attestation-policy.toml [findingDisposition] permits kind=ai under D0165's recorded delegation, so judgedBy=claudeOpus5 on a High finding satisfies the declared policy. The check worked as designed; the defect was upstream of it, in the write. A guard against MISATTRIBUTION is not constructible from the record alone - a self-consistent record cannot prove who tapped - so the control is the write path: the recorder forwards By unconditionally, and the rehearsal exercises that path against a served copy. The e2e's existing legs already pin the server side (explicit judged_by resolution on the acceptance leg; Person enforcement on the sitting leg)."; }
    part fpImplementGateR1 : TestResult { :>> id = "0d800778-0814-6778-9b3e-000000300778"; :>> outcome = VerdictKind::pass; :>> judgedAgainst = "d24d52d"; :>> judgedAt = "2026-08-21"; :>> judgedBy = "claudeOpus5"; }

    verification fpReviewGate : Test { :>> id = "0d800779-0814-6779-9b3e-000000300779"; :>> title = "Sprint 380 review gate — three passes per D0172"; :>> createdAt = "2026-08-21"; :>> createdBy = "claudeOpus5"; :>> method = VerificationMethod::inspect; :>> procedureText = "PASS 1, CLAIMS vs computed: d0173 accepted and issue159 dispositioned read back from orient pendingAcceptances and the dispositions view; the corrected records validate; rehearsal green with validate clean on the copy. PASS 2, BOUNDARY: the rehearsal could not reuse the real rows (the copy already contains their recorded outcomes - accepting an accepted decision refuses), so it used a synthetic row against a still-pending finding; the limit that the copy is destroyed before its judgedBy can be read back is stated rather than papered over - attribution is asserted by the next real pull. PASS 3, OWN DIFF: the attest text first quoted the note AFTER the event sentence, burying their words - reordered so the verbatim note leads. WHAT A REVIEWER SHOULD ATTACK: the sitting path now overwrites the raw note with the composed attest text; deliberate, because the note is quoted verbatim inside it, but a consumer wanting the bare note must read the quoted segment."; }
    part fpReviewGateR1 : TestResult { :>> id = "0d80077a-0814-677a-9b3e-00000030077a"; :>> outcome = VerdictKind::pass; :>> judgedAgainst = "d24d52d"; :>> judgedAt = "2026-08-21"; :>> judgedBy = "claudeOpus5"; }

    verification fpCloseOutGate : Test { :>> id = "0d80077b-0814-677b-9b3e-00000030077b"; :>> title = "Sprint 380 closeOut gate (autonomous, D0049)"; :>> createdAt = "2026-08-21"; :>> createdBy = "claudeOpus5"; :>> method = VerificationMethod::inspect; :>> procedureText = "Autonomous closeOut (D0049). Their two verdicts are recorded facts with their name on them; the two inbox rows are marked Processed only AFTER the corrected records land (a row marked processed against a mis-attributed record would have closed the loop on a falsehood); issue197 recorded and cleared by dcRecorderForwardsBy; the skill's rows.json shape gains the head field. validate clean; 39 guards ALL PASS."; }
    part fpCloseOutGateR1 : TestResult { :>> id = "0d80077c-0814-677c-9b3e-00000030077c"; :>> outcome = VerdictKind::pass; :>> judgedAgainst = "d24d52d"; :>> judgedAt = "2026-08-21"; :>> judgedBy = "claudeOpus5"; }

    verification fpRetroGate : Test { :>> id = "0d80077d-0814-677d-9b3e-00000030077d"; :>> title = "Sprint 380 retro gate (autonomous, D0049)"; :>> createdAt = "2026-08-21"; :>> createdBy = "claudeOpus5"; :>> method = VerificationMethod::analyze; :>> procedureText = "Autonomous retro (D0049). AVOIDABLE-ISSUE SCAN under rcRecurrence: ambient-actor-instead-of-carried-actor is a FIRST occurrence in the recorder, but it is the same failure family issue072 recorded in the server (an omitted actor defaulting to a named human) - the family's rule now covers both directions: a write path neither DEFAULTS an actor nor INHERITS one when the event names who acted. WELL: (1) the defect was caught by the cheapest control in the whole stack - reading the diff before staging - which is worth noting because the expensive controls were all green; (2) the correction preserved the event's truth in the record itself (the disposition's text states the misattribution and its correction) rather than silently landing clean history; (3) the delegation-narrows-guards insight is recorded in the issue for the next policy decision to weigh. Estimate 2 pts, delivered."; }
    part fpRetroGateR1 : TestResult { :>> id = "0d80077e-0814-677e-9b3e-00000030077e"; :>> outcome = VerdictKind::pass; :>> judgedAgainst = "d24d52d"; :>> judgedAt = "2026-08-21"; :>> judgedBy = "claudeOpus5"; }
}
