// ProjectDeliveryS298 — Sprint 298: project-declared types already resolve and their instances
// already count; the missing piece was the COLLISION rule (userDefinedTypedefs +
// projectVocabularyIngestible, D0128). EXECUTE. 5 pts.
package ProjectDeliveryS298 {
    private import EngineElement::*;
    private import EngineWork::*;
    private import EngineVerification::*;
    private import EngineRelationships::*;

    #CharteredBy dependency from projectTypesStory to d0144;

    part projectTypesStory : Story {
        :>> id = "0d80024f-0814-624f-9b3e-00000030024f";
        :>> title = "Sprint 298: measure what project types already do; guard what they must not do (5 pts)";
        :>> createdAt = "2026-08-15"; :>> createdBy = "claudeOpus5"; :>> kind = WorkKind::code; :>> priority = WorkPriority::p0; :>> owner = "claudeOpus5"; :>> estimatedPoints = 5;
    }

    action def DeliveryRunS298 {
        action storyProjectTypes;
        verification storyProjectTypesDoD : Test { :>> id = "0d800250-0814-6250-9b3e-000000300250"; :>> method = VerificationMethod::test; :>> procedureText = "Delivers userDefinedTypedefs AND projectVocabularyIngestible (D0128). BOTH ITEMS OPEN ON A PREMISE THAT IS NO LONGER TRUE, and measuring it was the first act rather than the last: userDefinedTypedefs states that a user-authored `part def` in `.tracking` fails with `unresolved type reference` because resolution only scans `.engine/schema`. MEASURED: it resolves. A probe reproducing the item's own motivating case — five project defs (FunctionKindDef, FunctionVerb, RetiredVerb, NodeRoleDef, NamingRule) subtyping Element, plus instances, exactly the fcn-arch function dictionary that once produced 107 diagnostics — validates CLEAN, cross-file, provided the consuming package imports the declaring one, which is ordinary SysML scoping and not a defect. The INSTANCES count too, which is projectVocabularyIngestible's distinct ask: `keel diagram` finds them in the model, `duplicate-identity` scans them, and a declared view selecting `type = \"FunctionVerb\"` returned the instance projecting its PROJECT-DEFINED attributes (verbKind, example). WHAT WAS GENUINELY MISSING is the collision rule both items ask to be decided: a project `part def Story :> Element` — shadowing the type `orient` counts work by — validated clean and passed every guard, SILENTLY. Whichever definition wins, the other is ignored and a computed view starts counting something other than what the reader believes. DELIVERED: `type-collision`, a hard guard, 31 -> 32 guards. Measured before building: 91 engine defs against 305 project defs, ZERO collisions, so it starts clean with nothing grandfathered. VERIFIED BOTH WAYS: the shadowing probe FAILS naming both declaration sites; the five-type project vocabulary PASSES, because extension is the wanted behaviour. clippy clean; 137 lib tests; validate 321 clean."; }
        part storyProjectTypesDoDR1 : TestResult { :>> id = "0d800251-0814-6251-9b3e-000000300251"; :>> outcome = VerdictKind::pass; :>> judgedAgainst = "eeebc13"; :>> judgedAt = "2026-08-15"; :>> judgedBy = "claudeOpus5"; }
    }

    verification ptRefineGate : Test { :>> id = "0d800252-0814-6252-9b3e-000000300252"; :>> title = "Sprint 298 refine gate (DoR)"; :>> createdAt = "2026-08-15"; :>> createdBy = "claudeOpus5"; :>> method = VerificationMethod::inspect; :>> procedureText = "DoR. CONSUMER CHECK (dorConsumer, D0144) inverted into a PREMISE check, which is the same discipline pointed at the item rather than at the design: before building type resolution for `.tracking`, run the failing case the item describes. It did not fail. Building the described feature would have produced code that changed nothing and a sprint record claiming a fix for a defect that was not there — the most expensive possible outcome, because it would have looked like progress. estimatedPoints=5. DoR met."; }
    part ptRefineGateR1 : TestResult { :>> id = "0d800253-0814-6253-9b3e-000000300253"; :>> outcome = VerdictKind::pass; :>> judgedAgainst = "eeebc13"; :>> judgedAt = "2026-08-15"; :>> judgedBy = "claudeOpus5"; }

    verification ptStandupGate : Test { :>> id = "0d800254-0814-6254-9b3e-000000300254"; :>> title = "Sprint 298 standup gate"; :>> createdAt = "2026-08-15"; :>> createdBy = "claudeOpus5"; :>> method = VerificationMethod::inspect; :>> procedureText = "Approach: reproduce each item's motivating case as a real probe in `.tracking`, measure, then delete the probe. Both items were written against a real failure; the question is whether that failure survives, and only running it answers that. Then look for what the items ask that is NOT yet true — which turned out to be the collision rule both of them explicitly defer ('decide precedence + collision rules vs engine types'). No blockers."; }
    part ptStandupGateR1 : TestResult { :>> id = "0d800255-0814-6255-9b3e-000000300255"; :>> outcome = VerdictKind::pass; :>> judgedAgainst = "eeebc13"; :>> judgedAt = "2026-08-15"; :>> judgedBy = "claudeOpus5"; }

    verification ptImplementGate : Test { :>> id = "0d800256-0814-6256-9b3e-000000300256"; :>> title = "Sprint 298 implement gate"; :>> createdAt = "2026-08-15"; :>> createdBy = "claudeOpus5"; :>> method = VerificationMethod::test; :>> procedureText = "The guard checks NAMES ONLY, deliberately. Whether a project MEANT to extend the engine type or to replace it is not decidable from the text, and a guard that guessed would be wrong in one direction or the other — either blocking a legitimate rename or permitting a silent shadow. Reporting the collision with BOTH declaration sites and letting the author rename is exact, cheap to act on, and cannot be wrong. The alternative considered was a precedence rule (engine wins, or project wins): rejected because either choice makes the losing definition silently inert, which is the defect itself rather than a fix for it."; }
    part ptImplementGateR1 : TestResult { :>> id = "0d800257-0814-6257-9b3e-000000300257"; :>> outcome = VerdictKind::pass; :>> judgedAgainst = "eeebc13"; :>> judgedAt = "2026-08-15"; :>> judgedBy = "claudeOpus5"; }

    verification ptReviewGate : Test { :>> id = "0d800258-0814-6258-9b3e-000000300258"; :>> title = "Sprint 298 review gate"; :>> createdAt = "2026-08-15"; :>> createdBy = "claudeOpus5"; :>> method = VerificationMethod::inspect; :>> procedureText = "Reviewed. ONE ASK IS DELIBERATELY NOT MET and is recorded rather than quietly dropped: projectVocabularyIngestible lists COVERAGE among the things project instances should participate in, and they do not — `compute_coverage` targets Needs, SystemRequirements and accepted Decisions only. That is correct: assurance coverage measures whether stakeholder commitments are discharged, and a project's domain vocabulary is data the project reasons ABOUT, not a commitment it must verify. Including it would dilute an assurance metric with dictionary entries. Identity, query, render and temporal all do work, and were each demonstrated. Also noted: the item's suggestion that this be opt-in per project was not implemented — resolution already works for everyone, and adding a switch to disable a capability nobody has complained about would be inventing a setting to answer a question no one asked."; }
    part ptReviewGateR1 : TestResult { :>> id = "0d800259-0814-6259-9b3e-000000300259"; :>> outcome = VerdictKind::pass; :>> judgedAgainst = "eeebc13"; :>> judgedAt = "2026-08-15"; :>> judgedBy = "claudeOpus5"; }

    verification ptAnchorGate : Test { :>> id = "0d800260-0814-6260-9b3e-000000300260"; :>> title = "Sprint 298 anchor-correction gate"; :>> createdAt = "2026-08-15"; :>> createdBy = "claudeOpus5"; :>> method = VerificationMethod::test; :>> procedureText = "A stamping script inserted a TestResult into the MIDDLE OF A SENTENCE. It anchored on the first `\"; }` after the DoD's name, and that fragment also occurs INSIDE procedureText prose — the file broke with `unexpected character '-'` at backlog.sysml:1400. Caught immediately by `keel validate` in the same command, restored with `git checkout`, and redone with a line-based anchor: a DoD is authored on ONE line, so inserting after that line is exact. WORTH RECORDING because it is the same class as sprint 273's rule — never patch by a pattern you have not confirmed is unique — arriving through a new door: the pattern was unique as a TERMINATOR but not as a SUBSTRING, and this corpus is full of prose quoting its own syntax. The in-loop validate is what made it a two-minute correction rather than a corrupted commit."; }
    part ptAnchorGateR1 : TestResult { :>> id = "0d800261-0814-6261-9b3e-000000300261"; :>> outcome = VerdictKind::pass; :>> judgedAgainst = "eeebc13"; :>> judgedAt = "2026-08-15"; :>> judgedBy = "claudeOpus5"; }

    verification ptCloseOutGate : Test { :>> id = "0d80025a-0814-625a-9b3e-00000030025a"; :>> title = "Sprint 298 closeOut gate (autonomous, D0049)"; :>> createdAt = "2026-08-15"; :>> createdBy = "claudeOpus5"; :>> method = VerificationMethod::inspect; :>> procedureText = "Autonomous closeOut (D0049). userDefinedTypedefs and projectVocabularyIngestible both carry passing DoD TestResults — one sprint for both, because the same measurement answers both and a second ceremonial sprint for the same finding would be process theatre. Guards 31 -> 32. Every probe removed; the repo carries no synthetic vocabulary. clippy clean; 137 lib tests; validate 321 clean; check-engine clean; 32 guards green. No gate bypassed."; }
    part ptCloseOutGateR1 : TestResult { :>> id = "0d80025b-0814-625b-9b3e-00000030025b"; :>> outcome = VerdictKind::pass; :>> judgedAgainst = "eeebc13"; :>> judgedAt = "2026-08-15"; :>> judgedBy = "claudeOpus5"; }

    verification ptRetroGate : Test { :>> id = "0d80025c-0814-625c-9b3e-00000030025c"; :>> title = "Sprint 298 retro gate (autonomous, D0049)"; :>> createdAt = "2026-08-15"; :>> createdBy = "claudeOpus5"; :>> method = VerificationMethod::analyze; :>> procedureText = "Autonomous retro (D0049) under D0131's retroTrack. WELL: (1) the item's PREMISE was tested before its solution was built, and the premise was false — building the described feature would have produced code that changed nothing and a record claiming a fix for a defect that no longer existed, which looks exactly like progress and is worse than doing nothing; (2) the real gap was the part both items explicitly deferred ('decide precedence + collision rules'), found by asking what they ask for that is NOT yet true; (3) the coverage exclusion is recorded as a reasoned NO rather than an oversight. AVOIDABLE-ISSUE 1: my collision-measurement script reported '0 engine defs' and I nearly concluded there were no engine types to collide with — the regex was compiled without `re.M`, so `^` matched only at file start. I caught it because 0 was obviously absurd for a 15-file schema directory, not because anything checked. NO NEW ITEM, reason stated: this is the same read-the-number-and-ask-if-it-is-plausible discipline that caught the 190/470 conformance artifact in sprint 283, and it worked again. The operational rule already in force is the one that saved it: a measurement that is surprising is a measurement to re-check before it becomes a conclusion. Estimate 5 pts, delivered."; }
    part ptRetroGateR1 : TestResult { :>> id = "0d80025d-0814-625d-9b3e-00000030025d"; :>> outcome = VerdictKind::pass; :>> judgedAgainst = "eeebc13"; :>> judgedAt = "2026-08-15"; :>> judgedBy = "claudeOpus5"; }
}
