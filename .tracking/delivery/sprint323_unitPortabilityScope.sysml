// ProjectDeliveryS323 — Sprint 323: the concept generalizes; the command waits for demand. CHANGE (§3a). 2 pts.
package ProjectDeliveryS323 {
    private import EngineElement::*;
    private import EngineWork::*;
    private import EngineVerification::*;
    private import EngineRelationships::*;

    #CharteredBy dependency from unitScopeStory to d0159;

    part unitScopeStory : Story {
        :>> id = "0d8003e0-0814-63e0-9b3e-0000003003e0";
        :>> title = "Sprint 323: D0159 — viewpoints are a second unit KIND, not built yet (2 pts)";
        :>> createdAt = "2026-08-17"; :>> createdBy = "claudeOpus5"; :>> kind = WorkKind::decision; :>> priority = WorkPriority::p0; :>> owner = "claudeOpus5"; :>> estimatedPoints = 2;
    }

    action def DeliveryRunS323 {
        action storyUnitScope;
        verification storyUnitScopeDoD : Test { :>> id = "0d8003e1-0814-63e1-9b3e-0000003003e1"; :>> method = VerificationMethod::analyze; :>> procedureText = "Resolves issue138 via dcUnitPortabilityScope, which asked for a DECISION before any code. D0159 records that the unit concept DOES generalize — `unit.toml` is unit-shaped and merely named after processes, and both apparent obstacles already have answers inside the process mechanism (a shared-file declaration carried BY NAME as rules already are; a binary-capability dependency carried by name with import reporting it, as guards already are) — and that the command is NOT built, because the demand is provably zero: all 32 viewpoints are ENGINE-authored, `keel init` ships the whole set to every downstream project, and no project has ever authored one, so the only unserved case has never occurred. issue138 is dispositioned acceptRisk rather than dismissed, because the gap is real and knowingly unaddressed; AI-judged, which the authority policy permits for a LOW finding (D0080) and requires a human for only at or above Medium. D0159 is PROPOSED and blocks nothing — no action depends on it. READ BACK: `open-issues` reports ZERO open, validate 351 clean, check-engine clean, 34 guards ALL PASS."; }
        part storyUnitScopeDoDR1 : TestResult { :>> id = "0d8003e2-0814-63e2-9b3e-0000003003e2"; :>> outcome = VerdictKind::pass; :>> judgedAgainst = "7f09bc8"; :>> judgedAt = "2026-08-17"; :>> judgedBy = "claudeOpus5"; }
    }

    verification usRefineGate : Test { :>> id = "0d8003e3-0814-63e3-9b3e-0000003003e3"; :>> title = "Sprint 323 refine gate (DoR)"; :>> createdAt = "2026-08-17"; :>> createdBy = "claudeOpus5"; :>> method = VerificationMethod::inspect; :>> procedureText = "DoR. The DoD's own instruction was to DECIDE before writing code, and the first thing I did was look for the demand rather than for the design — which inverted the answer. The design question ('can it use the same mechanism?') has a clean yes; the demand question ('does anyone need it?') has a measured no. Had I started from the design I would have built it, because the code is small and the shape is obvious, and that is exactly the trap. estimatedPoints=2."; }
    part usRefineGateR1 : TestResult { :>> id = "0d8003e4-0814-63e4-9b3e-0000003003e4"; :>> outcome = VerdictKind::pass; :>> judgedAgainst = "7f09bc8"; :>> judgedAt = "2026-08-17"; :>> judgedBy = "claudeOpus5"; }

    verification usStandupGate : Test { :>> id = "0d8003e5-0814-63e5-9b3e-0000003003e5"; :>> title = "Sprint 323 standup gate"; :>> createdAt = "2026-08-17"; :>> createdBy = "claudeOpus5"; :>> method = VerificationMethod::inspect; :>> procedureText = "Approach: MEASURE the demand (who authors viewpoints, and does `keel init` already ship them) before designing anything, then record the design analysis so it is not lost, then disposition the finding at the authority its severity allows. No blockers."; }
    part usStandupGateR1 : TestResult { :>> id = "0d8003e6-0814-63e6-9b3e-0000003003e6"; :>> outcome = VerdictKind::pass; :>> judgedAgainst = "7f09bc8"; :>> judgedAt = "2026-08-17"; :>> judgedBy = "claudeOpus5"; }

    verification usImplementGate : Test { :>> id = "0d8003e7-0814-63e7-9b3e-0000003003e7"; :>> title = "Sprint 323 implement gate"; :>> createdAt = "2026-08-17"; :>> createdBy = "claudeOpus5"; :>> method = VerificationMethod::analyze; :>> procedureText = "NO CODE WAS WRITTEN, which is the deliverable. The reason is stated in D0159 and it is a consistency argument I hold myself to: D0157 was accepted five records earlier on exactly this reasoning applied to the HUMAN'S speculative feature — a capability built for a demand that does not exist must be maintained, documented, kept green by 34 guards, and reasoned about by every future reader, and the first real user would probably want it differently because their requirement would be written against a real transfer instead of an imagined one. Declining my own speculative feature on the same grounds is what makes that discipline a rule rather than a preference about other people's ideas. WHAT WAS ACTUALLY MEASURED, since 'zero demand' is the whole basis: every one of the 32 declared Viewpoints is authored under `.engine/views`, none under `.tracking`; `keel init` ships `.engine/` including views, so a downstream project starts holding all 32; therefore the only unserved case is a PROJECT-authored viewpoint moving to another project, and there are no project-authored viewpoints."; }
    part usImplementGateR1 : TestResult { :>> id = "0d8003e8-0814-63e8-9b3e-0000003003e8"; :>> outcome = VerdictKind::pass; :>> judgedAgainst = "7f09bc8"; :>> judgedAt = "2026-08-17"; :>> judgedBy = "claudeOpus5"; }

    verification usReviewGate : Test { :>> id = "0d8003e9-0814-63e9-9b3e-0000003003e9"; :>> title = "Sprint 323 review gate"; :>> createdAt = "2026-08-17"; :>> createdBy = "claudeOpus5"; :>> method = VerificationMethod::inspect; :>> procedureText = "Reviewed. TWO THINGS I CHECKED BEFORE CLAIMING THE AUTHORITY TO DISPOSITION THIS MYSELF: that issue138 is Severity::Low, and that the control actually permits it — `attestation-authority` requires the declared human policy only for dispositions at or above Medium, and the guard's own documentation records the precedent that demanding a human on every disposition would fail a correct AI-dispositioned Low finding (D0080). I did not manufacture a human acceptance for D0159 either: it is PROPOSED, so `acceptanceEventRule` is not engaged and no confirmation event exists to be fabricated. The alternative I rejected was marking D0159 accepted with an inspect-method acceptance event — that would satisfy the letter of the rule (which asks for a passing `*Accept` result) while evading its purpose, which is that a human accepts direction. acceptRisk over dismiss for the same honesty reason: dismissing would assert the gap is not real."; }
    part usReviewGateR1 : TestResult { :>> id = "0d8003ea-0814-63ea-9b3e-0000003003ea"; :>> outcome = VerdictKind::pass; :>> judgedAgainst = "7f09bc8"; :>> judgedAt = "2026-08-17"; :>> judgedBy = "claudeOpus5"; }

    verification usCloseOutGate : Test { :>> id = "0d8003eb-0814-63eb-9b3e-0000003003eb"; :>> title = "Sprint 323 closeOut gate (autonomous, D0049)"; :>> createdAt = "2026-08-17"; :>> createdBy = "claudeOpus5"; :>> method = VerificationMethod::inspect; :>> procedureText = "Autonomous closeOut (D0049). ZERO OPEN ISSUES for the first time in this run — issue132, 133, 135, 136, 137, 138 and 139 all resolved across sprints 318-323. The ready frontier is empty. D0159 sits in pendingAcceptances, queued rather than blocking, per the human's standing instruction not to be stopped for approval. validate 351 clean; check-engine clean; 34 guards ALL PASS; no code changed, so no rebuild and no test-count movement. What remains is non-blocking burndown, chiefly the 41 SystemRequirements that are exercised but never EXAMINED — and critic-independence means the critic cannot be me, which is a real blocker rather than an approval one."; }
    part usCloseOutGateR1 : TestResult { :>> id = "0d8003ec-0814-63ec-9b3e-0000003003ec"; :>> outcome = VerdictKind::pass; :>> judgedAgainst = "7f09bc8"; :>> judgedAt = "2026-08-17"; :>> judgedBy = "claudeOpus5"; }

    verification usRetroGate : Test { :>> id = "0d8003ed-0814-63ed-9b3e-0000003003ed"; :>> title = "Sprint 323 retro gate (autonomous, D0049)"; :>> createdAt = "2026-08-17"; :>> createdBy = "claudeOpus5"; :>> method = VerificationMethod::analyze; :>> procedureText = "Autonomous retro (D0049) under D0131's retroTrack. WELL: (1) measuring demand before designing inverted the answer, and the sprint's deliverable is therefore no code — the same discipline D0157 applied to the human's idea, now applied to mine, which is the only way it counts as a rule; (2) the authority to disposition was CHECKED against the guard rather than assumed from the severity number; (3) the tempting evasion was named and rejected in the review gate rather than silently avoided — marking D0159 accepted with an inspect-method acceptance event would have satisfied `acceptanceEventRule`'s letter while defeating its purpose, and writing that down is worth more than quietly not doing it. AVOIDABLE-ISSUE: none this sprint. PATTERN WORTH CARRYING, from six issues closed in six sprints: five of the seven resolved were the same shape — a check narrower than its subject (issue136 a resolver of the wrong kind, issue139 an enumeration narrower than the audit, issue133 a parser accepting a flag as a path) or a statement wider than its demand (issue132's Need, and the hosted direction D0157 declined). Narrow checks and wide statements are the two ways this model has drifted, and both pass every gate. Estimate 2 pts, delivered."; }
    part usRetroGateR1 : TestResult { :>> id = "0d8003ee-0814-63ee-9b3e-0000003003ee"; :>> outcome = VerdictKind::pass; :>> judgedAgainst = "7f09bc8"; :>> judgedAt = "2026-08-17"; :>> judgedBy = "claudeOpus5"; }
}
