// ProjectDeliveryS690 — Sprint 690: A Decision or task DoD that quotes the human links a Statement holding their words verbatim. Resolves issue428 (stpa-self run 2, UCA-H1, hazard EHZ3): the tree held the agent's rendering of the human's direction with nothing to check it against, because the intake channel (keel record statement, D0216/D0236) was bound only to elicitation. Delivers dcDirectionDecisionsLinkTheirStatement under D0463 (process-change, held proposed for the human: guards.rs and guard-constraints.sysml are enforcement surface, D0209 clause 2). CHANGE, CR: commit.. EXECUTE. 3 pts.
package ProjectDeliveryS690 {
    private import EngineElement::*;
    private import EngineWork::*;
    private import EngineVerification::*;
    private import EngineRelationships::*;

    #CharteredBy dependency from directionCitedLinksItsStatementStory to d0463;

    part directionCitedLinksItsStatementStory : Story {
        :>> id = "0a430869-071c-4a4f-ac00-bd417024de86";
        :>> title = "Sprint 690: A Decision or task DoD that quotes the human links a Statement holding their words verbatim. Resolves issue428 (stpa-self run 2, UCA-H1, hazard EHZ3): the tree held the agent's rendering of the human's direction with nothing to check it against, because the intake channel (keel record statement, D0216/D0236) was bound only to elicitation. Delivers dcDirectionDecisionsLinkTheirStatement under D0463 (process-change, held proposed for the human: guards.rs and guard-constraints.sysml are enforcement surface, D0209 clause 2). CHANGE, CR: commit. (3 pts)";
        :>> createdAt = "2026-09-13"; :>> createdBy = "claudeFable5"; :>> kind = WorkKind::code; :>> priority = WorkPriority::p0; :>> owner = "claudeFable5"; :>> estimatedPoints = 3;
    }

    action def DeliveryRunS690 {
        action storyDirectionCitedLinksItsStatement;
        verification storyDirectionCitedLinksItsStatementDoD : Test { :>> id = "aef8d6ee-1b2e-442f-ac72-f8da767d36af"; :>> method = VerificationMethod::test; :>> procedureText = "DELIVERED: guard direction-cited (HARD, guard 73) in guards.rs - human_spans reads an attribution phrase (their words / the human's words / the human said / human's own words / the human, YYYY-MM-DD), an optional verbatim, then a quoted span of 8+ characters in curly or straight quotes (a straight closing quote is one not followed by a letter or digit); direction_violations (pure core) splits citing records by createdAt against 2026-09-12 into forward violators (no DerivedFrom edge to a Statement, or a linked Statement whose folded text lacks the span), grandfathered Decisions, and undated DoDs; the guard reads Decisions from .engine/decisions/ and DoDs plus Statements and edges from .tracking/, prints one counted-history line, and names the fix in each violation. Registered in GUARD_NAMES and the dispatch, constraint def directionCited (D0195 cl.1), gDirectionCited in control-map.sysml mapped to ehz3, guards.md row, ccDirectionLinksItsStatement gains its edge to gDirectionCited. Four unit tests hold the D0388 pair: the reader's forms and non-forms; a citing Decision after the cutoff with no Statement is refused and one whose Statement lacks the span is refused (known-positive); a linked citing Decision passes and a Decision quoting nobody is untouched (known-negative); the self-build holds with one history line. On the tree at HEAD: 1883 scanned, 0 violations, 8 citing Decisions and 6 undated citing DoDs counted. FOUND and tracked: keel record task stamps no createdAt/createdBy on the DoD Test (issue513, resolver dcRecordedDoDsCarryTheirDate, recorded this sprint)."; }
        // RAN: RAN: cargo clippy --workspace --all-targets -- -D warnings -> Finished; cargo test --release --lib -- direction_cited -> 4 passed; cargo test --release --lib -- guards -> 106 passed 0 failed; keel-serve gate guard direction-cited -> PASS 1883 scanned, 0 violation(s), 1 counted-history line (8 citing Decisions, 6 undated DoDs); gate guard --no-receipt -> ALL PASS; gate validate -> 789 clean; gate check-engine -> clean
        part storyDirectionCitedLinksItsStatementDoDR1 : TestResult { :>> id = "4b6e25bf-e6df-4be3-b300-ec9e1f1ed31b"; :>> outcome = VerdictKind::pass; :>> judgedAgainst = "860c078"; :>> judgedAt = "2026-09-13"; :>> judgedBy = "claudeFable5"; }
    }

    verification directionCitedLinksItsStatementRefineGate : Test { :>> id = "dd91d82a-c6c4-4b88-82bf-4e82d0a9658a"; :>> title = "Sprint 690 refine gate (DoR)"; :>> createdAt = "2026-09-13"; :>> createdBy = "claudeFable5"; :>> method = VerificationMethod::inspect; :>> procedureText = "Chartered by D0463. Three points: a reader with six forms and two quote styles, a pure core with a three-way split, the tree walk over two roots, four registration surfaces, four tests, a process-change Decision and a found Issue. DoR: the DoD is on the backlog item (dcDirectionDecisionsLinkTheirStatementDoD, method test); issue428 carries #Resolves from it; ccDirectionLinksItsStatement states the constraint; no blocker. NOT A FORK: issue428's resolver and CC-H1 name the change; the two design choices inside it (a closed anchor vocabulary; undated DoDs counted rather than guessed) are stated in D0463 and the second is tracked as issue513."; }
    // RAN: AI-examined inspect/analyze pass (D0312 B); sprint file section holds the examination
    part directionCitedLinksItsStatementRefineGateR1 : TestResult { :>> id = "af7a03b3-6efc-4f61-be61-62abd4268873"; :>> outcome = VerdictKind::proposed; :>> judgedAgainst = "860c078"; :>> judgedAt = "2026-09-13"; :>> judgedBy = "claudeFable5"; }
    verification directionCitedLinksItsStatementStandupGate : Test { :>> id = "2cda91aa-796c-444c-9b90-3ee41b333225"; :>> title = "Sprint 690 standup gate"; :>> createdAt = "2026-09-13"; :>> createdBy = "claudeFable5"; :>> method = VerificationMethod::inspect; :>> procedureText = "Order: read the compound-decisions and consent-scope guards as the forward-only idiom; survey how the tree's Decisions actually phrase a citation before writing the reader (the first draft read straight quotes only and missed the curly verbatim form the acceptance receipts use); record the resolver task and issue513 first so the guard's history line names a real Issue; patch guards.rs, guard-constraints.sysml, control-map.sysml, guards.md, engine-ucas.sysml; clippy over ALL targets (the pre-commit hook lints test code too, sprint 689 learned that); unit tests; rebuild and copy to keel-serve.exe; run the guard alone, then the four gates; record D0463 (held) with its DependsOn to d0236; record the sprint, gates and DoD result; commit CR: detached; read git status -sb and the CI conclusion."; }
    // RAN: AI-examined inspect/analyze pass (D0312 B); sprint file section holds the examination
    part directionCitedLinksItsStatementStandupGateR1 : TestResult { :>> id = "eb251098-3ca0-435d-a608-9920010b144f"; :>> outcome = VerdictKind::proposed; :>> judgedAgainst = "860c078"; :>> judgedAt = "2026-09-13"; :>> judgedBy = "claudeFable5"; }
    verification directionCitedLinksItsStatementImplementGate : Test { :>> id = "2e895bba-d5ba-4557-8cd4-5cad4258937a"; :>> title = "Sprint 690 implement gate"; :>> createdAt = "2026-09-13"; :>> createdBy = "claudeFable5"; :>> method = VerificationMethod::test; :>> procedureText = "guards.rs: DIRECTION_CUTOFF, DIRECTION_ANCHORS, fold_quoted, human_spans, DirectionRecord, direction_violations, excerpt, quoted_field, direction_cited, mod direction_cited_tests; GUARD_NAMES 72 -> 73 with direction-cited; dispatch arm. guard-constraints.sysml: constraint def directionCited (guard 73). control-map.sysml: gDirectionCited -> ehz3. guards.md: the direction-cited row. engine-ucas.sysml: dependency from ccDirectionLinksItsStatement to gDirectionCited. backlog.sysml: dcRecordedDoDsCarryTheirDate (record task). issues-claudeFable5.sysml: issue513 with #Resolves. RAN: cargo clippy --workspace --all-targets -- -D warnings -> Finished, no warnings; cargo test --release --lib -- direction_cited -> 4 passed; cargo test --release --lib -- guards -> 106 passed 0 failed; cargo build --release -> Finished; ./target/release/keel-serve.exe gate guard direction-cited -> PASS 1883 scanned, 0 violation(s), 1 counted-history line (8 citing Decisions before 2026-09-12, 6 undated citing DoDs, issue513); gate validate -> 789 clean; gate check-engine -> clean; sync-claude --check -> matches. D0463 recorded proposed, OUTSIDE standing consent (ProspectiveChange), #DependsOn d0236 authored by textpatch."; }
    // RAN: RAN: cargo clippy --workspace --all-targets -- -D warnings -> Finished; cargo test --release --lib -- direction_cited -> 4 passed; cargo test --release --lib -- guards -> 106 passed 0 failed; keel-serve gate guard direction-cited -> PASS 1883 scanned, 0 violation(s), 1 counted-history line (8 citing Decisions, 6 undated DoDs); gate guard --no-receipt -> ALL PASS; gate validate -> 789 clean; gate check-engine -> clean
    part directionCitedLinksItsStatementImplementGateR1 : TestResult { :>> id = "cff329ae-32de-4b23-be8b-4d86f0fd0959"; :>> outcome = VerdictKind::pass; :>> judgedAgainst = "860c078"; :>> judgedAt = "2026-09-13"; :>> judgedBy = "claudeFable5"; }
    verification directionCitedLinksItsStatementReviewGate : Test { :>> id = "33468523-42d9-4f19-a035-66668035b941"; :>> title = "Sprint 690 review gate — three passes per D0172"; :>> createdAt = "2026-09-13"; :>> createdBy = "claudeFable5"; :>> method = VerificationMethod::inspect; :>> procedureText = "Three passes (D0172). Correctness: the reader and the Statement side fold the same escapes through one function, so a doubled quote in a Statement's text and a bare quote in a Decision compare equal; the closing-quote rule was checked against the tree's own citations (an apostrophe inside a quote, a usage line naming their words, a dated attribution with no quote) and each is in the first unit test; the tree walk reads the same files the write path emits (one-line Decision fields, one-line DoDs) and a hand-authored multi-line DoD is read to its procedureText line, so an undated one is counted, never mis-judged. Honesty: the DoD result is method test with the cargo and guard receipts; the counts 8 and 6 are the guard's own print, quoted; the self-build test asserts the history line exists rather than a number that history could change. Scope: the guard does not read acceptance receipts (their words, verbatim: in a dNNNNAccept Test) - those are D0289's and guard acceptance-binds-to-text holds them; it does not compel a Statement on a Decision that paraphrases or names the human without quoting; ccDirectionLinksItsStatement's statement (claudeOpus5's item) is not edited, the edge is ADDED (D0108)."; }
    // RAN: AI-examined inspect/analyze pass (D0312 B); sprint file section holds the examination
    part directionCitedLinksItsStatementReviewGateR1 : TestResult { :>> id = "53b2e7c9-6f15-487b-ac1a-ba3a685c11c3"; :>> outcome = VerdictKind::proposed; :>> judgedAgainst = "860c078"; :>> judgedAt = "2026-09-13"; :>> judgedBy = "claudeFable5"; }
    verification directionCitedLinksItsStatementCloseOutGate : Test { :>> id = "0f2dd7b9-0b97-42f3-bfb3-6e1bd88defea"; :>> title = "Sprint 690 closeOut gate (autonomous, D0049)"; :>> createdAt = "2026-09-13"; :>> createdBy = "claudeFable5"; :>> method = VerificationMethod::inspect; :>> procedureText = "Closes on the four unit tests and the guards module green, clippy clean over all targets, the guard's own PASS line on the real tree, gate validate, gate check-engine, gate guard --no-receipt ALL PASS with D0463 in the index, and sync-claude --check, over the index holding guards.rs, guard-constraints.sysml, control-map.sysml, guards.md, engine-ucas.sysml, backlog.sysml, issues-claudeFable5.sysml, D0463, this sprint and the DoD result."; }
    // RAN: AI-examined inspect/analyze pass (D0312 B); sprint file section holds the examination
    part directionCitedLinksItsStatementCloseOutGateR1 : TestResult { :>> id = "fa19d72f-2940-4729-840a-d405e5cd3a6d"; :>> outcome = VerdictKind::proposed; :>> judgedAgainst = "860c078"; :>> judgedAt = "2026-09-13"; :>> judgedBy = "claudeFable5"; }
    verification directionCitedLinksItsStatementRetroGate : Test { :>> id = "096f8d34-8c65-4733-ae4b-c659bd8d046c"; :>> title = "Sprint 690 retro gate (autonomous, D0049)"; :>> createdAt = "2026-09-13"; :>> createdBy = "claudeFable5"; :>> method = VerificationMethod::analyze; :>> procedureText = "AVOIDABLE-ISSUE SCAN, one new item (D0131): issue513 - keel record task stamps no createdAt or createdBy on the DoD Test it writes, so no createdAt-cut guard can judge a task DoD forward; the write path applies D0129 to the action and not to the Test beside it. Tracked with resolver dcRecordedDoDsCarryTheirDate, recorded before the guard was finished so the guard's history line names it. STATED: the first reader draft accepted straight quotes only and read 8 citing Decisions; the survey of the tree's phrasing added the curly verbatim form, and the count stayed 8 because the curly form lives in acceptance receipts the guard does not read - the survey was still the right step, since a Decision field written that way tomorrow is now read. The pre-commit clippy over all targets is now a step in this sprint's standup, not a surprise at the commit."; }
    // RAN: AI-examined inspect/analyze pass (D0312 B); sprint file section holds the examination
    part directionCitedLinksItsStatementRetroGateR1 : TestResult { :>> id = "9c71ed56-152d-43e8-b6b3-ce2607612bfe"; :>> outcome = VerdictKind::proposed; :>> judgedAgainst = "860c078"; :>> judgedAt = "2026-09-13"; :>> judgedBy = "claudeFable5"; }
}
