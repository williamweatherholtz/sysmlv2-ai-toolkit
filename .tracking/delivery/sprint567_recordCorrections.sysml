// ProjectDeliveryS567 — Sprint 567: D0234's record corrected to what was measured - and the gate learned to let a correction and its re-binding land together. EXECUTE. 3 pts.
package ProjectDeliveryS567 {
    private import EngineElement::*;
    private import EngineWork::*;
    private import EngineVerification::*;
    private import EngineRelationships::*;

    #CharteredBy dependency from recordCorrectionsStory to d0329;

    part recordCorrectionsStory : Story {
        :>> id = "a5f68455-2f56-4be4-b6db-e5051529be3d";
        :>> title = "Sprint 567: D0234's record corrected to what was measured - and the gate learned to let a correction and its re-binding land together (3 pts)";
        :>> createdAt = "2026-09-05"; :>> createdBy = "claudeOpus5"; :>> kind = WorkKind::code; :>> priority = WorkPriority::p0; :>> owner = "claudeOpus5"; :>> estimatedPoints = 3;
    }

    action def DeliveryRunS567 {
        action storyRecordCorrections;
        verification storyRecordCorrectionsDoD : Test { :>> id = "cbfb60e0-cfe9-4edb-858e-eac359c67c74"; :>> method = VerificationMethod::test; :>> procedureText = "DELIVERED BACKLOG ITEMS: dcPanelRecordCorrections (resolves issue283; D0330 carries the corrections, D0329 and D0331 the two guard changes the work needed). DONE: the six refuted claims are corrected in D0330, a Decision beside D0234 with a #DependsOn edge - not in D0234 itself, because D0108 forbids a non-owner editing in place and the ownership guard said so when the edit was first tried (D0234 is claudeFable5-owned). sprint469's two RAN receipts no longer cite commits in deleted scratch repositories - they name the suite tests that prove the same claims (land_gate, init_smoke, no_green_over_nothing) and explain the installed-units version bump 10 to 12 as adoption_check_can_fail exporting from the live root (issue339). The validate/require_project refusal names the directory that is actually missing. Guard 61 reads a re-binding against the commit that first carried it (D0329), with a pending warning while uncommitted, pinned by the extended acceptance_binds_to_text test."; }
        // RAN: same suite receipt: 524/0 exit 0
        part storyRecordCorrectionsDoDR1 : TestResult { :>> id = "ab832874-0078-4cb0-9885-c38736abea69"; :>> outcome = VerdictKind::pass; :>> judgedAgainst = "f84ff686e69a9d7770c67816aa2ecede8b84f470"; :>> judgedAt = "2026-09-05"; :>> judgedBy = "claudeOpus5"; }
    }

    verification recordCorrectionsRefineGate : Test { :>> id = "3009bd3f-8f30-451b-9a51-8d42da4dadda"; :>> title = "Sprint 567 refine gate (DoR)"; :>> createdAt = "2026-09-05"; :>> createdBy = "claudeOpus5"; :>> method = VerificationMethod::inspect; :>> procedureText = "READY: issue283 listed six refuted claims and the DoD named the remedy for each. The unplanned half was that the correction could not be committed: the gate refused the edit without a re-binding and the re-binding's SHA once the text differed - the existing test had committed in a hook-less fixture, which is the one thing the live gate forbids."; }
    verification recordCorrectionsStandupGate : Test { :>> id = "ed5a8431-e9c2-4692-952b-0277e1d7f393"; :>> title = "Sprint 567 standup gate"; :>> createdAt = "2026-09-05"; :>> createdBy = "claudeOpus5"; :>> method = VerificationMethod::inspect; :>> procedureText = "THE CORRECTION EXPOSED TWO CONTROL GAPS AND ONE RULE THAT HELD: an owner's editorial correction to an accepted Decision had no path through the gate (D0329); re-staging a 2026-08-29 sprint file made retro-backlog judge an unchanged retro by a later rule (D0331); and the ownership guard rightly refused a non-owner's in-place edit of D0234, so the corrections became D0330. D0329 gives it one without loosening the rule - a re-binding that lands with its text vouches for that text; a landing commit whose text also differs still fails."; }
    verification recordCorrectionsImplementGate : Test { :>> id = "e3ca7122-f966-42a9-b509-d2c2ce431e3e"; :>> title = "Sprint 567 implement gate"; :>> createdAt = "2026-09-05"; :>> createdBy = "claudeOpus5"; :>> method = VerificationMethod::test; :>> procedureText = "RAN: keel accept d0234 --rebind under the standing words (R2 at f84ff68); keel guard acceptance-binds-to-text . before the guard change FAIL (1 violation, d0234), after it PASS with the pending warning; validate on a tree holding .engine and no .tracking now says .tracking/; cargo test --test acceptance_binds_to_text 1 passed with the third phase; clippy -D warnings clean; the full suite in the background to completion (receipt on the DoD result)."; }
    verification recordCorrectionsReviewGate : Test { :>> id = "be75e7c4-6cb4-47d4-9f03-de102eb8a8d4"; :>> title = "Sprint 567 review gate — three passes per D0172"; :>> createdAt = "2026-09-05"; :>> createdBy = "claudeOpus5"; :>> method = VerificationMethod::inspect; :>> procedureText = "THREE PASSES. (1) ARE THE CORRECTED CLAIMS CHECKABLE: each names its measurement - the three single-project behaviours by mechanism, the repository count by machine, the short-circuit by code path, the suite tests by name, the bump by issue number. (2) DOES EVERY EVIDENCE REFERENCE IN SPRINT469 RESOLVE: the scratch commits are gone from the receipt; the remaining references are test names in the tree and f356770, which resolves. (3) IS THE GUARD WEAKER: no - drift with no landing commit or with a differing landing text still fails; the arming test covers both the pending and the landed case."; }
    verification recordCorrectionsCloseOutGate : Test { :>> id = "54f42c41-b11b-4912-9a18-3f26bd5538a9"; :>> title = "Sprint 567 closeOut gate (autonomous, D0049)"; :>> createdAt = "2026-09-05"; :>> createdBy = "claudeOpus5"; :>> method = VerificationMethod::inspect; :>> procedureText = "CLOSED. D0329 accepted under standing consent; issue283 resolved by computation."; }
    verification recordCorrectionsRetroGate : Test { :>> id = "2e8407b4-1495-4bf8-8a98-2ad6584f2cf4"; :>> title = "Sprint 567 retro gate (autonomous, D0049)"; :>> createdAt = "2026-09-05"; :>> createdBy = "claudeOpus5"; :>> method = VerificationMethod::analyze; :>> procedureText = "no new item - already tracked: issue283 is resolved by dcPanelRecordCorrections and d0234's stated limits (a staged file belonging to no project, decision numbers colliding in the model) stand as recorded; the facts-pedant lens that found these six is the adversarial-panel-review process. The lesson: a claim in a Decision is checkable only if it names its measurement - both, eight, none were counts nobody had made."; }
}
