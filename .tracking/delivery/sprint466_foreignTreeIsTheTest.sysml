// ProjectDeliveryS466 — Sprint 466: adoption stops being a habit and becomes a gate, and the gate says out loud what it cannot see. EXECUTE. 3 pts.
package ProjectDeliveryS466 {
    private import EngineElement::*;
    private import EngineWork::*;
    private import EngineVerification::*;
    private import EngineRelationships::*;

    #CharteredBy dependency from foreignTreeIsTheTestStory to d0231;

    part foreignTreeIsTheTestStory : Story {
        :>> id = "e8486bc5-3bed-49c9-8843-1ae329b74663";
        :>> title = "Sprint 466: the check that passed everything, and what that was worth (3 pts)";
        :>> createdAt = "2026-08-25"; :>> createdBy = "claudeFable5"; :>> kind = WorkKind::code; :>> priority = WorkPriority::p0; :>> owner = "claudeFable5"; :>> estimatedPoints = 3;
    }

    action def DeliveryRunS466 {
        action storyForeignTreeIsTheTest;
        verification storyForeignTreeIsTheTestDoD : Test { :>> id = "cc889227-0a8d-4152-927e-fc4d4a58a76c"; :>> method = VerificationMethod::test; :>> procedureText = "DELIVERED: dcForeignTreeIsTheTest (resolves issue264; D0231). The human asked which of three things was losing us rigor: verification not strong enough, the wrong measures, or the reporting from verification being inaccurate. MEASURED rather than opined: the first is the LEAST supported - 51 guards, 42 hard-blocking, 99 percent of live requirements examined and 91 percent exercised, and no recent defect traceable to a lax threshold. But 39 of 51 guards read only the authored model, 11 cross some boundary, and ZERO read another project's tree, while 11 of the last 20 issues were discovered in the field and cluster at exactly that boundary. keel adoption-check now scaffolds a fresh project and gates that FOREIGN tree in both directions per unit - clean WITHOUT it, because a control must not fire on a project that never adopted it, and clean WITH it freshly imported, because a unit must carry everything it references - as a CI gate on every push, 25 units in 16 seconds on the runner. IT REPORTED 25 OF 25 CLEAN ON ITS FIRST RUN, which is the shape of a control aimed at nothing, so it was made PROVEN ABLE TO FAIL: a companion test mutilates a bundle exactly as the engine really did before D0222 and asserts the foreign gate goes red naming process-skill. AND IT CATCHES LESS THAN I FIRST CLAIMED - I wrote five defects, testing showed two - because the fixture is a current keel scaffold, which is keel adopting keel rather than a real adopter. That gap is issue265 with a resolver, and a second test fails the build if the stated scope is ever quietly deleted."; }
        // RAN: keel adoption-check . -> 25/25; cargo test --workspace -> 269+9+2+1+32 passed; keel validate . -> 518 clean; keel guard -> ALL PASS (51)
        part storyForeignTreeIsTheTestDoDR1 : TestResult { :>> id = "e738fbac-0a6b-43f5-a7f1-0d8d9f174324"; :>> outcome = VerdictKind::pass; :>> judgedAgainst = "3b2bb49"; :>> judgedAt = "2026-08-25"; :>> judgedBy = "claudeFable5"; }
        // RAN: keel adoption-check . -> 25/25; cargo test --workspace -> 269+9+2+1+32 passed; keel validate . -> 518 clean; keel guard -> ALL PASS (51)
        part storyForeignTreeIsTheTestDoDR2 : TestResult { :>> id = "a105f59e-a6df-4a7a-8100-d29e954607e3"; :>> outcome = VerdictKind::pass; :>> judgedAgainst = "3b2bb4912509f6a97b6465c992826831f6ffc3a7"; :>> judgedAt = "2026-08-25"; :>> judgedBy = "claudeFable5"; }
    }

    verification foreignTreeIsTheTestRefineGate : Test { :>> id = "091b3da4-0898-4c60-b61b-6cb96f62d3c5"; :>> title = "Sprint 466 refine gate (DoR)"; :>> createdAt = "2026-08-25"; :>> createdBy = "claudeFable5"; :>> method = VerificationMethod::inspect; :>> procedureText = "DoR. Resolves issue264, raised by the human's question about where rigor is being lost. Scope: measure which of three hypotheses the evidence supports, then build the highest-yield control the measurement points at, then bound its claim honestly. 3 points."; }
    part foreignTreeIsTheTestRefineGateR1 : TestResult { :>> id = "9fcca2db-77e7-4a6e-91ca-b423c49bcbad"; :>> outcome = VerdictKind::pass; :>> judgedAgainst = "3b2bb49"; :>> judgedAt = "2026-08-25"; :>> judgedBy = "claudeFable5"; }
    part foreignTreeIsTheTestRefineGateR2 : TestResult { :>> id = "205e9849-1856-4ab6-b1b5-42058a036ea8"; :>> outcome = VerdictKind::pass; :>> judgedAgainst = "3b2bb4912509f6a97b6465c992826831f6ffc3a7"; :>> judgedAt = "2026-08-25"; :>> judgedBy = "claudeFable5"; }
    verification foreignTreeIsTheTestStandupGate : Test { :>> id = "5d891e09-3f38-4d12-bc2b-af6b919dde30"; :>> title = "Sprint 466 standup gate"; :>> createdAt = "2026-08-25"; :>> createdBy = "claudeFable5"; :>> method = VerificationMethod::inspect; :>> procedureText = "Approach: measure before proposing - classify guards by what they READ and issues by how they were FOUND, rather than reasoning about which hypothesis feels right. Build the check to drive the real CLI, not internal functions, since an adopter runs commands. Share restore_dst with import instead of reimplementing the path mapping, because two copies of that mapping is the same-fact-in-two-places class that has cost this project more than any other. .github/workflows and guards are keystone-locked, so D0231 co-commits as a SafetyChange. No blockers."; }
    part foreignTreeIsTheTestStandupGateR1 : TestResult { :>> id = "d5262270-7191-4973-8874-4e5907d26670"; :>> outcome = VerdictKind::pass; :>> judgedAgainst = "3b2bb49"; :>> judgedAt = "2026-08-25"; :>> judgedBy = "claudeFable5"; }
    part foreignTreeIsTheTestStandupGateR2 : TestResult { :>> id = "3cfb86df-df3b-42f0-8507-c66e45d8175b"; :>> outcome = VerdictKind::pass; :>> judgedAgainst = "3b2bb4912509f6a97b6465c992826831f6ffc3a7"; :>> judgedAt = "2026-08-25"; :>> judgedBy = "claudeFable5"; }
    verification foreignTreeIsTheTestImplementGate : Test { :>> id = "91e2721a-ec88-4b8d-9fe1-c07eefae5f33"; :>> title = "Sprint 466 implement gate"; :>> createdAt = "2026-08-25"; :>> createdBy = "claudeFable5"; :>> method = VerificationMethod::test; :>> procedureText = "Verified in BOTH directions, and the negative direction is the one that matters. POSITIVE: 25 of 25 units clean locally and in CI, the step's own log quoted, 16 seconds on the runner against 3 minutes on Windows. NEGATIVE: a bundle mutilated the way the engine really was before D0222 - process and SKILL.md travel, the binding declaration stays home - turns the foreign gate RED with process-skill named, asserted by an automated test rather than a one-off probe. SCOPE, tested not assumed: the fixture carries .engine/rules/guard-constraints.sysml, so issue263's symbol RESOLVES there and that defect is invisible; every fixture process carries the current convention, so issue259 is invisible too. validate 518 + all 51 guards + clippy 0 errors + 269 + 9 + 2 + 1 + 32 tests."; }
    // RAN: cargo test --test adoption_check_can_fail -> 2 passed; keel adoption-check . --unit intake -> clean in 20s; gh run view 32851429166 --log -> the CI step ran 25 units in 16s
    part foreignTreeIsTheTestImplementGateR1 : TestResult { :>> id = "5e18a4d9-a921-47d2-97d8-9a4bf66608af"; :>> outcome = VerdictKind::pass; :>> judgedAgainst = "3b2bb49"; :>> judgedAt = "2026-08-25"; :>> judgedBy = "claudeFable5"; }
    // RAN: cargo test --test adoption_check_can_fail -> 2 passed; keel adoption-check . --unit intake -> clean in 20s; gh run view 32851429166 --log -> the CI step ran 25 units in 16s
    part foreignTreeIsTheTestImplementGateR2 : TestResult { :>> id = "4465d82f-4f21-41c5-ae8a-933e90058a5b"; :>> outcome = VerdictKind::pass; :>> judgedAgainst = "3b2bb4912509f6a97b6465c992826831f6ffc3a7"; :>> judgedAt = "2026-08-25"; :>> judgedBy = "claudeFable5"; }
    verification foreignTreeIsTheTestReviewGate : Test { :>> id = "391fc04f-42aa-4202-8464-4f570b872311"; :>> title = "Sprint 466 review gate — three passes per D0172"; :>> createdAt = "2026-08-25"; :>> createdBy = "claudeFable5"; :>> method = VerificationMethod::inspect; :>> procedureText = "PASS 1, CLAIMS: every number is a quoted read-back - the guard-target census, the discoveredInField rate, the 3.9 percent fail rate over 5120 results, the CI timing. The ONE claim I made without testing it - that this would have caught five recent defects - was wrong, and testing it is what produced the honest two. PASS 2, BOUNDARY: (i) the fixture is keel adopting keel, so an older vintage is unrepresented and two real defects are invisible - issue265; (ii) the WITHOUT direction can only fail if something in the fixture references the stripped unit, which no current unit does, so that half is presently unexercised by any real case and is proven only by construction; (iii) the check drives the CLI by re-invoking the binary, so it tests the binary it was built from and could never catch a defect that is identical in both; (iv) three minutes locally is slow enough that someone will want to skip it. PASS 3, OWN DIFF: the sprint's real finding is about my own reporting. A brand-new check reporting 25 of 25 clean was the moment to over-claim, and I nearly did - the two tests and the stated scope exist because the first draft of this Decision asserted five defects covered. WHAT A REVIEWER SHOULD ATTACK: whether a gate whose failure mode is presently unreachable in one of its two directions is a gate or a decoration."; }
    part foreignTreeIsTheTestReviewGateR1 : TestResult { :>> id = "72180e6f-2140-47d9-ab59-76c8bc824d21"; :>> outcome = VerdictKind::pass; :>> judgedAgainst = "3b2bb49"; :>> judgedAt = "2026-08-25"; :>> judgedBy = "claudeFable5"; }
    part foreignTreeIsTheTestReviewGateR2 : TestResult { :>> id = "dbab8fe3-c677-48b7-b3de-68d2278924fd"; :>> outcome = VerdictKind::pass; :>> judgedAgainst = "3b2bb4912509f6a97b6465c992826831f6ffc3a7"; :>> judgedAt = "2026-08-25"; :>> judgedBy = "claudeFable5"; }
    verification foreignTreeIsTheTestCloseOutGate : Test { :>> id = "8ebed432-e48f-4c53-9cec-9a1c87817cb4"; :>> title = "Sprint 466 closeOut gate (autonomous, D0049)"; :>> createdAt = "2026-08-25"; :>> createdBy = "claudeFable5"; :>> method = VerificationMethod::inspect; :>> procedureText = "Autonomous closeOut (D0049). issue264 resolved; issue265 records the fixture's vintage gap with a resolver rather than leaving it implied. Adoption is a control now instead of something done when someone remembers, which is D0047 applied to a finding about the controls themselves. validate + all 51 guards + check-engine + rules green at 3b2bb49."; }
    part foreignTreeIsTheTestCloseOutGateR1 : TestResult { :>> id = "c49a4c91-1aff-48d3-a67a-29dff16be876"; :>> outcome = VerdictKind::pass; :>> judgedAgainst = "3b2bb49"; :>> judgedAt = "2026-08-25"; :>> judgedBy = "claudeFable5"; }
    part foreignTreeIsTheTestCloseOutGateR2 : TestResult { :>> id = "33438e91-3fd3-4630-a529-8f6a02d1869a"; :>> outcome = VerdictKind::pass; :>> judgedAgainst = "3b2bb4912509f6a97b6465c992826831f6ffc3a7"; :>> judgedAt = "2026-08-25"; :>> judgedBy = "claudeFable5"; }
    verification foreignTreeIsTheTestRetroGate : Test { :>> id = "0d880a93-450a-4181-b62c-0d4ead873eb2"; :>> title = "Sprint 466 retro gate (autonomous, D0049)"; :>> createdAt = "2026-08-25"; :>> createdBy = "claudeFable5"; :>> method = VerificationMethod::analyze; :>> procedureText = "Autonomous retro (D0049). AVOIDABLE-ISSUE SCAN under rcRecurrence: (1) THE FINDING, and it is about attestation rather than code: the first draft of this Decision claimed five defects covered, from reasoning alone. Testing each showed two. The claim was not careless - it was PLAUSIBLE, which is worse, because plausible claims survive review. The generalisable rule: a claim of the form 'this would have caught X' must be tested against X, and X is usually still reproducible. (2) A new check that passes everything on its first run should be treated as evidence about the CHECK, not about the tree - here it prompted the can-fail test, and that instinct should be a step rather than a mood. (3) The check's own two-direction design came from asking which way the historical failures ran, rather than from what was easy to implement; one direction would have looked complete. WELL: measuring before proposing produced a different answer than my prior - I would have said the measures were too weak, and the evidence says they are strong and pointed inward. Estimate 3 pts, delivered 3."; }
    part foreignTreeIsTheTestRetroGateR1 : TestResult { :>> id = "d489b7ed-2702-4a48-b8a1-ba60be4b75ee"; :>> outcome = VerdictKind::pass; :>> judgedAgainst = "3b2bb49"; :>> judgedAt = "2026-08-25"; :>> judgedBy = "claudeFable5"; }
    part foreignTreeIsTheTestRetroGateR2 : TestResult { :>> id = "ab3c0edd-b1f1-4a26-b56e-0138aa79fadf"; :>> outcome = VerdictKind::pass; :>> judgedAgainst = "3b2bb4912509f6a97b6465c992826831f6ffc3a7"; :>> judgedAt = "2026-08-25"; :>> judgedBy = "claudeFable5"; }
}
