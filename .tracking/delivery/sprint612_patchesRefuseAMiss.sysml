// ProjectDeliveryS612 — Sprint 612: Sprint 612 makes a missed patch a failure (dcPatchesFailWhenTheyMiss, resolves issue398) under D0386: scripts/textpatch.py is the one shape a text patch takes - it refuses an absent or ambiguous anchor, writes nothing on refusal, and names append as its own operation - with its own probe, and CLAUDE.md section 6 names it beside the Write-tool rule.. EXECUTE. 2 pts.
package ProjectDeliveryS612 {
    private import EngineElement::*;
    private import EngineWork::*;
    private import EngineVerification::*;
    private import EngineRelationships::*;

    #CharteredBy dependency from patchesRefuseAMissStory to d0386;

    part patchesRefuseAMissStory : Story {
        :>> id = "9bff12dc-00f4-4c27-b869-6e2a18d08cfd";
        :>> title = "Sprint 612: Sprint 612 makes a missed patch a failure (dcPatchesFailWhenTheyMiss, resolves issue398) under D0386: scripts/textpatch.py is the one shape a text patch takes - it refuses an absent or ambiguous anchor, writes nothing on refusal, and names append as its own operation - with its own probe, and CLAUDE.md section 6 names it beside the Write-tool rule. (2 pts)";
        :>> createdAt = "2026-09-08"; :>> createdBy = "claudeOpus5"; :>> kind = WorkKind::code; :>> priority = WorkPriority::p0; :>> owner = "claudeOpus5"; :>> estimatedPoints = 2;
    }

    action def DeliveryRunS612 {
        action storyPatchesRefuseAMiss;
        verification storyPatchesRefuseAMissDoD : Test { :>> id = "355796e1-1a6a-4553-9ca0-b0192884c856"; :>> method = VerificationMethod::test; :>> procedureText = "DONE MEANS: a patch that cannot find its anchor fails, and never lands somewhere it does no work. Resolves issue398: a patch adding a computation section to the facts script fell through to an append when its anchor did not match, putting the section AFTER the serialisation - so the script ran clean, exited zero, wrote its file and silently omitted everything the section computed. DO: make the assertion the only available shape rather than a convention - a patch asserts its anchor's presence and its count, exits non-zero when either is wrong, and where an end-of-file addition is genuinely intended it is stated explicitly rather than reached by failure. Decide whether this belongs as a shared helper these scripts import or as a documented rule with an example, and record which and why. VERIFY: a patch whose anchor is absent exits non-zero and writes nothing, shown by constructing that case; a patch whose anchor appears twice refuses rather than picking one; and a deliberate append is distinguishable in the script's own text from an accidental one."; }
        // RAN: scripts/textpatch.py --probe 11 pass; CLAUDE.md section 6 names it; D0386 records helper-named-by-rule; instruments-declared clean
        part storyPatchesRefuseAMissDoDR1 : TestResult { :>> id = "a5994013-fc36-4eac-92e7-c2ab36b1c875"; :>> outcome = VerdictKind::pass; :>> judgedAgainst = "4b85cde944f3034fdc75478c78a1ff8f7dfe4ff4"; :>> judgedAt = "2026-09-08"; :>> judgedBy = "claudeOpus5"; }
    }

    verification patchesRefuseAMissRefineGate : Test { :>> id = "dfb182fa-848e-4f22-b8e3-0a9d6d040898"; :>> title = "Sprint 612 refine gate (DoR)"; :>> createdAt = "2026-09-08"; :>> createdBy = "claudeOpus5"; :>> method = VerificationMethod::inspect; :>> procedureText = "Scope: scripts/textpatch.py (module + CLI + --probe), CLAUDE.md section 6 rule line, D0386 recording the helper-named-by-rule choice. Out of scope: a hook that detects a bare str.replace in a heredoc (stated in D0386 as not pretended), and running python probes in CI (no python check runs there today; a retro item). Estimate 2 points: one module with a probe, one doc line, one Decision. DoR: points set, charter d0386, scope clear, no blocking dependency, DoD authored."; }
    // RAN: DoR inspected: 2 points, charter d0386, scope in the refine text, DoD authored, no blocking dependency
    part patchesRefuseAMissRefineGateR1 : TestResult { :>> id = "e9493e64-e5b3-4a58-81fa-fe3cd2dbb2e4"; :>> outcome = VerdictKind::pass; :>> judgedAgainst = "4b85cde944f3034fdc75478c78a1ff8f7dfe4ff4"; :>> judgedAt = "2026-09-08"; :>> judgedBy = "claudeOpus5"; }
    verification patchesRefuseAMissStandupGate : Test { :>> id = "ae9d48e3-9bb1-4626-8ba4-a085ed3d4237"; :>> title = "Sprint 612 standup gate"; :>> createdAt = "2026-09-08"; :>> createdBy = "claudeOpus5"; :>> method = VerificationMethod::inspect; :>> procedureText = "Plan: (1) textpatch.py with replace_once / insert_after / insert_before / append, refusal on 0 or >1 occurrences via SystemExit 1, temp-file-then-rename so a refusal leaves the target untouched, newline-preserving reads and writes; (2) --probe with the issue398 case (absent anchor: refused, nothing written, nothing appended), the ambiguous case, the empty anchor, CRLF preservation; (3) D0386; (4) the CLAUDE.md line, applied THROUGH the helper as its first real use; (5) instruments-declared clean over the new script; gates."; }
    // RAN: plan of five steps recorded in the standup text; all five executed in this commit
    part patchesRefuseAMissStandupGateR1 : TestResult { :>> id = "a7e8a1d7-069d-4dcf-a79d-e01f7be1a67a"; :>> outcome = VerdictKind::pass; :>> judgedAgainst = "4b85cde944f3034fdc75478c78a1ff8f7dfe4ff4"; :>> judgedAt = "2026-09-08"; :>> judgedBy = "claudeOpus5"; }
    verification patchesRefuseAMissImplementGate : Test { :>> id = "e9cf7723-6646-46c9-bf11-f80bae36f022"; :>> title = "Sprint 612 implement gate"; :>> createdAt = "2026-09-08"; :>> createdBy = "claudeOpus5"; :>> method = VerificationMethod::test; :>> procedureText = "RAN: python scripts/textpatch.py --probe (11 cases); the CLAUDE.md insertion through insert_after with git diff --stat showing 6 insertions and no line-ending churn; keel guard instruments-declared . ; keel gate --fast; keel guard."; }
    // RAN: python scripts/textpatch.py --probe: 11 pass 0 failure(s) exit 0, incl. absent anchor refused with file unchanged and nothing appended, duplicate anchor refused, empty anchor refused, CRLF preserved; CLAUDE.md line inserted through insert_after, git diff --stat CLAUDE.md = 6 insertions; keel guard instruments-declared . PASS 19 scanned 0 violations; keel gate --fast clean
    part patchesRefuseAMissImplementGateR1 : TestResult { :>> id = "9dde33a5-347b-4462-8958-ea696f6bf112"; :>> outcome = VerdictKind::pass; :>> judgedAgainst = "4b85cde944f3034fdc75478c78a1ff8f7dfe4ff4"; :>> judgedAt = "2026-09-08"; :>> judgedBy = "claudeOpus5"; }
    verification patchesRefuseAMissReviewGate : Test { :>> id = "87d89c7e-97e2-40b2-af3d-c1d9b51e70a3"; :>> title = "Sprint 612 review gate — three passes per D0172"; :>> createdAt = "2026-09-08"; :>> createdBy = "claudeOpus5"; :>> method = VerificationMethod::inspect; :>> procedureText = "Reviewed against the DoD: the absent-anchor case is constructed in the probe and reads refused / unchanged / nothing appended; the twice-occurring anchor is refused with the count named; append is a separately named function and CLI verb, so a deliberate end-of-file addition reads as one in the caller's text; the helper-or-rule choice is D0386 with its reason (each fails alone in a way the other covers)."; }
    // RAN: reviewed against the DoD: absent anchor constructed in the probe and read refused/unchanged/not appended; twice-occurring anchor refused naming the count 2; append is a named function and CLI verb; helper-or-rule recorded as D0386 with the reason
    part patchesRefuseAMissReviewGateR1 : TestResult { :>> id = "c5b539a7-158d-4eab-8ff6-0f85505ecb4f"; :>> outcome = VerdictKind::pass; :>> judgedAgainst = "4b85cde944f3034fdc75478c78a1ff8f7dfe4ff4"; :>> judgedAt = "2026-09-08"; :>> judgedBy = "claudeOpus5"; }
    verification patchesRefuseAMissCloseOutGate : Test { :>> id = "61e65b0f-c5aa-4d1b-8e66-fb191afbf1c2"; :>> title = "Sprint 612 closeOut gate (autonomous, D0049)"; :>> createdAt = "2026-09-08"; :>> createdBy = "claudeOpus5"; :>> method = VerificationMethod::inspect; :>> procedureText = "Sprint 612 closes when dcPatchesFailWhenTheyMissDoD carries a pass at the commit that carries the helper, the probe, the Decision and the CLAUDE.md line, and issue398 leaves keel show open-issues."; }
    // RAN: DoD pass recorded on storyPatchesRefuseAMissDoD and dcPatchesFailWhenTheyMissDoD at this SHA; issue398 resolution read back from keel show open-issues after the record
    part patchesRefuseAMissCloseOutGateR1 : TestResult { :>> id = "234509f2-0e29-449a-9a63-76e356b446b2"; :>> outcome = VerdictKind::pass; :>> judgedAgainst = "4b85cde944f3034fdc75478c78a1ff8f7dfe4ff4"; :>> judgedAt = "2026-09-08"; :>> judgedBy = "claudeOpus5"; }
    verification patchesRefuseAMissRetroGate : Test { :>> id = "d1292f30-1cb4-4ab3-aa26-aeac7ca1b597"; :>> title = "Sprint 612 retro gate (autonomous, D0049)"; :>> createdAt = "2026-09-08"; :>> createdBy = "claudeOpus5"; :>> method = VerificationMethod::analyze; :>> procedureText = "Retro held; avoidable-issue scan: one finding - the helper's probe, like check_templates --self-test, runs only by hand because no python check runs in CI, so a regression in either is found by the next session that happens to run it; recorded as backlog item dcScriptProbesRunInCi. Process improvement: the CLAUDE.md line is what makes the helper findable; the four scratch patches of 2026-09-08 (three asserting, one bare) are the evidence a rule alone lapses."; }
    // RAN: retro held; one finding recorded as backlog item dcScriptProbesRunInCi in this commit; the retro text names it
    part patchesRefuseAMissRetroGateR1 : TestResult { :>> id = "09fb7aac-b0c6-449a-923f-bf653b2ab5ab"; :>> outcome = VerdictKind::pass; :>> judgedAgainst = "4b85cde944f3034fdc75478c78a1ff8f7dfe4ff4"; :>> judgedAt = "2026-09-08"; :>> judgedBy = "claudeOpus5"; }
}
