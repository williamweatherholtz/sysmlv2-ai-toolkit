// ProjectDeliveryS647 — Sprint 647: every refusal is a ledger fact, and the census's human-binding refusals are dissolved to WARN or struck with their reason. EXECUTE. 3 pts.
package ProjectDeliveryS647 {
    private import EngineElement::*;
    private import EngineWork::*;
    private import EngineVerification::*;
    private import EngineRelationships::*;

    #CharteredBy dependency from refusalsAreLedgerFactsStory to d0424;
    #CharteredBy dependency from refusalsAreLedgerFactsStory to d0426;
    #CharteredBy dependency from refusalsAreLedgerFactsStory to d0423;

    part refusalsAreLedgerFactsStory : Story {
        :>> id = "5d324361-e98c-4adf-ac51-45ede702bc7c";
        :>> title = "Sprint 647: every refusal is a ledger fact, and the census's human-binding refusals are dissolved to WARN or struck with their reason (3 pts)";
        :>> createdAt = "2026-09-10"; :>> createdBy = "claudeOpus5"; :>> kind = WorkKind::code; :>> priority = WorkPriority::p0; :>> owner = "claudeOpus5"; :>> estimatedPoints = 3;
    }

    action def DeliveryRunS647 {
        action storyRefusalsAreLedgerFacts;
        verification storyRefusalsAreLedgerFactsDoD : Test { :>> id = "29dfb35b-4b5f-441c-a424-3f7511de42d5"; :>> method = VerificationMethod::test; :>> procedureText = "DELIVERED BACKLOG ITEMS: dcRefusalIsALedgerFact (resolves issue445, issue446) and dcUnsignedTapIsRecordedWithAWarn (resolves issue447). Done means: the fire-ledger line carries the EMITTED verdict, the refusing control and the actorKind it fell on; a write-path refusal writes a refused line; the commit tier's three processes each write a commit-gate-<tier> line; keel enforcement-report reads them back as refusals per (event, control, actorKind); an unsigned console/deck tap records with a WARN line instead of a 401; the short-words and read-back checks on a delegated acceptance record with WARN (D0423); the gesture-word-only refusal is kept and recorded as D0427 (proposed); the census strikes (acceptance-binds-to-text, no-quote, enroll wrong code) are closed out in issue447 with the reason each binds the agent, not the human. Verified how: the verifier subagent's receipt (D0425) - the touched test binaries, cargo test --lib, validate, check-engine, guard --no-receipt, enforcement-report, open-issues - not the primary's description. The DoD's own VERIFY clause naming a refusal of `--words A` is superseded by D0423: A now records with WARN, and the ledger-tested refusal is the no-quote path."; }
        // RAN: verifier receipt (D0425): lib 454/0 + parser 32/0; device_bound_taps 1/0; hook_and_push_controls_actually_fire 8/0; accept_honours_delegation 4/0; reject_has_a_cli_path 4/0; gesture_citation_is_the_commands 2/0; acceptance_binds_to_text 1/0; validate 734 clean; check-engine clean; guard ALL PASS (66 warnings/8 guards); enforcement-report refusals rows + commit-gate-{validate,guard,check-engine} present; DISCREPANCIES none
        part storyRefusalsAreLedgerFactsDoDR2 : TestResult { :>> id = "c37ac0b7-2947-488c-bbc2-341de496c3af"; :>> outcome = VerdictKind::pass; :>> judgedAgainst = "94a7f0b60cabb308eb971c0fb17e101e66756c6f"; :>> judgedAt = "2026-09-10"; :>> judgedBy = "claudeOpus5"; }
    }

    verification refusalsAreLedgerFactsRefineGate : Test { :>> id = "2653dab0-ae9d-4a4a-b9aa-00f75281c121"; :>> title = "Sprint 647 refine gate (DoR)"; :>> createdAt = "2026-09-10"; :>> createdBy = "claudeOpus5"; :>> method = VerificationMethod::inspect; :>> procedureText = "DoR: two backlog items, both chartered by accepted Decisions (D0424 for the ledger fact, D0426 for the dissolution), no blocking dependency; 3 pts - the ledger change touches main.rs, pm.rs and serve.rs plus six test binaries."; }
    part refusalsAreLedgerFactsRefineGateR1 : TestResult { :>> id = "40fe2f52-604d-4c6c-9fe9-471eb434c910"; :>> outcome = VerdictKind::pass; :>> judgedAgainst = "94a7f0b60cabb308eb971c0fb17e101e66756c6f"; :>> judgedAt = "2026-09-10"; :>> judgedBy = "claudeOpus5"; }
    verification refusalsAreLedgerFactsStandupGate : Test { :>> id = "f3c0ccb7-36b8-4c79-98f3-9c49b18b5a05"; :>> title = "Sprint 647 standup gate"; :>> createdAt = "2026-09-10"; :>> createdBy = "claudeOpus5"; :>> method = VerificationMethod::inspect; :>> procedureText = "Blocker at standup: none. The one open question - whether the gesture-word-only check meets D0426's criterion - was answered by reading whose act it falls on (the agent's), and recorded as D0427 rather than argued in prose."; }
    part refusalsAreLedgerFactsStandupGateR1 : TestResult { :>> id = "3007d130-0724-4a6f-9526-0ad86942395b"; :>> outcome = VerdictKind::pass; :>> judgedAgainst = "94a7f0b60cabb308eb971c0fb17e101e66756c6f"; :>> judgedAt = "2026-09-10"; :>> judgedBy = "claudeOpus5"; }
    verification refusalsAreLedgerFactsImplementGate : Test { :>> id = "f419286f-c3b1-4b4c-b53a-c7620b888b77"; :>> title = "Sprint 647 implement gate"; :>> createdAt = "2026-09-10"; :>> createdBy = "claudeOpus5"; :>> method = VerificationMethod::test; :>> procedureText = "Implemented: ledger_gate / ledger_refused / hook_refuse in main.rs; TapReceipt replacing require_device across six serve.rs routes; enforcement-report refusals rows in pm.rs; D0423 WARN paths in accept/reject; tests device_bound_taps, hook_and_push_controls_actually_fire (the_commit_tier_leaves_a_commit_gate_line), accept_honours_delegation, reject_has_a_cli_path, pm::refusals_are_read_back_per_event_control_and_actor_kind."; }
    // RAN: verifier receipt (D0425): lib 454/0 + parser 32/0; device_bound_taps 1/0; hook_and_push_controls_actually_fire 8/0; accept_honours_delegation 4/0; reject_has_a_cli_path 4/0; gesture_citation_is_the_commands 2/0; acceptance_binds_to_text 1/0; validate 734 clean; check-engine clean; guard ALL PASS (66 warnings/8 guards); enforcement-report refusals rows + commit-gate-{validate,guard,check-engine} present; DISCREPANCIES none
    part refusalsAreLedgerFactsImplementGateR2 : TestResult { :>> id = "868cd0eb-2510-4df9-9316-454a2f72d1d2"; :>> outcome = VerdictKind::pass; :>> judgedAgainst = "94a7f0b60cabb308eb971c0fb17e101e66756c6f"; :>> judgedAt = "2026-09-10"; :>> judgedBy = "claudeOpus5"; }
    verification refusalsAreLedgerFactsReviewGate : Test { :>> id = "2e3f2f11-cbcc-4202-8ff5-e028a066ca96"; :>> title = "Sprint 647 review gate — three passes per D0172"; :>> createdAt = "2026-09-10"; :>> createdBy = "claudeOpus5"; :>> method = VerificationMethod::inspect; :>> procedureText = "Three passes per D0172: (1) correctness - the verifier's receipt for every touched binary and the three model gates; (2) the contract - no prose state, every refusal attributable, the docs synced in the same commit (CLAUDE.md acceptance paragraph, fire-ledger paragraph, D0425 roles); (3) the residual - a line from before 2026-09-10 is unrecorded, so the census has no history yet; dcControlCensusByActorKind is the lens that reads the new fields forward."; }
    part refusalsAreLedgerFactsReviewGateR1 : TestResult { :>> id = "03657de4-64b2-49f6-970e-5599a473b70e"; :>> outcome = VerdictKind::pass; :>> judgedAgainst = "94a7f0b60cabb308eb971c0fb17e101e66756c6f"; :>> judgedAt = "2026-09-10"; :>> judgedBy = "claudeOpus5"; }
    verification refusalsAreLedgerFactsCloseOutGate : Test { :>> id = "231e1a71-fc71-4361-ab0b-3edd736d2ca3"; :>> title = "Sprint 647 closeOut gate (autonomous, D0049)"; :>> createdAt = "2026-09-10"; :>> createdBy = "claudeOpus5"; :>> method = VerificationMethod::inspect; :>> procedureText = "Closed out autonomously (D0049): recorded by the recorder subagent from the verifier's receipt (D0425); the result evidence names the receipt's commands."; }
    part refusalsAreLedgerFactsCloseOutGateR1 : TestResult { :>> id = "105f3277-60f3-4125-851b-9e90a2cdedd1"; :>> outcome = VerdictKind::pass; :>> judgedAgainst = "94a7f0b60cabb308eb971c0fb17e101e66756c6f"; :>> judgedAt = "2026-09-10"; :>> judgedBy = "claudeOpus5"; }
    verification refusalsAreLedgerFactsRetroGate : Test { :>> id = "01959217-dc93-4c29-8d33-d5f7286d5151"; :>> title = "Sprint 647 retro gate (autonomous, D0049)"; :>> createdAt = "2026-09-10"; :>> createdBy = "claudeOpus5"; :>> method = VerificationMethod::analyze; :>> procedureText = "Avoidable-issue scan: Retro finding: the D0426 census needed a criterion (whose act does the refusal fall on) before any control could be classified, and the criterion was only stated in D0426's text - D0427 is its first application. Already tracked: dcControlCensusByActorKind (the computed lens), so no new item."; }
    part refusalsAreLedgerFactsRetroGateR2 : TestResult { :>> id = "5893affa-9305-4c5b-93d0-ae55e25e7731"; :>> outcome = VerdictKind::pass; :>> judgedAgainst = "94a7f0b60cabb308eb971c0fb17e101e66756c6f"; :>> judgedAt = "2026-09-10"; :>> judgedBy = "claudeOpus5"; }
    // RAN: scan retro findings - no avoidable issues identified (dcControlCensusByActorKind already tracked; reviewed dcRefusalIsALedgerFact and dcUnsignedTapIsRecordedWithAWarn deliverables)
}
