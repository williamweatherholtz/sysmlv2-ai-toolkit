// ProjectDeliveryS494 — Sprint 494: the kickoff path proven end to end on a throwaway project. EXECUTE. 5 pts.
package ProjectDeliveryS494 {
    private import EngineElement::*;
    private import EngineWork::*;
    private import EngineVerification::*;
    private import EngineRelationships::*;

    #CharteredBy dependency from kickoffReadyStory to d0250;

    part kickoffReadyStory : Story {
        :>> id = "29f06184-da85-4f10-9c8d-503a8c840d49";
        :>> title = "Sprint 494: kickoff-ready - the demo ran the whole path and found one more defect on the way (5 pts)";
        :>> createdAt = "2026-08-29"; :>> createdBy = "claudeOpus5"; :>> kind = WorkKind::code; :>> priority = WorkPriority::p0; :>> owner = "claudeOpus5"; :>> estimatedPoints = 5;
    }

    action def DeliveryRunS494 {
        action storyKickoffReady;
        verification storyKickoffReadyDoD : Test { :>> id = "392a3ec2-667d-4901-b844-ff9597faa8cf"; :>> method = VerificationMethod::test; :>> procedureText = "Discharges dcKickoffReady (increment 5) and RESOLVES issue309. DONE, each proven by running it: (1) se-templates' exec-summary kit became a UNIT (process definition + engine skill + registry + extras; D0238 there) and is PUBLISHED to the real library alongside decision-channel, intake and control-propriety; (2) release v0.3.1 tagged, CI green, three platform assets published, their SHA-256s committed to keel-wrapper.toml; (3) the THROWAWAY DEMO ran the whole path - keel init --profile strict, sh keelw version offline from the seeded cache, git first push (the issue306 fix proving itself), library imports, sync-claude, green gate, pushed - and then, with an EMPTIED cache, keelw fetched the real published release from GitHub, verified the committed checksum, and ran the clean CI-built binary. VERIFY: method=demo - the transcript is the evidence; plus the placement-defect fix (issue309) with its unit-test control.: DELIVERED BACKLOG ITEMS: <items>. <what done means, verified how>."; }
        // RAN: // RAN (method=demo, the transcript is the evidence): keel init --profile strict; sh keelw version OFFLINE from the seeded cache; git first push LANDED (issue306 fix live); import exec-summary + control-propriety --from-library; sync-claude 40/40; guard 0 FAIL; pushed. Then cache EMPTIED: keelw fetched the real published v0.3.1 from GitHub, verified the committed SHA-256, ran keel 0.3.1 build c4d5dbf (clean, no +dirty). Release CI SUCCESS 4m56s. issue309 found live by the demo and fixed with a 4-case unit-test control; full suite 0 FAILED; clippy clean
        part storyKickoffReadyDoDR1 : TestResult { :>> id = "5c2ea20a-0395-4244-a378-9a110b5de23b"; :>> outcome = VerdictKind::pass; :>> judgedAgainst = "c4d5dbf"; :>> judgedAt = "2026-08-29"; :>> judgedBy = "claudeOpus5"; }
    }

    verification kickoffReadyRefineGate : Test { :>> id = "3c22925f-38a2-431b-ad0f-a6306dff419f"; :>> title = "Sprint 494 refine gate (DoR)"; :>> createdAt = "2026-08-29"; :>> createdBy = "claudeOpus5"; :>> method = VerificationMethod::inspect; :>> procedureText = "READY: increments 1-4 landed and proven; the demo is the integration test of all of them at once, which is why it runs LAST and why its DoD is method=demo - the artifact is the transcript of the path a real project will take."; }
    verification kickoffReadyStandupGate : Test { :>> id = "a4d7e847-35c2-475c-9473-d6b2029b4140"; :>> title = "Sprint 494 standup gate"; :>> createdAt = "2026-08-29"; :>> createdBy = "claudeOpus5"; :>> method = VerificationMethod::inspect; :>> procedureText = "One cross-project step: se-templates authored its own D0238 under its own keystone lock, which fired exactly as this repo's does - the unit-extras edit needed the co-committed marked Decision there too. Enforcement parity, observed in the field."; }
    verification kickoffReadyImplementGate : Test { :>> id = "d718256c-5859-42aa-9632-9cfb19bbb08f"; :>> title = "Sprint 494 implement gate"; :>> createdAt = "2026-08-29"; :>> createdBy = "claudeOpus5"; :>> method = VerificationMethod::test; :>> procedureText = "RAN, in order: exec-summary unit authored + published; v0.3.1 tagged, release CI SUCCESS (4m56s), checksums of the PUBLISHED assets committed; demo: init, keelw offline (seeded cache), first push LANDED, import exec-summary + control-propriety --from-library, sync-claude (the drift guard demanded it, correctly), guard 0 FAIL, pushed; cache emptied, keelw fetched v0.3.1 from GitHub, verified, ran - keel 0.3.1, build commit c4d5dbf, no +dirty. THE DEMO FOUND issue309 LIVE: the exec-summary import landed templates/ and tests/ under .engine/ - restore_dst inferred residence from a leading dot, fitting the .github specimen and misplacing every dotless root extra (the pf02 overfit class, verbatim). FIXED: residence travels WITH the bundle (unit.toml carries extras; restore_dst_with restores declared extras where they lived; dot rule stays as pre-extras fallback; both import loops thread one list). Re-published, re-imported, extras at the root."; }
    verification kickoffReadyReviewGate : Test { :>> id = "7b8f093a-833c-4407-8593-4d215931aee4"; :>> title = "Sprint 494 review gate — three passes per D0172"; :>> createdAt = "2026-08-29"; :>> createdBy = "claudeOpus5"; :>> method = VerificationMethod::inspect; :>> procedureText = "THREE PASSES. (1) THE DEMO IS AN HONEST INTEGRATION TEST: it exercised the real library, the real published release, the real hooks - a probe of copies proves copies, and this proved the shipped thing. (2) THE FIX IS DATA-DRIVEN, NOT A GUESS SWAP: the dot heuristic survives for pre-extras bundles, so nothing already exported imports differently; the unit test pins all four placement cases. (3) THE PIN ATE ITS OWN AUTHOR: on version bump, validate REFUSED this very repo until the re-stamp - increment 1 demonstrated on the project that built it, which is the self-hosting evidence nSelfHosting names."; }
    verification kickoffReadyCloseOutGate : Test { :>> id = "251b7841-6bba-4947-b3a1-6400d61d8fea"; :>> title = "Sprint 494 closeOut gate (autonomous, D0049)"; :>> createdAt = "2026-08-29"; :>> createdBy = "claudeOpus5"; :>> method = VerificationMethod::inspect; :>> procedureText = "CLOSED, and the plan with it: increments 1-5 all discharged, every identified ready-check item implemented and demonstrated. THE REAL KICKOFF IS NOW THE HUMAN'S ACT: keel init <project> with the v0.3.1 binary (or copy keelw + keel-wrapper.toml and let it fetch), keel library init <the library remote>, import a la carte, project-onboarding to charter the set. RESIDUALS, named: the library remote is a LOCAL bare repo (C:/Users/WilliamWeatherholtz/claude_code/keel-library.git) - pushing it to a GitHub remote is the human's choice of home; keel-wrapper.toml checksums exist for 0.3.1 only; the demo project is throwaway and was not deleted, so the human can inspect the transcript's tree."; }
    verification kickoffReadyRetroGate : Test { :>> id = "3fab13c9-b8d9-450c-956b-a9319f8e0bd0"; :>> title = "Sprint 494 retro gate (autonomous, D0049)"; :>> createdAt = "2026-08-29"; :>> createdBy = "claudeOpus5"; :>> method = VerificationMethod::analyze; :>> procedureText = "FINDING: the demo found in five minutes what four increments of TDD had not - a cross-project integration defect (issue309) invisible to every unit-scoped test because it lives in the SEAM between export's layout and import's placement rule. The arming-probe lesson generalises: unit tests prove parts, probes prove controls, and only running the REAL PATH proves the seams. dcKickoffReady being method=demo was the right call for exactly this reason. SECOND: three keystone locks fired across two projects this increment (guards.rs here, unit-extras there, control-arming here) and every one was satisfied by a marked Decision rather than bypassed - the enforcement surface is now demonstrably self-consistent across the fleet."; }
}
