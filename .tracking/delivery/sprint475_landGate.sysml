// ProjectDeliveryS475 - Sprint 475: keel land pushed FIRST and gated only after a rejection, so on the success path nothing was gated at all. EXECUTE. 2 pts.
package ProjectDeliveryS475 {
    private import EngineElement::*;
    private import EngineWork::*;
    private import EngineVerification::*;
    private import EngineRelationships::*;

    #CharteredBy dependency from landGateStory to d0234;

    part landGateStory : Story {
        :>> id = "37408b84-8f1d-4e10-9721-51c72d4cd3fc";
        :>> title = "Sprint 475: land gates before the first push, workspace-wide - the D0234 clause that was never implemented (2 pts)";
        :>> createdAt = "2026-08-27"; :>> createdBy = "claudeOpus5"; :>> kind = WorkKind::code; :>> priority = WorkPriority::p1; :>> owner = "claudeOpus5"; :>> estimatedPoints = 2;
    }

    action def DeliveryRunS475 {
        action storyLandGate;
        verification storyLandGateDoD : Test { :>> id = "a4504b87-a0dd-4afe-894e-c0283f225572"; :>> method = VerificationMethod::test; :>> procedureText = "DELIVERED: dcLandGatesBeforeThePush (issue280). cmd_land now runs the workspace-wide gate BEFORE the first push and refuses on failure, saying that nothing was pushed and that the check covers every project in the repository rather than the one the caller stands in. The post-merge gate on the retry path is unchanged - it exists for a different property, that two contributions green alone can be red together. A push carries the whole repository, which is why the gate is workspace-wide and why gating only the caller's project was the hole. Held by keel-cli/tests/land_gate.rs against a REAL bare remote, because the defect was entirely in the ORDER of two real operations and a stubbed push could not have seen it."; }
    // RAN: cargo test --release => 12 suites 0 failures, incl the new keel-cli/tests/land_gate.rs driving a REAL bare remote | disable-and-rerun: with the pre-push gate stubbed out the same test FAILED with 'land must REFUSE a broken workspace, but exited 0', and passed once restored - the proof the control catches issue280 rather than passing beside it | live reproduction in C:/kt/ld: bare remote + two peer projects, beta given an unparseable tracking file and committed with --no-verify, then keel land run FROM ALPHA => exit 1 'REFUSING to push' with 21 problems, and git ls-remote showed the remote still at the baseline; removing the broken file and re-running => exit 0 'landed' with remote and local at the same SHA | cargo clippy --release --all-targets => 0 errors.
        part storyLandGateDoDR1 : TestResult { :>> id = "98d79342-901d-4488-bda1-1c3c28546a9c"; :>> outcome = VerdictKind::pass; :>> judgedAgainst = "3bb8e77"; :>> judgedAt = "2026-08-27"; :>> judgedBy = "claudeOpus5"; }
    }

    verification landGateRefineGate : Test { :>> id = "8aae5b20-abb6-4799-b5fb-0ae0efcd2e80"; :>> title = "Sprint 475 refine gate (DoR)"; :>> createdAt = "2026-08-27"; :>> createdBy = "claudeOpus5"; :>> method = VerificationMethod::inspect; :>> procedureText = "DoR: dcLandGatesBeforeThePush ranked first after sprint 474. NO new Decision is needed and that is the notable part - D0234 clause 4 already asserts that sync and land gate every project in the workspace before anything is pushed, and this sprint brings the CODE up to a claim that was already accepted. The DoD asked for the Decision text to be corrected; making the assertion TRUE is the better correction, because editing an accepted record in place is how history stops being evidence (D0129). Resolver: dcLandGatesBeforeThePush. estimatedPoints=2. #CharteredBy d0234."; }
    part landGateRefineGateR1 : TestResult { :>> id = "b27d8fad-a5c5-40a7-941b-c9f32ff0bacf"; :>> outcome = VerdictKind::pass; :>> judgedAgainst = "3bb8e77"; :>> judgedAt = "2026-08-27"; :>> judgedBy = "claudeOpus5"; }
    verification landGateStandupGate : Test { :>> id = "af4af275-8bee-4f55-941a-054a9e42cf3f"; :>> title = "Sprint 475 standup gate"; :>> createdAt = "2026-08-27"; :>> createdBy = "claudeOpus5"; :>> method = VerificationMethod::inspect; :>> procedureText = "Approach: hoist gate_passes above the retry loop. It is already workspace-wide and already the same entry point the commit hook uses, so no new gate DEFINITION is introduced - which matters, because dcOneGateDefinition is an open finding about three bodies of the gate with three different bars and this must not add a fourth. Strengthening a gate to match an accepted Decision needs no keystone authorisation; the lock exists for weakening."; }
    part landGateStandupGateR1 : TestResult { :>> id = "0951c0fd-e576-498e-9976-49546655b54d"; :>> outcome = VerdictKind::pass; :>> judgedAgainst = "3bb8e77"; :>> judgedAt = "2026-08-27"; :>> judgedBy = "claudeOpus5"; }
    verification landGateImplementGate : Test { :>> id = "ac4140f8-73f3-4ff5-bd48-15bac1ce0f9a"; :>> title = "Sprint 475 implement gate"; :>> createdAt = "2026-08-27"; :>> createdBy = "claudeOpus5"; :>> method = VerificationMethod::test; :>> procedureText = "Implemented, then verified twice over: live against a bare remote, and by a new integration test that drives a real remote and asserts the broken commit never left the machine. Then disable-and-rerun, which is now standard for every control this session ships: with the pre-push gate stubbed out the test FAILS with the exact false-green it exists to catch. Doc-sync in the same commit: CLAUDE.md described land as gating only the MERGED tree on rejection, which this change makes incomplete."; }
    // RAN: cargo test --release => 12 suites 0 failures, incl the new keel-cli/tests/land_gate.rs driving a REAL bare remote | disable-and-rerun: with the pre-push gate stubbed out the same test FAILED with 'land must REFUSE a broken workspace, but exited 0', and passed once restored - the proof the control catches issue280 rather than passing beside it | live reproduction in C:/kt/ld: bare remote + two peer projects, beta given an unparseable tracking file and committed with --no-verify, then keel land run FROM ALPHA => exit 1 'REFUSING to push' with 21 problems, and git ls-remote showed the remote still at the baseline; removing the broken file and re-running => exit 0 'landed' with remote and local at the same SHA | cargo clippy --release --all-targets => 0 errors.
    part landGateImplementGateR1 : TestResult { :>> id = "4e415af0-489f-4638-a392-6603da0a56df"; :>> outcome = VerdictKind::pass; :>> judgedAgainst = "3bb8e77"; :>> judgedAt = "2026-08-27"; :>> judgedBy = "claudeOpus5"; }
    verification landGateReviewGate : Test { :>> id = "4289cd3c-5c42-4288-862f-b39ad17b1968"; :>> title = "Sprint 475 review gate"; :>> createdAt = "2026-08-27"; :>> createdBy = "claudeOpus5"; :>> method = VerificationMethod::inspect; :>> procedureText = "Diff reviewed. Two properties are now distinct and both are kept: the pre-push gate answers 'is what I am about to push honest', and the post-merge gate answers 'are two green contributions red together'. Collapsing them would have lost the second. The refusal message names the workspace scope explicitly, because the reader's mental model is their own project and the gate's scope is the repository - a refusal citing a project they are not in would otherwise read as a bug."; }
    part landGateReviewGateR1 : TestResult { :>> id = "d3dd5532-ae88-4a36-b784-71cdd8d06211"; :>> outcome = VerdictKind::pass; :>> judgedAgainst = "3bb8e77"; :>> judgedAt = "2026-08-27"; :>> judgedBy = "claudeOpus5"; }
    verification landGateCloseOutGate : Test { :>> id = "27d5b947-8b64-43bb-8cfc-b7460fc9b5a0"; :>> title = "Sprint 475 closeOut gate (autonomous, D0049)"; :>> createdAt = "2026-08-27"; :>> createdBy = "claudeOpus5"; :>> method = VerificationMethod::inspect; :>> procedureText = "Autonomous closeOut (D0049): the DoD is recorded pass with its RAN receipt; the frontier was read back from keel whats-next. Remaining from the panel: dcNoCommandReportsGreenOverNothing, dcOneGateDefinition, dcPanelRecordCorrections and dcEveryAdvertisedViewIsBound. Self-evidencing (D0051): no human confirmation claimed."; }
    part landGateCloseOutGateR1 : TestResult { :>> id = "60815323-d205-4b2e-ae3f-a15ac71abfc2"; :>> outcome = VerdictKind::pass; :>> judgedAgainst = "3bb8e77"; :>> judgedAt = "2026-08-27"; :>> judgedBy = "claudeOpus5"; }
    verification landGateRetroGate : Test { :>> id = "20560227-e972-44c3-966d-bcfd332d2224"; :>> title = "Sprint 475 retro gate (autonomous, D0049)"; :>> createdAt = "2026-08-27"; :>> createdBy = "claudeOpus5"; :>> method = VerificationMethod::analyze; :>> procedureText = "Autonomous retro (D0049). WELL: this is the cheapest fix of the session - one hoisted call - and it closed a hole through which any broken project could leave any machine. The cost was all in the VERIFICATION, which is the right ratio and the opposite of how the defect got here. FINDING: D0234 asserted this property in prose and the code never had it, for five days, while the Decision read as authoritative. That is the same class as issue277 - a Decision citing a compensating control that did not work - and it is now the second instance in three sprints. An accepted Decision's prose is not checked against anything. AVOIDABLE-ISSUE SCAN: the function carries an `@audit-hash ceLandGate` marker, so it was explicitly identified as gate-bearing code and reviewed as such, and the review still missed that the gate call sat INSIDE the retry loop. Marking code as critical is not the same as testing it. Candidate forward control, stated not built: for each `@audit-hash` marker, require a named test that exercises the property the marker claims. Estimate 2 pts held."; }
    part landGateRetroGateR1 : TestResult { :>> id = "15468daf-20bb-4cc3-a47a-30e7e2b05af7"; :>> outcome = VerdictKind::pass; :>> judgedAgainst = "3bb8e77"; :>> judgedAt = "2026-08-27"; :>> judgedBy = "claudeOpus5"; }
}
