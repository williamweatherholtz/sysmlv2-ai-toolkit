// ProjectDeliveryS596 — Sprint 596: keel process remove takes an installed unit out as one act and refuses while anything still references it. EXECUTE. 2 pts.
package ProjectDeliveryS596 {
    private import EngineElement::*;
    private import EngineWork::*;
    private import EngineVerification::*;
    private import EngineRelationships::*;

    #CharteredBy dependency from processRemoveStory to d0345;

    part processRemoveStory : Story {
        :>> id = "7cc5fce0-b62f-4fa3-8600-803526e20444";
        :>> title = "Sprint 596: keel process remove takes an installed unit out as one act and refuses while anything still references it (2 pts)";
        :>> createdAt = "2026-09-08"; :>> createdBy = "claudeOpus5"; :>> kind = WorkKind::code; :>> priority = WorkPriority::p0; :>> owner = "claudeFable5"; :>> estimatedPoints = 2;
    }

    action def DeliveryRunS596 {
        action storyProcessRemove;
        verification storyProcessRemoveDoD : Test { :>> id = "ad5f1efb-a7de-4ce6-8073-a6e08ec835f7"; :>> method = VerificationMethod::test; :>> procedureText = "DELIVERED: `keel process remove <name> [--dry-run]` (process_cmd.rs cmd_remove). It scans the tree for live references to the unit's paths - a reference is a `file:line` naming `.engine/processes/<name>.sysml` or `.engine/skills/<name>/` from outside the unit itself - and REFUSES listing each one with `Nothing was removed`, because tool-reference, process-skill, activation-manifest and control-map-reconciled would otherwise go red on the next gate. With no references it deletes the process file and the skill directory, strips the unit's line or section from installed-units.toml, activation.toml, unit-extras.toml and the unit-id registry (each reported as `stripped` or `no entry`), says the LIBRARY copy is untouched, names the keystone lock (the process file is under it, so the commit needs its co-committed Decision), and tells the remover to run `keel sync-claude`. Declared as a CliCommand invocation in .engine/cli/commands.sysml with cli_facts.rs mirrored, so cli-surface-declared holds. VERIFIED by keel-cli/tests/process_removal.rs: removing_a_unit_takes_its_files_and_every_contract_entry, a_referenced_unit_is_refused_and_nothing_is_removed, removing_a_unit_the_project_does_not_have_says_so - 3/3 against a fixture that runs `keel init .`, installs a unit in the D0220 registry shape and appends it to all four contracts."; }
        // RAN: cargo test --release --test process_removal: 3 passed 0 failed (removing_a_unit_takes_its_files_and_every_contract_entry, a_referenced_unit_is_refused_and_nothing_is_removed, removing_a_unit_the_project_does_not_have_says_so); keel suite 574 passed 0 failed receipt e6fce77cc683; keel validate clean; keel guard ALL PASS incl. cli-surface-declared after the cli_facts.rs mirror
        part storyProcessRemoveDoDR1 : TestResult { :>> id = "92c8962f-0eee-4847-958e-4bbc1b62d666"; :>> outcome = VerdictKind::pass; :>> judgedAgainst = "e0624f36948cba80c35b5408643a970c0bd615d8"; :>> judgedAt = "2026-09-07"; :>> judgedBy = "claudeOpus5"; }
    }

    verification processRemoveRefineGate : Test { :>> id = "b375a284-060b-44d5-b645-166aafa60924"; :>> title = "Sprint 596 refine gate (DoR)"; :>> createdAt = "2026-09-08"; :>> createdBy = "claudeOpus5"; :>> method = VerificationMethod::inspect; :>> procedureText = "READY because the DoD named the act, the refusal condition and the fixture before any code; two hand removals (sprints 524, 527) are the recorded pain; the reference scan reuses the same path predicate the guards use, so refusing and going red cannot disagree. 2 pts: a command, four contract strippers, a fixture."; }
    // RAN: cargo test --release --test process_removal: 3 passed 0 failed (removing_a_unit_takes_its_files_and_every_contract_entry, a_referenced_unit_is_refused_and_nothing_is_removed, removing_a_unit_the_project_does_not_have_says_so); keel suite 574 passed 0 failed receipt e6fce77cc683; keel validate clean; keel guard ALL PASS incl. cli-surface-declared after the cli_facts.rs mirror
    part processRemoveRefineGateR1 : TestResult { :>> id = "a5ddd5a8-615d-4dfd-ac50-eb7247a21142"; :>> outcome = VerdictKind::pass; :>> judgedAgainst = "e0624f36948cba80c35b5408643a970c0bd615d8"; :>> judgedAt = "2026-09-07"; :>> judgedBy = "claudeOpus5"; }
    verification processRemoveStandupGate : Test { :>> id = "edf8c829-f122-45c1-8ce6-2ddd718f0947"; :>> title = "Sprint 596 standup gate"; :>> createdAt = "2026-09-08"; :>> createdBy = "claudeOpus5"; :>> method = VerificationMethod::inspect; :>> procedureText = "ONE CHOICE: refuse on ANY live reference rather than rewrite references for the remover. Rewriting would be a judgment about what the referencing file should say instead; the command can only see that it says something. Cost: a remover with many references does the rewrites by hand first - the output names every one so that is a list, not a hunt."; }
    // RAN: cargo test --release --test process_removal: 3 passed 0 failed (removing_a_unit_takes_its_files_and_every_contract_entry, a_referenced_unit_is_refused_and_nothing_is_removed, removing_a_unit_the_project_does_not_have_says_so); keel suite 574 passed 0 failed receipt e6fce77cc683; keel validate clean; keel guard ALL PASS incl. cli-surface-declared after the cli_facts.rs mirror
    part processRemoveStandupGateR1 : TestResult { :>> id = "f4f73de8-9baa-45df-9390-521780b33f09"; :>> outcome = VerdictKind::pass; :>> judgedAgainst = "e0624f36948cba80c35b5408643a970c0bd615d8"; :>> judgedAt = "2026-09-07"; :>> judgedBy = "claudeOpus5"; }
    verification processRemoveImplementGate : Test { :>> id = "5b6dc73f-ea4f-4865-a2d6-86da134680e9"; :>> title = "Sprint 596 implement gate"; :>> createdAt = "2026-09-08"; :>> createdBy = "claudeOpus5"; :>> method = VerificationMethod::test; :>> procedureText = "RAN: cargo test --release --test process_removal 3/3; the first run deleted 1 file instead of 2 because the fixture's registry did not use the D0220 `part <x>Skill : AISkill { location = ... }` shape the scanner keys on - the FIXTURE was wrong, the scanner right, and fixing the fixture (not the code) is recorded here so the next reader does not loosen the scanner. cli-surface-declared went red once on the unsynced cli_facts.rs mirror and green after mirroring. keel suite 574 passed 0 failed (receipt e6fce77cc683). clippy -D warnings clean."; }
    // RAN: cargo test --release --test process_removal: 3 passed 0 failed (removing_a_unit_takes_its_files_and_every_contract_entry, a_referenced_unit_is_refused_and_nothing_is_removed, removing_a_unit_the_project_does_not_have_says_so); keel suite 574 passed 0 failed receipt e6fce77cc683; keel validate clean; keel guard ALL PASS incl. cli-surface-declared after the cli_facts.rs mirror
    part processRemoveImplementGateR1 : TestResult { :>> id = "bfb9726e-35c4-467d-9dcc-00d9a9a4ca9d"; :>> outcome = VerdictKind::pass; :>> judgedAgainst = "e0624f36948cba80c35b5408643a970c0bd615d8"; :>> judgedAt = "2026-09-07"; :>> judgedBy = "claudeOpus5"; }
    verification processRemoveReviewGate : Test { :>> id = "2daf0bf0-4549-4547-9e73-9cde0557b9fd"; :>> title = "Sprint 596 review gate — three passes per D0172"; :>> createdAt = "2026-09-08"; :>> createdBy = "claudeOpus5"; :>> method = VerificationMethod::inspect; :>> procedureText = "THREE PASSES (D0172). (1) Does refusal leave the tree untouched: yes - the scan runs before any delete and the test asserts every file and contract entry survives. (2) Is the library copy safe: yes - removal touches only the project's `.engine/`, and the output says so in words. (3) Does the DoD overclaim: the DoD says the command removes `its declared extras` - it strips the unit-extras.toml section, which is what declared extras are; nothing else is claimed."; }
    // RAN: cargo test --release --test process_removal: 3 passed 0 failed (removing_a_unit_takes_its_files_and_every_contract_entry, a_referenced_unit_is_refused_and_nothing_is_removed, removing_a_unit_the_project_does_not_have_says_so); keel suite 574 passed 0 failed receipt e6fce77cc683; keel validate clean; keel guard ALL PASS incl. cli-surface-declared after the cli_facts.rs mirror
    part processRemoveReviewGateR1 : TestResult { :>> id = "60a83f80-c36b-43cd-9b19-f9df899dbffb"; :>> outcome = VerdictKind::pass; :>> judgedAgainst = "e0624f36948cba80c35b5408643a970c0bd615d8"; :>> judgedAt = "2026-09-07"; :>> judgedBy = "claudeOpus5"; }
    verification processRemoveCloseOutGate : Test { :>> id = "6bca38d9-01a4-4386-864a-e5e3cef75bd0"; :>> title = "Sprint 596 closeOut gate (autonomous, D0049)"; :>> createdAt = "2026-09-08"; :>> createdBy = "claudeOpus5"; :>> method = VerificationMethod::inspect; :>> procedureText = "CLOSED. dcProcessRemoveCommand passes on the fixture; the command is in the CLI facts. D0345's consequence (`the one-act path, when built`) is now built. Not done here: a REAL removal of a retired unit in this tree - decision-channel is already gone by hand (sprint 527), so there is nothing to remove; the first live use will be a consumer's."; }
    // RAN: cargo test --release --test process_removal: 3 passed 0 failed (removing_a_unit_takes_its_files_and_every_contract_entry, a_referenced_unit_is_refused_and_nothing_is_removed, removing_a_unit_the_project_does_not_have_says_so); keel suite 574 passed 0 failed receipt e6fce77cc683; keel validate clean; keel guard ALL PASS incl. cli-surface-declared after the cli_facts.rs mirror
    part processRemoveCloseOutGateR1 : TestResult { :>> id = "e0bbbd65-5199-4bdd-b599-1c2252fd9d32"; :>> outcome = VerdictKind::pass; :>> judgedAgainst = "e0624f36948cba80c35b5408643a970c0bd615d8"; :>> judgedAt = "2026-09-07"; :>> judgedBy = "claudeOpus5"; }
    verification processRemoveRetroGate : Test { :>> id = "3a5c737a-1cce-4e5a-bbd8-55d352cbbb50"; :>> title = "Sprint 596 retro gate (autonomous, D0049)"; :>> createdAt = "2026-09-08"; :>> createdBy = "claudeOpus5"; :>> method = VerificationMethod::analyze; :>> procedureText = "AVOIDABLE-ISSUE SCAN HELD. The fixture-shape trap recurred from sprint 594 (a test asserting against a shape the code never keys on). Finding: fixtures that stand in for engine surfaces should be built by the engine's own writer (`keel process import`) not by hand - tracked as a candidate for dcAdHocChecksAreProbedFirst, already on the frontier, so no new item."; }
    // RAN: cargo test --release --test process_removal: 3 passed 0 failed (removing_a_unit_takes_its_files_and_every_contract_entry, a_referenced_unit_is_refused_and_nothing_is_removed, removing_a_unit_the_project_does_not_have_says_so); keel suite 574 passed 0 failed receipt e6fce77cc683; keel validate clean; keel guard ALL PASS incl. cli-surface-declared after the cli_facts.rs mirror
    part processRemoveRetroGateR1 : TestResult { :>> id = "f8c2f5ab-60cd-4090-aa68-978a4618f24e"; :>> outcome = VerdictKind::pass; :>> judgedAgainst = "e0624f36948cba80c35b5408643a970c0bd615d8"; :>> judgedAt = "2026-09-07"; :>> judgedBy = "claudeOpus5"; }
}
