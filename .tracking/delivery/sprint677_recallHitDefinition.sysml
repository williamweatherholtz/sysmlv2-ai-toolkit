// ProjectDeliveryS677 — Sprint 677: The eight-case recall harness says what a hit is and which case it cannot reach, before it runs. Under D0408 option A (the human's word, 2026-09-11) a hit stays the ground-truth record among the shown rows - the named record, or nothing - and the d0176 obligation case is a declared UNREACHABLE sentinel: recall_ab.py carries the marker in its CASES table, prints `unreachable (declared)` in place of `no`, states the bar as 7 of 8 with the sentinel not counted against it, and would print a hit on the sentinel as news rather than fold it into the norm. Resolves issue391. EXECUTE.. EXECUTE. 1 pts.
package ProjectDeliveryS677 {
    private import EngineElement::*;
    private import EngineWork::*;
    private import EngineVerification::*;
    private import EngineRelationships::*;

    #CharteredBy dependency from recallHitDefinitionStory to d0408;

    part recallHitDefinitionStory : Story {
        :>> id = "5ca9e08b-a0a7-4285-8728-6d88ae820d75";
        :>> title = "Sprint 677: The eight-case recall harness says what a hit is and which case it cannot reach, before it runs. Under D0408 option A (the human's word, 2026-09-11) a hit stays the ground-truth record among the shown rows - the named record, or nothing - and the d0176 obligation case is a declared UNREACHABLE sentinel: recall_ab.py carries the marker in its CASES table, prints `unreachable (declared)` in place of `no`, states the bar as 7 of 8 with the sentinel not counted against it, and would print a hit on the sentinel as news rather than fold it into the norm. Resolves issue391. EXECUTE. (1 pts)";
        :>> createdAt = "2026-09-11"; :>> createdBy = "claudeOpus5"; :>> kind = WorkKind::code; :>> priority = WorkPriority::p0; :>> owner = "claudeOpus5"; :>> estimatedPoints = 1;
    }

    action def DeliveryRunS677 {
        action storyRecallHitDefinition;
        verification storyRecallHitDefinitionDoD : Test { :>> id = "07d9b2ae-ab98-4aad-8bfe-f3dbdb3c834b"; :>> method = VerificationMethod::test; :>> procedureText = "DELIVERED BACKLOG ITEMS: dcRecallHitDefinitionIsStated. Done means: .engine/tools/recall_ab.py states in its docstring what a hit is (the named ground-truth record among the shown rows, D0408 option A) and what the bar is (7 of 8, the eighth a declared sentinel); its CASES table carries a third field, REACHABLE or UNREACHABLE, set before any run, with UNREACHABLE on the d0176 case only; the d0176 row prints `unreachable (declared)` in place of `no`; the summary prints the required bar, whether it is met on the reachable cases, and a NEWS line if a sentinel ever hits. No engine code changes. The criterion 'the hand set stays at 7/8 or better' lives only in recallRanksLinkedRecordsAsWellAsGrepDoesDoD, a done DoD whose R3 pass stands, so under D0307 it is not edited and remains true as read; the definition lands in the harness header and in this item's DoD result. Verified by running python .engine/tools/recall_ab.py against a settled binary and reading the d0176 row and the summary lines."; }
        // RAN: python .engine/tools/recall_ab.py against keel 0.4.1 build 10b6912 (unchanged through the run): injection ON 7/8, d0176 row reads unreachable (declared), required bar 7 of 8 MET (7/7 reachable), OFF 0/8, silent 0/8, mean 923 ms; dcRecallHitDefinitionIsStatedDoDR1 recorded at 56d3968; keel-serve validate exit 0 775 files clean; check-engine exit 0; guard --no-receipt ALL PASS exit 0
        part storyRecallHitDefinitionDoDR1 : TestResult { :>> id = "714bae8a-73b5-43d0-988f-4baf0107a084"; :>> outcome = VerdictKind::pass; :>> judgedAgainst = "56d3968"; :>> judgedAt = "2026-09-11"; :>> judgedBy = "claudeOpus5"; }
    }

    verification recallHitDefinitionRefineGate : Test { :>> id = "ec649790-9eeb-49db-8660-8d05e3deba5f"; :>> title = "Sprint 677 refine gate (DoR)"; :>> createdAt = "2026-09-11"; :>> createdBy = "claudeOpus5"; :>> method = VerificationMethod::inspect; :>> procedureText = "Chartered by D0408, accepted by the human 2026-09-11 on the brief copy-out (option A, the recommended course). Resolves issue391. One point: two fields and one print branch in one Python harness plus its docstring; no Rust, no schema, no process. NOT A PROCESS CHANGE - it fixes the meaning of one measurement in the harness that takes it. NOT A FORK - the fork was D0408 and is decided."; }
    // RAN: python .engine/tools/recall_ab.py against keel 0.4.1 build 10b6912 (unchanged through the run): injection ON 7/8, d0176 row reads unreachable (declared), required bar 7 of 8 MET (7/7 reachable), OFF 0/8, silent 0/8, mean 923 ms; keel-serve validate exit 0 775 files clean; check-engine exit 0; guard --no-receipt ALL PASS exit 0; chartered by d0408 (accepted by the human 2026-09-11, option A); 1 point; task dcRecallHitDefinitionIsStated; resolves issue391
    part recallHitDefinitionRefineGateR1 : TestResult { :>> id = "b70cdae5-d5d8-4195-b10a-3151f917e1e5"; :>> outcome = VerdictKind::proposed; :>> judgedAgainst = "56d3968"; :>> judgedAt = "2026-09-11"; :>> judgedBy = "claudeOpus5"; }
    verification recallHitDefinitionStandupGate : Test { :>> id = "3e640a88-f170-4f0f-9eb5-610e327d9b54"; :>> title = "Sprint 677 standup gate"; :>> createdAt = "2026-09-11"; :>> createdBy = "claudeOpus5"; :>> method = VerificationMethod::inspect; :>> procedureText = "Order: read D0408 option A and the DoD; locate every place the criterion is stated (grep recall_ab, hand-set, 7/8, of 8 over .engine/docs, .engine/skills, .claude/skills, .engine/contracts, scripts, .tracking); edit the harness docstring, CASES table and print path; run the harness to a file and read it back; record. Blocker met: the only statement of the criterion outside the Decision is the done DoD at backlog.sysml:519, which D0307 forbids editing - resolved by stating the definition and bar in the harness and in the DoD result, as D0408's consequences direct. No cargo or keel-land was running; the harness named build 10b6912 before and after."; }
    // RAN: python .engine/tools/recall_ab.py against keel 0.4.1 build 10b6912 (unchanged through the run): injection ON 7/8, d0176 row reads unreachable (declared), required bar 7 of 8 MET (7/7 reachable), OFF 0/8, silent 0/8, mean 923 ms; keel-serve validate exit 0 775 files clean; check-engine exit 0; guard --no-receipt ALL PASS exit 0; criterion search: grep recall_ab|hand-set|7/8|of 8 over .engine/docs .engine/skills .claude/skills .engine/contracts scripts .tracking - the only criterion statement is the done DoD recallRanksLinkedRecordsAsWellAsGrepDoesDoD (backlog.sysml:519), not edited under D0307
    part recallHitDefinitionStandupGateR1 : TestResult { :>> id = "135bb5c5-11f2-46f3-ae3f-ab13f1c8dd0b"; :>> outcome = VerdictKind::proposed; :>> judgedAgainst = "56d3968"; :>> judgedAt = "2026-09-11"; :>> judgedBy = "claudeOpus5"; }
    verification recallHitDefinitionImplementGate : Test { :>> id = "6c548a25-c043-4caa-a45a-9b6a880492b3"; :>> title = "Sprint 677 implement gate"; :>> createdAt = "2026-09-11"; :>> createdBy = "claudeOpus5"; :>> method = VerificationMethod::test; :>> procedureText = ".engine/tools/recall_ab.py: docstring gains WHAT A HIT IS and THE BAR IS 7 OF 8 sections; module constants REACHABLE / UNREACHABLE and REQUIRED derived from the table; CASES rows carry the marker, d0176 UNREACHABLE; the hit column widens to the marker's width; the summary prints required bar, bar MET / NOT MET on the reachable count, and a NEWS line when a sentinel hits. Nothing under keel-cli/src changed."; }
    // RAN: python .engine/tools/recall_ab.py against keel 0.4.1 build 10b6912 (unchanged through the run): injection ON 7/8, d0176 row reads unreachable (declared), required bar 7 of 8 MET (7/7 reachable), OFF 0/8, silent 0/8, mean 923 ms; keel-serve validate exit 0 775 files clean; check-engine exit 0; guard --no-receipt ALL PASS exit 0; git status: one file modified, .engine/tools/recall_ab.py; python ast.parse on it: syntax ok; nothing under keel-cli/src changed
    part recallHitDefinitionImplementGateR1 : TestResult { :>> id = "5d621337-1240-408d-b721-f3fe7a1df5bb"; :>> outcome = VerdictKind::pass; :>> judgedAgainst = "56d3968"; :>> judgedAt = "2026-09-11"; :>> judgedBy = "claudeOpus5"; }
    verification recallHitDefinitionReviewGate : Test { :>> id = "ad937efb-1baa-4519-921a-0d15c3570275"; :>> title = "Sprint 677 review gate — three passes per D0172"; :>> createdAt = "2026-09-11"; :>> createdBy = "claudeOpus5"; :>> method = VerificationMethod::inspect; :>> procedureText = "Delivered, measured 2026-09-11 against keel 0.4.1 build 10b6912, unchanged through the run: injection ON 7/8, the seven reachable cases at positions 8, 3, 4, 5, 4, 9, 11 of 13 rows; d0176 row reads `unreachable (declared)`; required bar 7 of 8 - MET (7/7 reachable cases hit); injection OFF 0/8; silent 0/8; mean 923 ms. The harness now says less than it looked like it said about semantic reach, and says so in its own output - the cost D0408 priced. Residual: zero headroom on the seven; the sentinel has no gradient, by design."; }
    // RAN: python .engine/tools/recall_ab.py against keel 0.4.1 build 10b6912 (unchanged through the run): injection ON 7/8, d0176 row reads unreachable (declared), required bar 7 of 8 MET (7/7 reachable), OFF 0/8, silent 0/8, mean 923 ms; keel-serve validate exit 0 775 files clean; check-engine exit 0; guard --no-receipt ALL PASS exit 0; seven reachable hits at positions 8 3 4 5 4 9 11 of 13 rows
    part recallHitDefinitionReviewGateR1 : TestResult { :>> id = "6790bd3a-37bc-42d9-b078-4f54cdc3a7e5"; :>> outcome = VerdictKind::proposed; :>> judgedAgainst = "56d3968"; :>> judgedAt = "2026-09-11"; :>> judgedBy = "claudeOpus5"; }
    verification recallHitDefinitionCloseOutGate : Test { :>> id = "1f4f49df-53dc-479c-85a8-9e021fd46717"; :>> title = "Sprint 677 closeOut gate (autonomous, D0049)"; :>> createdAt = "2026-09-11"; :>> createdBy = "claudeOpus5"; :>> method = VerificationMethod::inspect; :>> procedureText = "Sprint 677 closes on the harness run and the three checks (validate, check-engine, guard). dcRecallHitDefinitionIsStated gets its DoD result (method=inspect, an AI-examined pass lands proposed under D0312 B for the human's judge-set); issue391 resolves through it (computed). recallRanksLinkedRecordsAsWellAsGrepDoesDoD is not touched."; }
    // RAN: python .engine/tools/recall_ab.py against keel 0.4.1 build 10b6912 (unchanged through the run): injection ON 7/8, d0176 row reads unreachable (declared), required bar 7 of 8 MET (7/7 reachable), OFF 0/8, silent 0/8, mean 923 ms; keel-serve validate exit 0 775 files clean; check-engine exit 0; guard --no-receipt ALL PASS exit 0; dcRecallHitDefinitionIsStatedDoDR1 recorded at 56d3968 by append-result (method=inspect); issue391 resolves through it
    part recallHitDefinitionCloseOutGateR1 : TestResult { :>> id = "d17a8e39-c1cc-4a30-95a6-76d25fc66433"; :>> outcome = VerdictKind::proposed; :>> judgedAgainst = "56d3968"; :>> judgedAt = "2026-09-11"; :>> judgedBy = "claudeOpus5"; }
    verification recallHitDefinitionRetroGate : Test { :>> id = "755adcee-46aa-460b-a014-576da5fbae71"; :>> title = "Sprint 677 retro gate (autonomous, D0049)"; :>> createdAt = "2026-09-11"; :>> createdBy = "claudeOpus5"; :>> method = VerificationMethod::analyze; :>> procedureText = "AVOIDABLE-ISSUE SCAN: no new item. FINDING: the only place the 7/8 criterion was written was a DoD that had since passed, so the definition it relied on had no editable home outside a Decision; the fix put the definition where the measurement is printed, which is where the next reader of a 7/8 will look. Tracked already: issue391 (resolved by this sprint). Nothing recurred that a control would catch."; }
    // RAN: python .engine/tools/recall_ab.py against keel 0.4.1 build 10b6912 (unchanged through the run): injection ON 7/8, d0176 row reads unreachable (declared), required bar 7 of 8 MET (7/7 reachable), OFF 0/8, silent 0/8, mean 923 ms; keel-serve validate exit 0 775 files clean; check-engine exit 0; guard --no-receipt ALL PASS exit 0; retro names no new item; issue391 already tracked and resolved by this sprint
    part recallHitDefinitionRetroGateR1 : TestResult { :>> id = "b48f384e-52f5-4ea0-b90f-23621f5698af"; :>> outcome = VerdictKind::proposed; :>> judgedAgainst = "56d3968"; :>> judgedAt = "2026-09-11"; :>> judgedBy = "claudeOpus5"; }
}
