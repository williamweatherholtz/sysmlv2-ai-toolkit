// ProjectDeliveryS619 — Sprint 619: Sprint 619 lets a signed plan cover the steps it names (dcSignedPlanCoversItsNamedSteps, D0375 option C) under D0396: a marker Decision recorded with plan and step is accepted at record time when the plan is human-signed and names the step, with a PLAN-COVERED note and a guard that holds the cover to the plan; the rule's own Decision is the live case.. EXECUTE. 5 pts.
package ProjectDeliveryS619 {
    private import EngineElement::*;
    private import EngineWork::*;
    private import EngineVerification::*;
    private import EngineRelationships::*;

    #CharteredBy dependency from planCoversStepStory to d0375;

    part planCoversStepStory : Story {
        :>> id = "f0432a84-6e51-4f48-ba61-921fc73abd74";
        :>> title = "Sprint 619: Sprint 619 lets a signed plan cover the steps it names (dcSignedPlanCoversItsNamedSteps, D0375 option C) under D0396: a marker Decision recorded with plan and step is accepted at record time when the plan is human-signed and names the step, with a PLAN-COVERED note and a guard that holds the cover to the plan; the rule's own Decision is the live case. (5 pts)";
        :>> createdAt = "2026-09-09"; :>> createdBy = "claudeOpus5"; :>> kind = WorkKind::code; :>> priority = WorkPriority::p0; :>> owner = "claudeOpus5"; :>> estimatedPoints = 5;
    }

    action def DeliveryRunS619 {
        action storyPlanCoversStep;
        verification storyPlanCoversStepDoD : Test { :>> id = "a93c3ea8-ec35-46ae-a99b-4101d65b7849"; :>> method = VerificationMethod::test; :>> procedureText = "DONE MEANS: a signed plan covers the steps it names (D0375, option C, the human's word 2026-09-08). A process-change or safety-change Decision recorded with `plan: dNNNN` and `step: <name>` in its draft is accepted AT RECORD TIME when the plan Decision (a) exists, (b) was accepted by a HUMAN'S OWN word - its AcceptR carries no AUTO-ACCEPTED token, and its judgedBy is a Person named in github-actors.toml as a decider - and (c) names the step in its own decision or consequences text, matched on the step name exactly; the acceptance note carries a PLAN-COVERED token, the plan id, and the step name, and the judge is the plan's judge. Any of (a)-(c) failing leaves the Decision proposed and says which clause failed and what the plan text was searched for. A guard `plan-covers-step` fails an accepted Decision whose note carries the token when its named plan no longer holds (a)-(c) against the tree - so the cover cannot outlive the plan it cites - and a plan cannot cover itself or another plan-covered Decision (one level: the human's word, then the steps it names, never a chain). VERIFY: tests in both directions - a marker Decision naming a step the plan text carries is accepted with the plan's judge; the same with the plan AUTO-ACCEPTED stays proposed naming clause (b); a step the plan does not name stays proposed naming clause (c) and quoting the searched text's length; a plan covering a plan is refused; the guard fails a fixture whose plan text was edited to drop the step; and the LIVE case - this rule's own Decision records `plan: d0375` `step: plan-covers-step` and is accepted at record time, because D0375's consequences text names it."; }
        // RAN: plan_cover.rs + record branch + guard 68; 1 unit + 5 integration tests; live D0396 accepted at record time under d0375; D0375 option C
        part storyPlanCoversStepDoDR1 : TestResult { :>> id = "c3844155-78c5-4520-9ee9-8f7a296a2919"; :>> outcome = VerdictKind::pass; :>> judgedAgainst = "216018767b33f8837870e96503aa9e526a34aca5"; :>> judgedAt = "2026-09-08"; :>> judgedBy = "claudeOpus5"; }
    }

    verification planCoversStepRefineGate : Test { :>> id = "1acd35f9-309e-4b5b-b770-96b29463c5e9"; :>> title = "Sprint 619 refine gate (DoR)"; :>> createdAt = "2026-09-09"; :>> createdBy = "claudeOpus5"; :>> method = VerificationMethod::inspect; :>> procedureText = "Scope: keel-cli/src/plan_cover.rs (assess, note, parse_note; unit test); the record path in main.rs (try_plan_cover, before the D0337 gate) reading plan:/step: from the draft; guard plan-covers-step (68) in guards.rs with its registration in GUARD_NAMES, dispatch, guard-constraints and guards.md; keel-cli/tests/signed_plan_covers_its_steps.rs; D0396 (the live case). Out of scope: chains deeper than one level (forbidden by construction), and a plan naming a step by regex rather than exact substring (exact is what the DoD says). Estimate 5 points: a module, a record-path branch, a guard, five integration tests, the live self-application. DoR: points set, charter d0375, scope clear, no blocking dependency, DoD authored."; }
    // RAN: DoR: 5 points, charter d0375, scope in refine text, DoD authored, no blocking dependency
    part planCoversStepRefineGateR1 : TestResult { :>> id = "84e78066-b348-483a-85e4-6ba3f9825b60"; :>> outcome = VerdictKind::pass; :>> judgedAgainst = "216018767b33f8837870e96503aa9e526a34aca5"; :>> judgedAt = "2026-09-08"; :>> judgedBy = "claudeOpus5"; }
    verification planCoversStepStandupGate : Test { :>> id = "a0b7fe60-5b26-4be9-9f6c-9a213d8aa8bf"; :>> title = "Sprint 619 standup gate"; :>> createdAt = "2026-09-09"; :>> createdBy = "claudeOpus5"; :>> method = VerificationMethod::inspect; :>> procedureText = "Plan: (1) plan_cover::assess runs the three clauses over the plan's file and the deciders table; note/parse_note carry the plan and step through the acceptance note; (2) the draft parser already reads plan:/step: header keys, so try_plan_cover fires before the standing-consent gate and accepts under the plan's judge or leaves proposed naming the clause; (3) guard plan-covers-step re-runs assess on every PLAN-COVERED acceptance; (4) register the guard; (5) tests: accept under the plan's judge, clause c with lengths, an AUTO-ACCEPTED plan refused clause b, a missing plan clause a, the guard failing when the plan drops the step; (6) record D0396 itself with plan d0375 step plan-covers-step - the live case; gates and doc-sync."; }
    // RAN: plan of six steps in the standup text; all six executed in this commit
    part planCoversStepStandupGateR1 : TestResult { :>> id = "0ca9174f-e999-4a08-8f6f-2fc90c922dc3"; :>> outcome = VerdictKind::pass; :>> judgedAgainst = "216018767b33f8837870e96503aa9e526a34aca5"; :>> judgedAt = "2026-09-08"; :>> judgedBy = "claudeOpus5"; }
    verification planCoversStepImplementGate : Test { :>> id = "96b0b787-9309-4439-8de5-d743090ad226"; :>> title = "Sprint 619 implement gate"; :>> createdAt = "2026-09-09"; :>> createdBy = "claudeOpus5"; :>> method = VerificationMethod::test; :>> procedureText = "RAN: cargo build --release; cargo clippy --release --all-targets -D warnings exit 0; cargo test --release --lib plan_cover 1 passed; cargo test --release --test signed_plan_covers_its_steps 5 passed 0 failed; keel record decision --from d_plan_cover.md accepted D0396 at record time PLAN-COVERED by d0375 step plan-covers-step judge wweatherholtz; keel validate . 703 clean; keel guard exit 0 (68 guards); keel sync-claude; keel guard doc-guard-count / doc-sync PASS."; }
    // RAN: cargo build --release clean; cargo clippy --release --all-targets -D warnings exit 0; cargo test --release --lib plan_cover 1 passed; cargo test --release --test signed_plan_covers_its_steps 5 passed 0 failed; record decision --from d_plan_cover.md accepted D0396 at record time PLAN-COVERED by d0375 step plan-covers-step; keel validate . 703 clean; keel guard exit 0 68 guards; sync-claude; doc-guard-count/doc-sync PASS
    part planCoversStepImplementGateR1 : TestResult { :>> id = "e6c9c8bf-289a-468d-a871-2696fcdb60b4"; :>> outcome = VerdictKind::pass; :>> judgedAgainst = "216018767b33f8837870e96503aa9e526a34aca5"; :>> judgedAt = "2026-09-08"; :>> judgedBy = "claudeOpus5"; }
    verification planCoversStepReviewGate : Test { :>> id = "6052bfc3-b4c3-430d-9c5e-abe13548f097"; :>> title = "Sprint 619 review gate — three passes per D0172"; :>> createdAt = "2026-09-09"; :>> createdBy = "claudeOpus5"; :>> method = VerificationMethod::inspect; :>> procedureText = "Reviewed against the DoD: a marker naming a step the plan carries is accepted under the plan's judge (test 1); the plan AUTO-ACCEPTED stays proposed naming clause b (test 3); a step the plan does not name stays proposed naming clause c with the searched lengths (test 2); a plan covering a plan is refused by construction (assess refuses a plan whose acceptance note carries PLAN-COVERED, clause b) and a Decision cannot be its own plan (the self clause); the guard fails a fixture whose plan dropped the step (test 5); and the live case - D0396 records plan d0375 step plan-covers-step and is accepted at record time because D0375's consequences name it."; }
    // RAN: reviewed vs DoD: accept under plan judge (test1); clause b on AUTO-ACCEPTED plan (test3); clause c with lengths (test2); plan-covers-plan and self refused by construction; guard fails on dropped step (test5); live D0396 accepted because D0375 consequences name plan-covers-step
    part planCoversStepReviewGateR1 : TestResult { :>> id = "b8f34dba-e21f-4e3f-a2db-ece19c9251cc"; :>> outcome = VerdictKind::pass; :>> judgedAgainst = "216018767b33f8837870e96503aa9e526a34aca5"; :>> judgedAt = "2026-09-08"; :>> judgedBy = "claudeOpus5"; }
    verification planCoversStepCloseOutGate : Test { :>> id = "2aa4d441-ff73-46b2-b5d5-616b93144f80"; :>> title = "Sprint 619 closeOut gate (autonomous, D0049)"; :>> createdAt = "2026-09-09"; :>> createdBy = "claudeOpus5"; :>> method = VerificationMethod::inspect; :>> procedureText = "Sprint 619 closes when dcSignedPlanCoversItsNamedStepsDoD carries a pass at the commit that carries the module, the record branch, the guard, the tests and the live D0396."; }
    // RAN: DoD pass on storyPlanCoversStepDoD and dcSignedPlanCoversItsNamedStepsDoD at this SHA; the live D0396 is accepted
    part planCoversStepCloseOutGateR1 : TestResult { :>> id = "579076e8-fc0b-48f5-a42c-11eb646400ea"; :>> outcome = VerdictKind::pass; :>> judgedAgainst = "216018767b33f8837870e96503aa9e526a34aca5"; :>> judgedAt = "2026-09-08"; :>> judgedBy = "claudeOpus5"; }
    verification planCoversStepRetroGate : Test { :>> id = "1617e554-f93f-4750-b281-b9f93cec7523"; :>> title = "Sprint 619 retro gate (autonomous, D0049)"; :>> createdAt = "2026-09-09"; :>> createdBy = "claudeOpus5"; :>> method = VerificationMethod::analyze; :>> procedureText = "Retro held; avoidable-issue scan: no new item - the compound-Decision guard (d0303) flagged the first draft of D0396 for its (a)/(b)/(c) enumeration, which is the guard working as designed; the reworded prose passed. Process improvement: a Decision describing one mechanism's several conditions reads as compound to decision-scaffolding, so such text is written as prose, not a lettered list - already the rule D0303 states."; }
    // RAN: retro held; the compound-guard flag on the first D0396 draft was the guard working; reworded to prose; no new Issue in this commit
    part planCoversStepRetroGateR1 : TestResult { :>> id = "949b81ee-890d-4a39-81a9-4551e7ca57c5"; :>> outcome = VerdictKind::pass; :>> judgedAgainst = "216018767b33f8837870e96503aa9e526a34aca5"; :>> judgedAt = "2026-09-08"; :>> judgedBy = "claudeOpus5"; }
}
