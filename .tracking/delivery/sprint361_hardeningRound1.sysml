// ProjectDeliveryS361 — Sprint 361: hardening round 1. All six findings of critique pass 1 cleared,
// including the one about the audit's own instrument. EXECUTE. 8 pts.
package ProjectDeliveryS361 {
    private import EngineElement::*;
    private import EngineWork::*;
    private import EngineVerification::*;
    private import EngineRelationships::*;

    #CharteredBy dependency from hardening1Story to d0169;

    part hardening1Story : Story {
        :>> id = "0d800640-0814-6640-9b3e-000000300640";
        :>> title = "Sprint 361: hardening round 1 — the audit measures itself, and five findings it produced are cleared (8 pts)";
        :>> createdAt = "2026-08-20"; :>> createdBy = "claudeOpus5"; :>> kind = WorkKind::code; :>> priority = WorkPriority::p0; :>> owner = "claudeOpus5"; :>> estimatedPoints = 8;
    }

    action def DeliveryRunS361 {
        action storyHardening1;
        verification storyHardening1DoD : Test { :>> id = "0d800641-0814-6641-9b3e-000000300641"; :>> method = VerificationMethod::test; :>> procedureText = "DELIVERED BACKLOG ITEMS: dcAuditInstrument, dcHelpFromDispatch, dcProcessEnforcement, dcDecisionFollowThrough, dcActualHoursOrRetire, dcCharterProvenanceSplit. Clears issue171-176 under D0169. MEASURED BEFORE AND AFTER, same tree: help coverage 40/75 (53%) to 75/75 (100%); process enforcement 11/24 enforced with 13 indistinguishable unknowns, now 11 enforced + 9 declared-unenforceable + 4 undeclared (83% accounted); decision promises 0 declared, now 4 declared with 1 unbuilt - D0161's `.knowledge/`, left visible deliberately; `decision_chartered` 306 split into 12 decision_rooted + 294 decision_ungrounded; `actualHours` demoted from a discipline metric to `estimationFeedbackIndicator`. NEW: `keel hardening` (3 lenses), `const CATALOGUE` + the coverage test, `.engine/contracts/process-enforcement.toml`, `.engine/contracts/decision-artifacts.toml`. validate 393 clean; check-engine clean; 38 guards ALL PASS; 191 tests; clippy clean."; }
        part storyHardening1DoDR1 : TestResult { :>> id = "0d800642-0814-6642-9b3e-000000300642"; :>> outcome = VerdictKind::pass; :>> judgedAgainst = "8940040"; :>> judgedAt = "2026-08-20"; :>> judgedBy = "claudeOpus5"; }
    }

    verification h1RefineGate : Test { :>> id = "0d800643-0814-6643-9b3e-000000300643"; :>> title = "Sprint 361 refine gate (DoR)"; :>> createdAt = "2026-08-20"; :>> createdBy = "claudeOpus5"; :>> method = VerificationMethod::inspect; :>> procedureText = "DoR. Six findings, and the ORDER was chosen rather than taken from the list: issue171 (the instrument) first, because it is the one that makes the other five re-checkable instead of re-derivable, and because it supplies the before/after measurements the other five are judged by. Two findings needed a route decision: issue173 and issue174 both look like they want a field on a frozen type, and both were answered with a DECLARED CONTRACT instead - neither is a property OF the item, both are claims about the tree checked against the tree, so neither needs invariant 5's sign-off. estimatedPoints=8."; }
    part h1RefineGateR1 : TestResult { :>> id = "0d800644-0814-6644-9b3e-000000300644"; :>> outcome = VerdictKind::pass; :>> judgedAgainst = "8940040"; :>> judgedAt = "2026-08-20"; :>> judgedBy = "claudeOpus5"; }

    verification h1StandupGate : Test { :>> id = "0d800645-0814-6645-9b3e-000000300645"; :>> title = "Sprint 361 standup gate"; :>> createdAt = "2026-08-20"; :>> createdBy = "claudeOpus5"; :>> method = VerificationMethod::inspect; :>> procedureText = "Approach: build the lens, then let the lens grade the fix. Every number in the DoD is read from `keel hardening` rather than from a fresh probe, which is the point of having built it - the fix and the measurement now share one definition, so they cannot disagree about whether the fix worked. No blockers. ONE THING RULED OUT UP FRONT: writing 13 guards to make the enforcement number green. A guard cannot be conjured for a judgment, and the cheapest way to make that ratio green is a guard that checks nothing."; }
    part h1StandupGateR1 : TestResult { :>> id = "0d800646-0814-6646-9b3e-000000300646"; :>> outcome = VerdictKind::pass; :>> judgedAgainst = "8940040"; :>> judgedAt = "2026-08-20"; :>> judgedBy = "claudeOpus5"; }

    verification h1ImplementGate : Test { :>> id = "0d800647-0814-6647-9b3e-000000300647"; :>> title = "Sprint 361 implement gate"; :>> createdAt = "2026-08-20"; :>> createdBy = "claudeOpus5"; :>> method = VerificationMethod::test; :>> procedureText = "THE LENS CAUGHT ITSELF TWICE AND THAT IS THE RESULT I WOULD KEEP. Its help probe first looked for `fn usage(`, which does not exist - the function is `print_usage` - so it read an empty help text and reported 0 of 75 documented. Corrected, it read 40 of 75, matching the hand count. Then the fix for issue172 moved the help lines into a `const CATALOGUE` and it reported 1 of 75. BOTH FAILURES WERE ABSURD RATHER THAN PLAUSIBLE, which is the entire argument for a lens over a regex: a mis-aimed lens fails loudly, a mis-written probe fails credibly - and four probes had already failed credibly in the pass that produced these findings. THE CONTRACTS CAN BE WRONG AND WERE: I entered two false promises into decision-artifacts.toml - `keel-cli/src/hook.rs`, which does not exist because the hook lives in `main.rs`, and `.engine/contracts/activation.toml`, which is absent BY DESIGN since no manifest means everything is active - and the lens dutifully reported two false gaps until I corrected them. D0134 and D0138 promised CAPABILITIES, not files. That cost is the right cost: a declared contract can be wrong out loud, where an undeclared assumption is wrong silently. THE COVERAGE TEST WAS VERIFIED BOTH WAYS: a dispatch arm with no catalogue line was added deliberately, and the test failed naming `undocumented-thing`."; }
    part h1ImplementGateR1 : TestResult { :>> id = "0d800648-0814-6648-9b3e-000000300648"; :>> outcome = VerdictKind::pass; :>> judgedAgainst = "8940040"; :>> judgedAt = "2026-08-20"; :>> judgedBy = "claudeOpus5"; }

    verification h1ReviewGate : Test { :>> id = "0d800649-0814-6649-9b3e-000000300649"; :>> title = "Sprint 361 review gate"; :>> createdAt = "2026-08-20"; :>> createdBy = "claudeOpus5"; :>> method = VerificationMethod::inspect; :>> procedureText = "Reviewed. WHAT I REFUSED: making the enforcement ratio green by writing guards, and making the charter number green by reclassifying. `decision_ungrounded` reads 294 of 360 - 82% of this project's delivery work is chartered by a Decision resting on nothing but my own judgment - and D0064 permits every one of them, which is precisely why the old single number was useless. I could have defined `grounded` loosely enough to move most of the 294 and I did not: grounded means an edge to a Statement, UserStory or Need, and nothing else. THE NUMBER IS SUPPOSED TO BE UNCOMFORTABLE. WHAT I WOULD DEFEND HARDEST is the three-bucket enforcement split, because the two-bucket version was actively misleading in BOTH directions: it made a definition-of-done look like technical debt, and it hid four cases where a guard genuinely could exist (actorEnrollment, deploy, distributedCollaboration, migration - D0108's ownership rule is a property of a diff and nothing checks it). Those four are recorded as `admittedGap = true`, which is a worse state than undeclared and is meant to read that way. HONEST LIMIT, stated in the Decision: `keel hardening` reads the repo's `main.rs`, so it audits the SOURCE TREE and not an installed binary."; }
    part h1ReviewGateR1 : TestResult { :>> id = "0d80064a-0814-664a-9b3e-00000030064a"; :>> outcome = VerdictKind::pass; :>> judgedAgainst = "8940040"; :>> judgedAt = "2026-08-20"; :>> judgedBy = "claudeOpus5"; }

    verification h1CloseOutGate : Test { :>> id = "0d80064b-0814-664b-9b3e-00000030064b"; :>> title = "Sprint 361 closeOut gate (autonomous, D0049)"; :>> createdAt = "2026-08-20"; :>> createdBy = "claudeOpus5"; :>> method = VerificationMethod::inspect; :>> procedureText = "Autonomous closeOut (D0049). All six findings of pass 1 cleared; D0169 PROPOSED and unsigned. Doc-sync rides along: CLAUDE.md gains `hardening` in the orient lens list and the two new contracts in the adoption bullet. FOUR ITEMS DELIBERATELY LEFT VISIBLE RATHER THAN CLOSED: D0161's `.knowledge/` stays unbuilt and now REPORTED, since the lens exists to surface it; and the four admitted enforcement gaps stay open, because writing four guards to clear a number I created this sprint would be the Goodhart the Decision argues against. Both are recorded as state, not as prose. validate 393 clean; check-engine clean; 38 guards ALL PASS; 191 tests; clippy clean."; }
    part h1CloseOutGateR1 : TestResult { :>> id = "0d80064c-0814-664c-9b3e-00000030064c"; :>> outcome = VerdictKind::pass; :>> judgedAgainst = "8940040"; :>> judgedAt = "2026-08-20"; :>> judgedBy = "claudeOpus5"; }

    verification h1RetroGate : Test { :>> id = "0d80064d-0814-664d-9b3e-00000030064d"; :>> title = "Sprint 361 retro gate (autonomous, D0049)"; :>> createdAt = "2026-08-20"; :>> createdBy = "claudeOpus5"; :>> method = VerificationMethod::analyze; :>> procedureText = "Autonomous retro (D0049) under D0131's retroTrack. WELL: (1) the instrument was built FIRST and then used to grade its own sprint, so the fix and the measurement share one definition; (2) both of the lens's own misfires were caught by the lens rather than by inspection, and both produced absurd numbers rather than plausible ones - the property that makes this better than a regex; (3) two findings that looked like frozen-schema changes were answered with declared contracts, so invariant 5 was never touched; (4) the enforcement ratio was NOT made green by writing guards, and the reason is recorded in the Decision rather than left as restraint nobody can see; (5) `decision_ungrounded` at 294 was reported rather than defined away. AVOIDABLE-ISSUE: a shell heredoc mangled content for the FOURTH time this session and I used one anyway, having written the rule down twice - once in sprint 360's own retro, one turn earlier. The rule is not the problem; reaching for the shell when the edit feels mechanical is. SECOND AVOIDABLE-ISSUE: I authored two false promises into a contract before checking that the files existed - `hook.rs` and `activation.toml`. Declaring a promise is authoring a fact, and I authored two wrong ones without running `ls`. The lens caught it, which is the system working, but the lens should not have had to. Estimate 8 pts, delivered."; }
    part h1RetroGateR1 : TestResult { :>> id = "0d80064e-0814-664e-9b3e-00000030064e"; :>> outcome = VerdictKind::pass; :>> judgedAgainst = "8940040"; :>> judgedAt = "2026-08-20"; :>> judgedBy = "claudeOpus5"; }
}
