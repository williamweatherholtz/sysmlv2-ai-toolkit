// ProjectDeliveryS491 — Sprint 491: keelw: the committed wrapper that resolves only the pin. EXECUTE. 5 pts.
package ProjectDeliveryS491 {
    private import EngineElement::*;
    private import EngineWork::*;
    private import EngineVerification::*;
    private import EngineRelationships::*;

    #CharteredBy dependency from keelWrapperStory to d0251;

    part keelWrapperStory : Story {
        :>> id = "e741d799-cc9c-4a65-9ffd-52edfe748ca4";
        :>> title = "Sprint 491: keelw - fetch exactly the pin, verify the committed checksum, never fall back to PATH (5 pts)";
        :>> createdAt = "2026-08-29"; :>> createdBy = "claudeOpus5"; :>> kind = WorkKind::code; :>> priority = WorkPriority::p0; :>> owner = "claudeOpus5"; :>> estimatedPoints = 5;
    }

    action def DeliveryRunS491 {
        action storyKeelWrapper;
        verification storyKeelWrapperDoD : Test { :>> id = "e4f6624d-05af-4d93-bfcd-8a82c3cfdf29"; :>> method = VerificationMethod::test; :>> procedureText = "Discharges dcKeelWrapper (increment 2, D0251 clause B). A committed POSIX-sh wrapper (keelw) resolves the pin from engine-version.toml against .keel/bin/<version>/; on a miss it downloads THAT VERSION AND NO OTHER from the release origin (KEELW_BASE_URL overrides - a mirror, an air-gapped tree, or a test), verifies the SHA-256 committed in keel-wrapper.toml, caches, execs. Refuses on: checksum mismatch (caching nothing), missing checksum entry (never trust-on-first-use), unreachable origin with an empty cache (instructions, NEVER PATH). keel init ships keelw + a starter keel-wrapper.toml and SEEDS the cache with the running binary, so a fresh project works offline immediately - init itself just proved that binary runs. VERIFY: five Gherkin scenarios in wrapper_resolves_only_the_pin.rs, written RED first (keelw did not exist); end-to-end init->sh keelw version on the seeded cache; 19 suites 0 FAILED.: DELIVERED BACKLOG ITEMS: <items>. <what done means, verified how>."; }
        // RAN: // RAN: wrapper_resolves_only_the_pin.rs RED (script absent) -> GREEN 5/5; live end-to-end init -> sh keelw version on the seeded cache, offline; clippy -D warnings clean; cargo test --workspace --release 19 suites 0 FAILED
        part storyKeelWrapperDoDR1 : TestResult { :>> id = "598bc8c6-5ebb-4318-9157-c66584fa258a"; :>> outcome = VerdictKind::pass; :>> judgedAgainst = "b7403e4"; :>> judgedAt = "2026-08-29"; :>> judgedBy = "claudeOpus5"; }
    }

    verification keelWrapperRefineGate : Test { :>> id = "48e3766a-ba59-4e27-a290-81b5d2c23d57"; :>> title = "Sprint 491 refine gate (DoR)"; :>> createdAt = "2026-08-29"; :>> createdBy = "claudeOpus5"; :>> method = VerificationMethod::inspect; :>> procedureText = "READY: chartered by accepted D0251; asset names mirror release.yml's matrix verbatim (keel-linux-x86_64, keel-macos-aarch64, keel-windows-x86_64.exe), read from the workflow rather than assumed."; }
    verification keelWrapperStandupGate : Test { :>> id = "47f5af66-cabf-4616-afe4-35d101330380"; :>> title = "Sprint 491 standup gate"; :>> createdAt = "2026-08-29"; :>> createdBy = "claudeOpus5"; :>> method = VerificationMethod::inspect; :>> procedureText = "No external blocker. One test-infrastructure defect found and fixed: the checksum helper keyed its temp file by PID while the harness runs scenarios as parallel THREADS of one process, so two fixtures hashed each other's bytes - the checksum test failing because of a checksum race. Unique-per-call sequence number fixed it."; }
    verification keelWrapperImplementGate : Test { :>> id = "6060095e-7cf3-4301-8f85-a7fbc7412c89"; :>> title = "Sprint 491 implement gate"; :>> createdAt = "2026-08-29"; :>> createdBy = "claudeOpus5"; :>> method = VerificationMethod::test; :>> procedureText = "RAN: wrapper_resolves_only_the_pin.rs RED (script absent) -> GREEN 5/5; live end-to-end: keel init to a temp dir, then sh keelw version ran the SEEDED cache binary with no network and no checksum entry needed. DOC-SYNC RODE THE CHANGE: the skew warning still said 'advisory only - nothing is blocked', and both engine-version.toml stamp comments still said 'read ONLY by the parity warning' - all three falsified by sprint 490 and corrected here in the same motion (the doc-sync rule, applied to the binary's own prose). clippy caught cmd_init at 117/100 lines after the insertion; extracted init_wrapper rather than suppressed."; }
    verification keelWrapperReviewGate : Test { :>> id = "71f6fdd4-06a2-4221-ae3e-b9e57e114455"; :>> title = "Sprint 491 review gate — three passes per D0172"; :>> createdAt = "2026-08-29"; :>> createdBy = "claudeOpus5"; :>> method = VerificationMethod::inspect; :>> procedureText = "THREE PASSES. (1) THE ANTI-AUTO-UPDATE PROPERTY IS TESTED, not asserted: scenario 4 plants a NEWER asset at the origin and asserts the wrapper fetches the pin and nothing else - the exact property that lets D0251 coexist with D0175. (2) NEVER-TOFU: a missing checksum entry refuses even when the download would succeed; the committed contract is the authority, and the first download must never become it. (3) THE SEED IS NOT A BYPASS: seeding copies the binary that is CURRENTLY EXECUTING init into the cache keyed by ITS OWN version - it cannot install anything the operator was not already running."; }
    verification keelWrapperCloseOutGate : Test { :>> id = "05fc1439-ddd8-4065-842d-b8eac88f68e9"; :>> title = "Sprint 491 closeOut gate (autonomous, D0049)"; :>> createdAt = "2026-08-29"; :>> createdBy = "claudeOpus5"; :>> method = VerificationMethod::inspect; :>> procedureText = "CLOSED. Increment 2 of 5. RESIDUALS, named: (a) keel-wrapper.toml in THIS repo and in fresh scaffolds starts with an EMPTY version table - real checksums enter when the release is cut (dcKickoffReady step 2), and until then the wrapper serves only machines with a seeded or hand-installed cache, BY DESIGN (refuse beats TOFU); (b) the platform table covers the three release.yml targets - a fourth platform needs both files edited, loudly (unsupported-platform die)."; }
    verification keelWrapperRetroGate : Test { :>> id = "6921ca2e-89ca-4a8c-aff0-4fe8dc4efd8c"; :>> title = "Sprint 491 retro gate (autonomous, D0049)"; :>> createdAt = "2026-08-29"; :>> createdBy = "claudeOpus5"; :>> method = VerificationMethod::analyze; :>> procedureText = "FINDING: the checksum race in the test helper is the same lesson as the write-lock probe pointed at the tree - evidence must come from an artifact the contenders cannot corrupt. The helper now has what the model writes have always had: an identity no concurrent writer shares. SECOND: doc-sync inside BINARY STRINGS (the skew message, the stamp comment) is a surface the doc-sync guard does not scan - prose in format!() literals falsified by a behavior change is found only by the author remembering. Same class as issue246 (counts typed into prose); recorded as observation, not filed - the existing doc-sync machinery would need to read Rust string literals to close it, and that cost/benefit belongs to a human call."; }
}
