// ProjectDeliveryS509 — Sprint 509: the engine wrote a file that locked the project out. EXECUTE. 2 pts.
package ProjectDeliveryS509 {
    private import EngineElement::*;
    private import EngineWork::*;
    private import EngineVerification::*;
    private import EngineRelationships::*;

    #CharteredBy dependency from obligationDeadlockStory to d0276;

    part obligationDeadlockStory : Story {
        :>> id = "7a3e0c94-1b58-4d27-9f06-53c81e274ab3";
        :>> title = "Sprint 509: a project behind its pin can migrate again, and is told what it moved with (2 pts)";
        :>> createdAt = "2026-09-01"; :>> createdBy = "claudeOpus5"; :>> kind = WorkKind::code; :>> priority = WorkPriority::p0; :>> owner = "claudeOpus5"; :>> estimatedPoints = 2;
    }

    action def DeliveryRunS509 {
        action storyObligationDeadlock;
        verification storyObligationDeadlockDoD : Test { :>> id = "9c25b7e0-46f3-4a18-b5d9-08e6231fa74c"; :>> method = VerificationMethod::test; :>> procedureText = "DELIVERED BACKLOG ITEMS: dcObligationDoesNotLockTheTree (resolves issue324). FIRST ITEM of the D0275 migration plan, and first for a reason: a project that cannot migrate cannot take any engine change, so every later step depended on this one. THE LOCK: migrate refuses a dirty tree and its git status sees UNTRACKED files; committing to clean it fails because the pre-commit gate's validate REFUSES under skew (D0251); skew clears only by migrating. The file that sprang it was written by the engine itself - record_obligation under D0176/K7, whose doc comment reasons about deadlock at the FILE level and misses it at the TREE level - and it fires preferentially when a project is already unhealthy. DONE: check_preconditions tolerates an entry that is NEW and under .tracking/obligations/ and .sysml, returns the tolerated entries rather than swallowing them, and migrate PRINTS them. VERIFY: four cases, two of which exist to prove the carve-out stayed narrow rather than that it works."; }
        // RAN: obligation_does_not_lock_the_tree 4/4; the escape and naming cases were observed FAILING against the pre-fix binary with the deadlock's own refusal text in the output; workspace suite 454 passed / 0 failed
        part storyObligationDeadlockDoDR1 : TestResult { :>> id = "0e73a5f8-2c91-4b64-8a07-1d5f6392ce80"; :>> outcome = VerdictKind::pass; :>> judgedAgainst = "0e001a6"; :>> judgedAt = "2026-09-01"; :>> judgedBy = "claudeOpus5"; }
    }

    verification obligationDeadlockRefineGate : Test { :>> id = "1f84d6b2-53a7-4e09-9c31-72b0485ea6d1"; :>> title = "Sprint 509 refine gate (DoR)"; :>> createdAt = "2026-09-01"; :>> createdBy = "claudeOpus5"; :>> method = VerificationMethod::inspect; :>> procedureText = "READY on evidence I did not produce: a downstream session hit the lock, described all three legs, and each was verified here at file:line before any work started - migrate.rs:652-687, main.rs:226-230, main.rs:188, write.rs:471-481. The remedy and its two rejected alternatives were written into the task's DoD before implementation, so the acceptance criterion existed first."; }
    verification obligationDeadlockStandupGate : Test { :>> id = "2a95e7c3-64b8-4f10-8d42-83c1596fb7e2"; :>> title = "Sprint 509 standup gate"; :>> createdAt = "2026-09-01"; :>> createdBy = "claudeOpus5"; :>> method = VerificationMethod::inspect; :>> procedureText = "THE RISK IN THIS SPRINT IS OVER-WIDENING, not under-fixing. Weakening a refusal is the easy way to make a deadlock go away and the easy way to lose the property the refusal existed for. So the carve-out was written to the narrowest form that breaks the cycle - one directory, new entries only - and HALF the test suite asserts what is STILL refused. A single happy-path case would have passed against a fix that let migrate run on any dirty tree."; }
    verification obligationDeadlockImplementGate : Test { :>> id = "3b06f8d4-75c9-4021-9e53-94d267a0c8f3"; :>> title = "Sprint 509 implement gate"; :>> createdAt = "2026-09-01"; :>> createdBy = "claudeOpus5"; :>> method = VerificationMethod::test; :>> procedureText = "RAN: cargo test --release --test obligation_does_not_lock_the_tree -> 4 passed. ARMED per D0253 without contriving it: the first run WAS against the pre-fix binary and printed the deadlock's own refusal - 'uncommitted changes in .tracking/ or .engine/ - refusing to migrate' with '?? .tracking/obligations/' beneath it. cargo build --release clean. WHAT THE TEST FOUND THAT READING THE CODE DID NOT: the first implementation was correct in principle and did NOTHING. git COLLAPSES a wholly-untracked directory to a single entry, so status reported the directory with no filename and the per-file predicate never matched. Fixed by -uall, which also makes the refusal path name actual files instead of a directory the reader must go inspect."; }
    verification obligationDeadlockReviewGate : Test { :>> id = "4c17a9e5-86d0-4132-af64-a5e378b1d904"; :>> title = "Sprint 509 review gate — three passes per D0172"; :>> createdAt = "2026-09-01"; :>> createdBy = "claudeOpus5"; :>> method = VerificationMethod::inspect; :>> procedureText = "THREE PASSES. (1) IS THE EXEMPTION VISIBLE: yes, and that was a deliberate signature change - check_preconditions now RETURNS the tolerated entries instead of returning Option, so the caller must handle them and the natural thing is to print them. A carve-out that could be silent would be a check that quietly stopped working. (2) COULD THIS TOLERATE SOMETHING HOSTILE: the predicate requires new-or-added AND the obligations directory AND a .sysml extension. A file placed there by hand would be tolerated - but placing it requires the same access as editing the tree, so it grants nothing an attacker did not already have, and the migration still gates afterwards. (3) DID I WEAKEN A CONTROL WITHOUT AUTHORITY: worth stating plainly - migrate.rs is NOT on D0209 clause 2's enforcement surface, which covers guards.rs, adherence.rs, .githooks/ and CI workflows. So this change needed no signed Decision and one was recorded anyway. The coverage gap is named in D0276 rather than quietly relied on."; }
    verification obligationDeadlockCloseOutGate : Test { :>> id = "5d28b0f6-97e1-4243-b075-b6f489c2ea15"; :>> title = "Sprint 509 closeOut gate (autonomous, D0049)"; :>> createdAt = "2026-09-01"; :>> createdBy = "claudeOpus5"; :>> method = VerificationMethod::inspect; :>> procedureText = "CLOSED. issue324 resolved, four cases, armed. Step 1 of 5 in the D0275 migration plan; the next is D0252 clause A's capability declaration, which is D0273's stated prerequisite."; }
    verification obligationDeadlockRetroGate : Test { :>> id = "6e39c107-a8f2-4354-c186-c705a0d3fb26"; :>> title = "Sprint 509 retro gate (autonomous, D0049)"; :>> createdAt = "2026-09-01"; :>> createdBy = "claudeOpus5"; :>> method = VerificationMethod::analyze; :>> procedureText = "TWO FINDINGS. (1) THE FIRST FIX WAS CORRECT AND INERT. The predicate read exactly as intended and matched nothing, because git collapses an untracked directory to one entry - a fact about the tool, not about the logic, and invisible to any amount of re-reading. This is the second time today that running a thing beat reasoning about it (the other: the library remote turned out to be carrying the corrupted unit I had assumed stayed local). The generalisable form: when a predicate consumes another tool's OUTPUT FORMAT, the format is an assumption and must be observed rather than recalled. (2) THE KEYSTONE LOCK DOES NOT COVER SAFETY REFUSALS THAT ARE NOT GUARDS. srMigrationIsReversible is a SystemRequirement; migrate's refusals are what satisfy it; migrate.rs is not on the enforcement surface, so those refusals can be weakened with no signature. I recorded a Decision voluntarily, which is exactly the manual vigilance D0047 rejects as a control. Left OPEN rather than fixed: the obvious widening - lock all of keel-cli/src - would make every code change need a signature and is worse than the gap. A narrower answer would be to derive the locked set from what SystemRequirements actually cite, which is a real proposal and not one to make in a retro."; }
}
