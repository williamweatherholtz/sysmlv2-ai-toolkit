// ProjectDeliveryS467 — Sprint 467: an AI-judged test result records what it ran, and the over-claim rate becomes a measured number instead of a policed sentence. EXECUTE. 4 pts.
package ProjectDeliveryS467 {
    private import EngineElement::*;
    private import EngineWork::*;
    private import EngineVerification::*;
    private import EngineRelationships::*;

    #CharteredBy dependency from evidenceCitedStory to d0232;

    part evidenceCitedStory : Story {
        :>> id = "0ba17870-256d-4d02-9317-49ca6c7723c8";
        :>> title = "Sprint 467: the third control did not survive calibration (4 pts)";
        :>> createdAt = "2026-08-25"; :>> createdBy = "claudeFable5"; :>> kind = WorkKind::code; :>> priority = WorkPriority::p0; :>> owner = "claudeFable5"; :>> estimatedPoints = 4;
    }

    action def DeliveryRunS467 {
        action storyEvidenceCited;
        verification storyEvidenceCitedDoD : Test { :>> id = "c68cb209-7911-43dc-9ab3-11cac0c1478d"; :>> method = VerificationMethod::test; :>> procedureText = "DELIVERED: dcEvidenceCited (resolves issue266; D0232). The human named the problem directly - I very often over-claim, one test for one scenario reported as though the thing were now perfect - and asked for a SYSTEMIC fix rather than a case-by-case correction. They also corrected the aim: governance is here to constrain and check the AI and other work, never them. MEASURED FIRST: of 5135 recorded TestResults, exactly ONE recorded what produced it, so every pass in this model is a testimony no third party can re-derive, and the 3.9 percent fail rate over 5120 results is the signature of a system recording that work happened rather than testing whether it worked. BUILT: guard 52 evidence-cited requires an AI-judged method=test result to carry a RAN receipt naming what produced the verdict, written by append-result --evidence as a structured comment since schema core is frozen, forward-only from 2026-08-25; keel attestation reports the census by judge kind, reading 4749 AI-judged results with 1146 exercised at 0 percent receipted against 318 human judgments correctly out of scope. A HUMAN-JUDGED RESULT IS NEVER IN SCOPE, by design rather than as a courtesy, because their word IS the evidence. THE THIRD CONTROL WAS NOT BUILT AS ASKED: gating verdict WORDING was calibrated three times against the real corpus and failed every time, at 111, 35 and finally 0 percent precision on live data, so it ships as part of the census indicator with the false-positive counts recorded."; }
        // RAN: cargo test --lib a_receipt_is_demanded_of_the_ai_and_never_of_the_human -> 1 passed (4 directions incl. the human exemption); keel guard evidence-cited -> 5 scanned 0 violations; keel attestation . -> ai 4749/1146 exercised, human 318 out of scope; cargo test --workspace -> 271+9+2+1+32 passed
        part storyEvidenceCitedDoDR2 : TestResult { :>> id = "cc855790-bb2a-4419-a634-e5f60722db07"; :>> outcome = VerdictKind::pass; :>> judgedAgainst = "c84671a3f005feb4171d3087a0e11f76d6d81046"; :>> judgedAt = "2026-08-25"; :>> judgedBy = "claudeFable5"; }
    }

    verification evidenceCitedRefineGate : Test { :>> id = "eebe508f-4eda-4e19-abb8-3547f2acda56"; :>> title = "Sprint 467 refine gate (DoR)"; :>> createdAt = "2026-08-25"; :>> createdBy = "claudeFable5"; :>> method = VerificationMethod::inspect; :>> procedureText = "DoR. Resolves issue266, raised by the human as a systemic question about attestation honesty after they observed the over-claiming pattern directly. Scope: measure the gap, build what calibrates, and record honestly what does not. 4 points."; }
    part evidenceCitedRefineGateR2 : TestResult { :>> id = "b708c4f3-35c7-4228-8cc9-19dfe32157e2"; :>> outcome = VerdictKind::pass; :>> judgedAgainst = "c84671a3f005feb4171d3087a0e11f76d6d81046"; :>> judgedAt = "2026-08-25"; :>> judgedBy = "claudeFable5"; }
    verification evidenceCitedStandupGate : Test { :>> id = "039ddba8-0ca6-46bb-b38b-68886c98bf95"; :>> title = "Sprint 467 standup gate"; :>> createdAt = "2026-08-25"; :>> createdBy = "claudeFable5"; :>> method = VerificationMethod::inspect; :>> procedureText = "Approach: measure the corpus BEFORE writing any rule, because a guard that fires on real prose teaches the author to route around the write path - which is where every other check lives. Build the human exclusion in from the start rather than bolting it on, since the human's correction about aim is a design constraint and not a caveat. guards.rs and the write path are keystone-locked, so D0232 co-commits as a SafetyChange. No blockers."; }
    part evidenceCitedStandupGateR2 : TestResult { :>> id = "cc9fa0fd-9abe-4ea4-86a1-f2780c8c73ea"; :>> outcome = VerdictKind::pass; :>> judgedAgainst = "c84671a3f005feb4171d3087a0e11f76d6d81046"; :>> judgedAt = "2026-08-25"; :>> judgedBy = "claudeFable5"; }
    verification evidenceCitedImplementGate : Test { :>> id = "fbb1300c-4d68-4bbe-96bb-0aa2ec306698"; :>> title = "Sprint 467 implement gate"; :>> createdAt = "2026-08-25"; :>> createdBy = "claudeFable5"; :>> method = VerificationMethod::test; :>> procedureText = "Verified in four directions by test, not by inspection: an AI method=test result with no receipt is REFUSED; the same with a receipt passes; a HUMAN-judged result is NOT EVEN SCANNED; a pre-cutover date is out of scope. Live: the guard fired immediately on my own five results from twenty minutes earlier, which now carry receipts naming the commands that produced them, and it reads 5 scanned 0 violations after. keel attestation reports 4749 / 1146 / 0 percent and 318 human results separately. validate 519 + 52 guards ALL PASS + clippy 0 errors + 271 + 9 + 2 + 1 + 32 tests."; }
    // RAN: cargo test --lib a_receipt_is_demanded_of_the_ai_and_never_of_the_human -> 1 passed (AI-no-receipt refused, AI-with-receipt clean, HUMAN not scanned, pre-cutover out of scope); keel guard evidence-cited -> 5 scanned 0 violations after receipts written; keel attestation . -> ai 4749/1146 exercised / human 318 out of scope; cargo test --workspace -> 271+9+2+1+32
    part evidenceCitedImplementGateR3 : TestResult { :>> id = "8526e74e-d7fb-473c-978d-4ced75138416"; :>> outcome = VerdictKind::pass; :>> judgedAgainst = "c84671a3f005feb4171d3087a0e11f76d6d81046"; :>> judgedAt = "2026-08-25"; :>> judgedBy = "claudeFable5"; }
    verification evidenceCitedReviewGate : Test { :>> id = "d73a3a40-e3cc-4495-87b9-d5915ac6aead"; :>> title = "Sprint 467 review gate — three passes per D0172"; :>> createdAt = "2026-08-25"; :>> createdBy = "claudeFable5"; :>> method = VerificationMethod::inspect; :>> procedureText = "PASS 1, CLAIMS: every figure is a quoted read-back - the 5135 results with one receipt, the three calibration false-positive counts of 111, 35 and 1, the census rows. PASS 2, BOUNDARY: (i) THE BIG ONE, and it is stated in the Decision rather than buried: none of this constrains what I say in CHAT, which is where the human actually experiences the over-claiming, and CLAUDE.md already concedes no gate can read conversational output; (ii) the guard checks that a receipt EXISTS, never that it is true - I could write a command I did not run, and nothing re-executes it, so this raises the cost of a false claim rather than closing it; (iii) forward-only means 983 historical test-results stay unreceipted, so the census percentage will climb slowly and cannot be read as a quality trend for months; (iv) method is still MY choice, so an inspection stamped as a test now needs a fabricated receipt instead of no receipt - a higher bar, not an impossible one. PASS 3, OWN DIFF: I shipped the coverage-claim guard, watched it run 0-for-2 on my own newest work, narrowed it, watched it still fail, and removed it. The right conclusion was available from the FIRST calibration - two earlier language rules had already failed at 111 and 35 - and I built it anyway because the human had asked for all three. Doing what was asked is not a reason to ship a control that does not work; saying so is. WHAT A REVIEWER SHOULD ATTACK: whether a receipt nobody re-executes is meaningfully better than no receipt."; }
    part evidenceCitedReviewGateR2 : TestResult { :>> id = "2be0dd09-9dae-4486-9d9b-2de0eea1e2da"; :>> outcome = VerdictKind::pass; :>> judgedAgainst = "c84671a3f005feb4171d3087a0e11f76d6d81046"; :>> judgedAt = "2026-08-25"; :>> judgedBy = "claudeFable5"; }
    verification evidenceCitedCloseOutGate : Test { :>> id = "f8d6aaad-ff56-4bd0-bc2a-042878742051"; :>> title = "Sprint 467 closeOut gate (autonomous, D0049)"; :>> createdAt = "2026-08-25"; :>> createdBy = "claudeFable5"; :>> method = VerificationMethod::inspect; :>> procedureText = "Autonomous closeOut (D0049). issue266 resolved. A pass by an AI now owes a receipt; a pass by the human owes nothing, which is where the line belongs. The reported verification numbers should be expected to get WORSE as method=test claims either gain receipts or become honest inspections. validate + 52 guards + check-engine + rules green at c84671a."; }
    part evidenceCitedCloseOutGateR2 : TestResult { :>> id = "f42ddf42-c55c-4eab-950b-c26d72678068"; :>> outcome = VerdictKind::pass; :>> judgedAgainst = "c84671a3f005feb4171d3087a0e11f76d6d81046"; :>> judgedAt = "2026-08-25"; :>> judgedBy = "claudeFable5"; }
    verification evidenceCitedRetroGate : Test { :>> id = "c5525a52-6ef9-49f2-95bd-611b5a045af6"; :>> title = "Sprint 467 retro gate (autonomous, D0049)"; :>> createdAt = "2026-08-25"; :>> createdBy = "claudeFable5"; :>> method = VerificationMethod::analyze; :>> procedureText = "Autonomous retro (D0049). AVOIDABLE-ISSUE SCAN under rcRecurrence: (1) THE FINDING: I had already measured that language policing does not calibrate - 111 false positives on one rule, 35 on another - and then built a third language rule anyway because it was on the list. The evidence to stop was in hand before I started. When a class of control has failed calibration twice, the third instance needs a reason it is different, not a turn of the crank. (2) The char-boundary panic in the new report is a bug I fixed in the injection detector earlier this same session and reproduced verbatim - the second time is the argument for making it a shared helper rather than a habit. (3) The human's correction about AIM was load-bearing and I would not have arrived at it: a first draft would plausibly have demanded receipts from every result regardless of judge, which would have aimed governance at the one party it must never bind. WELL: measuring before writing each rule is what made the negative result legible rather than a matter of taste. Estimate 4 pts, delivered 4."; }
    part evidenceCitedRetroGateR2 : TestResult { :>> id = "08094df4-2c47-4514-a7c2-8aeabedc2235"; :>> outcome = VerdictKind::pass; :>> judgedAgainst = "c84671a3f005feb4171d3087a0e11f76d6d81046"; :>> judgedAt = "2026-08-25"; :>> judgedBy = "claudeFable5"; }
}
