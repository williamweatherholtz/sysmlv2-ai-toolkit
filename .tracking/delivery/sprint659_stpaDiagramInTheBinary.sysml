// ProjectDeliveryS659 — Sprint 659: Close dcStpaDiagramInTheBinary (D0285, D0221): the STPA control-structure diagram is drawn in the binary - keel show control-structure --svg, keel render control-structure --mode graph, and the console's /view/control-structure - byte-for-byte equal to what .engine/tools/stpa_diagram.py drew on the same JSON, the Python tool deleted in the same commit, and the five D0285 layout properties held as unit tests on the layout rather than as a skill's prose. The sprint also carries two findings the port exposed: the control-structure lens itself was nondeterministic across runs (its feedback rows kept HashMap order), and the console's generic viewpoint panel could not reach any renderer whose text began with keel show. EXECUTE. 5 pts.. EXECUTE. 5 pts.
package ProjectDeliveryS659 {
    private import EngineElement::*;
    private import EngineWork::*;
    private import EngineVerification::*;
    private import EngineRelationships::*;

    #CharteredBy dependency from stpaDiagramInTheBinaryStory to d0285;

    part stpaDiagramInTheBinaryStory : Story {
        :>> id = "e3236f64-895e-49c7-b9d2-d2fe125a06af";
        :>> title = "Sprint 659: Close dcStpaDiagramInTheBinary (D0285, D0221): the STPA control-structure diagram is drawn in the binary - keel show control-structure --svg, keel render control-structure --mode graph, and the console's /view/control-structure - byte-for-byte equal to what .engine/tools/stpa_diagram.py drew on the same JSON, the Python tool deleted in the same commit, and the five D0285 layout properties held as unit tests on the layout rather than as a skill's prose. The sprint also carries two findings the port exposed: the control-structure lens itself was nondeterministic across runs (its feedback rows kept HashMap order), and the console's generic viewpoint panel could not reach any renderer whose text began with keel show. EXECUTE. 5 pts. (5 pts)";
        :>> createdAt = "2026-09-10"; :>> createdBy = "claudeOpus5"; :>> kind = WorkKind::code; :>> priority = WorkPriority::p0; :>> owner = "claudeOpus5"; :>> estimatedPoints = 5;
    }

    action def DeliveryRunS659 {
        action storyStpaDiagramInTheBinary;
        verification storyStpaDiagramInTheBinaryDoD : Test { :>> id = "51dc7abe-74ff-4c3b-b83a-4cd08154b81f"; :>> method = VerificationMethod::test; :>> procedureText = "The DoD of dcStpaDiagramInTheBinary: keel show control-structure --svg draws the diagram in the binary. keel-cli/src/view/stpa_diagram.rs is a port of the Python tool's layout and serialisation with Python's int/float arithmetic reproduced (Num), and port_is_byte_equal_to_the_python_tool_on_the_same_json holds the render against the golden SVG the Python tool wrote for the fixture JSON (keel-cli/tests/fixtures/stpa/). On the live tree the render function's output equals HEAD's Python tool's output byte for byte on the same JSON; the CLI's stdout carries one more byte, the trailing newline cmd_view0's println! adds to every lens, which the Python tool did not write - stated here, not hidden. The Python tool is deleted in this commit and tool-reference / instruments-declared / cli-surface-declared stay green; the snStpaDiagram Sensor and fbStpaDiagram Feedback are removed with it, because a Sensor declares a measure outside the CLI (D0363) and the diagram is now the cliControlStructure lens, whose channel the control structure derives from the CLI facts. This story resolves issue461 (the control-structure lens's feedback rows varied between runs with the tree unchanged - sensors now walked in item-name order, held by instrument_feedback_rows_are_in_one_order_whatever_the_map_order) and issue462 (the console's generic viewpoint panel fetched /api/computed/show for every renderer beginning keel show - vpCmd now strips the show token too) and issue463 (keel suite --touched measured its changed set to HEAD, so the verifier's pre-commit run of the gate's own set was EMPTY on this very sprint - touched.rs now measures from the merge-base to the working tree plus untracked files under keel-cli). On the live tree the render is byte-equal to the Python tool's once the CR bytes Python's text-mode stdout adds on Windows are removed (the verifier's first comparison read a 218-byte difference that was exactly one CR per line). The five D0285 properties are unit tests on the layout: no_two_segments_share_a_line, every_edge_is_labelled_with_what_passes, every_crossing_carries_a_hop, no_line_passes_through_a_box, control_leaves_bottom_left_and_feedback_enters_bottom_right; plus an_absent_role_is_named_in_the_legend_and_drawn_nowhere and a_non_structure_json_is_refused_not_drawn_empty. The console serves the SVG at /view/control-structure and the safety viewpoint's panel embeds it. The skill (both renderings), the process file, the registry, the instruments file, the CLI facts and CLAUDE.md name the binary command and no longer the tool. VERIFY as the verifier reports: keel suite --touched (the gate's own set, D0432) all passed; clippy -D warnings clean; keel validate, check-engine, guard --no-receipt green; sync-claude --check clean; the live byte comparison against the HEAD copy of the Python tool."; }
        // RAN: verifier receipt 2026-09-10T20:40:42Z: suite --touched 594 passed 0 failed over 8 stems incl. stpa_diagram; clippy 0; validate 750 clean; check-engine clean; guard ALL PASS; sync-claude matches; Rust svg 33884 = Python 33883 + trailing newline (cmp EOF); determinism 3 runs equal; render 1 svg; Python tool deleted, no refs; 3 Resolves edges
        part storyStpaDiagramInTheBinaryDoDR1 : TestResult { :>> id = "363cf613-59e1-4a08-a39f-a4f88c12d13d"; :>> outcome = VerdictKind::pass; :>> judgedAgainst = "34e0ae3a1ef0970b0a72fb703b4ff74b87897e63"; :>> judgedAt = "2026-09-10T20:40:42Z"; :>> judgedBy = "claudeOpus5"; }
    }

    verification stpaDiagramInTheBinaryRefineGate : Test { :>> id = "880aa876-2970-4356-9641-8654958235ca"; :>> title = "Sprint 659 refine gate (DoR)"; :>> createdAt = "2026-09-10"; :>> createdBy = "claudeOpus5"; :>> method = VerificationMethod::inspect; :>> procedureText = "Five points: a thousand-line port whose correctness is judged byte for byte against the artefact it replaces, seven layout tests, four wiring sites (dispatch, render, serve route, console panel), a deletion with its doc-sync across eight files, and whatever the byte comparison turns up. Ready: dcStpaDiagramInTheBinary is head of whats-next after dcCommitDeltaView closed; its charter D0285 is accepted; the Python tool is a single file with no dependency beyond json/html/re, so the port is arithmetic and string building. Known before the tree was read: the positive case for the port is the fixture JSON whose Python SVG is the golden (equal bytes), the negative case is a JSON with no controllers array (refused, not drawn empty); the positive case for the determinism finding is sixty sensors in two independently seeded maps (with the sort removed the test fails on the first pair), the negative case is the sorted walk (five builds equal)."; }
    // RAN: verifier receipt 2026-09-10T20:40:42Z: whats-next head=dcStpaDiagramInTheBinary, charter d0285 accepted, 5 pts; advance step=Refine; guard ALL PASS incl. charter and ceremony
    part stpaDiagramInTheBinaryRefineGateR1 : TestResult { :>> id = "a7d4fb85-1ddb-47ac-80bb-484173e81b5f"; :>> outcome = VerdictKind::pass; :>> judgedAgainst = "34e0ae3a1ef0970b0a72fb703b4ff74b87897e63"; :>> judgedAt = "2026-09-10T20:40:42Z"; :>> judgedBy = "claudeOpus5"; }
    verification stpaDiagramInTheBinaryStandupGate : Test { :>> id = "59a89d53-39b2-4f6a-9004-e3ca66d7ed63"; :>> title = "Sprint 659 standup gate"; :>> createdAt = "2026-09-10"; :>> createdBy = "claudeOpus5"; :>> method = VerificationMethod::inspect; :>> procedureText = "Blocker at the start: none. Sprint 658's commit 34e0ae3 is on origin with CI conclusion success. The one hazard known going in: the port's first live byte comparison may differ for a reason that is not the port's - and it did, in the feedback row order, which turned out to be the lens's own nondeterminism (three runs of keel show control-structure differed at line 20 with nothing in the tree changed). Fixed at the root in control_structure.rs, then the comparison held."; }
    // RAN: verifier receipt 2026-09-10T20:40:42Z: HEAD=34e0ae3 equals origin/main; git status 22 changed paths; suite --touched set non-empty (8 stems) after issue463 fix
    part stpaDiagramInTheBinaryStandupGateR1 : TestResult { :>> id = "6148110f-fa40-4152-8f04-b037c6b0ad61"; :>> outcome = VerdictKind::pass; :>> judgedAgainst = "34e0ae3a1ef0970b0a72fb703b4ff74b87897e63"; :>> judgedAt = "2026-09-10T20:40:42Z"; :>> judgedBy = "claudeOpus5"; }
    verification stpaDiagramInTheBinaryImplementGate : Test { :>> id = "9e1a19d6-c5ca-4bc0-90c5-cb8a7c28390a"; :>> title = "Sprint 659 implement gate"; :>> createdAt = "2026-09-10"; :>> createdBy = "claudeOpus5"; :>> method = VerificationMethod::test; :>> procedureText = "Built: keel-cli/src/view/stpa_diagram.rs - Num (Python int/float semantics: int op int stays int, any float or a division yields a float that prints as repr), Edge / Seg / BoxAt / Label / Layout, layout(&Value) -> Result<Layout, String> (the levels, the boxes, the control channels by 8px lanes, the feedback channels, the verticals at each box's bottom-left for control and bottom-right for feedback, the labels wrapped and placed with leaders, the crossings), svg(&Layout) with the hop arcs computed from Layout::crossings, render_json, control_structure_svg (ViewError::Track) and control_structure_html (the page with the light/dark palette the SVG's CSS variables resolve against). Wired: main.rs dispatch takes --svg on show control-structure; reports.rs render_html routes control-structure --mode graph to the page; serve.rs adds /view/control-structure; console.html's vpCmd strips keel show as well as keel (15 of 30 viewpoint renderers begin with keel show; before this change the generic panel fetched /api/computed/show and got 404 for every one of them - verified by serving a copy of the binary on 7791: GET /api/computed/show 404, GET /api/computed/control-structure 200, GET /view/control-structure 200 with one svg element) and embeds the diagram in an iframe when the command is control-structure. Deleted: .engine/tools/stpa_diagram.py; migrate.rs PORTABLE_TOOLS and init_smoke.rs no longer name it. Doc-sync: .engine/processes/stpa-diagram.sysml header, .engine/skills/stpa-diagram/SKILL.md and .claude/skills/stpa-diagram/SKILL.md, registry.sysml purpose, .tracking/architecture/engine-instruments.sysml (snStpaDiagram and fbStpaDiagram removed: the diagram is a CLI lens now, not an instrument outside it), CLAUDE.md section 2, cli_facts.rs and commands.sysml cliControlStructure invocation and synopsis. Root fix carried: control_structure.rs instrument_feedback walks the sensors in item-name order (it walked the HashMap) with instrument_feedback_rows_are_in_one_order_whatever_the_map_order as the test; after the fix three consecutive runs of the lens are identical (cmp) and the Rust render equals the Python render on the live JSON. Lints: the module allows the numeric-port lints at module level with the reason stated in its doc comment (the casts are the port, the names are the geometry's, every index is into a constant table or a map filled from the list the index came from); the rest were fixed. issue461 (lens nondeterministic, in-field) and issue462 (viewpoint panel unreachable for show-prefixed renderers, code-read then runtime-verified) recorded, both resolved by this sprint's story. Second root fix carried, from the verifier's first report: keel suite --touched read changed modules [] against a tree with twenty edited files, because compute diffed base...HEAD and HEAD equalled origin/main - the verifier had run the gate's set as nothing and reported outcome empty (issue463, in-field). touched.rs compute now diffs from the merge-base of the base and HEAD to the working tree and adds git ls-files --others under keel-cli; the same command then read eight stems including the untracked stpa_diagram module, and the_changed_set_is_the_working_trees_not_heads holds it (probed: fails against the old compute)."; }
    // RAN: verifier receipt 2026-09-10T20:40:42Z: ./target/release/keel-suite.exe suite --touched . changed modules [cli_facts, control_structure, migrate, reports, serve, stpa_diagram, touched, view] passed=594 failed=0 258s; cargo clippy --release -p keel-cli --all-targets -- -D warnings exit=0; keel validate 750 files clean; check-engine clean; guard --no-receipt ALL PASS 0 FAIL; sync-claude --check matches
    part stpaDiagramInTheBinaryImplementGateR1 : TestResult { :>> id = "563404d5-660a-4c0c-bc41-8d3204532d6e"; :>> outcome = VerdictKind::pass; :>> judgedAgainst = "34e0ae3a1ef0970b0a72fb703b4ff74b87897e63"; :>> judgedAt = "2026-09-10T20:40:42Z"; :>> judgedBy = "claudeOpus5"; }
    verification stpaDiagramInTheBinaryReviewGate : Test { :>> id = "df669da2-bde3-45ff-acdb-bfd681c6ec8c"; :>> title = "Sprint 659 review gate — three passes per D0172"; :>> createdAt = "2026-09-10"; :>> createdBy = "claudeOpus5"; :>> method = VerificationMethod::inspect; :>> procedureText = "Three passes (D0172). Substance: the diagram is now a computed view of a computed view - the same binary that computes the structure draws it, so the picture cannot lag the structure, and the five properties the skill used to ask a reader to check by eye are asserted on every cargo test. The byte-equality discipline paid for itself twice: it is what found the lens's nondeterminism (a computed view varying with nothing in the tree changed, which every consumer of the JSON had been living with), and it is what made the port's correctness a fact rather than a resemblance. Record: three Issues, all found by running the thing rather than reading it; the nondeterminism is in-field (observed on the binary, three runs), the console defect is code-read then confirmed at runtime, and the empty touched set is in-field and the most consequential - the D0425 flow's verifier had, for its second sprint, run a set that was empty whenever the previous sprint had landed, and only the verifier's habit of reporting the receipt's own counts rather than the claim exposed it. Stated plainly: the CLI's stdout differs from the Python tool's by one trailing newline that cmd_view0 adds to every lens; the DoD's byte-for-byte clause is met by the render function and the fixture test, and the stdout byte is named in the DoD receipt rather than special-cased away. Not delivered by design: no stored SVG (a view), no change to what the structure computes, no brief republish (D0407 still proposed)."; }
    // RAN: verifier receipt 2026-09-10T20:40:42Z: live byte comparison show control-structure --svg Rust=33884 vs Python HEAD tool (CR stripped)=33883, cmp EOF on Python file after byte 33883 (trailing println newline); determinism 3 runs cmp 0,0; render control-structure --mode graph exit 0, 1 svg; stpa_diagram.py DELETED, git grep snStpaDiagram|fbStpaDiagram no hits
    part stpaDiagramInTheBinaryReviewGateR1 : TestResult { :>> id = "9957e3d4-01aa-4a1c-a9a6-0c3b0d482ef6"; :>> outcome = VerdictKind::pass; :>> judgedAgainst = "34e0ae3a1ef0970b0a72fb703b4ff74b87897e63"; :>> judgedAt = "2026-09-10T20:40:42Z"; :>> judgedBy = "claudeOpus5"; }
    verification stpaDiagramInTheBinaryCloseOutGate : Test { :>> id = "555331ad-7f97-4aae-8b26-caf8ffa5892d"; :>> title = "Sprint 659 closeOut gate (autonomous, D0049)"; :>> createdAt = "2026-09-10"; :>> createdBy = "claudeOpus5"; :>> method = VerificationMethod::inspect; :>> procedureText = "Delivered: keel show control-structure --svg, keel render control-structure --mode graph, the console's /view/control-structure and its safety-panel embed, keel-cli/src/view/stpa_diagram.rs with ten tests and two golden fixtures, the Python tool deleted with its eight doc-sync sites, the control-structure lens made deterministic with its test, keel suite --touched measuring the working tree, issue461, issue462 and issue463 recorded and triaged, dcStpaDiagramInTheBinary's DoD passed. Not delivered: nothing in scope left; the console embed is an iframe of the page rather than an inline svg, which is a choice (the page owns the palette) and not a gap."; }
    // RAN: verifier receipt 2026-09-10T20:40:42Z: #Resolves edges from storyStpaDiagramInTheBinary to issue461, issue462, issue463 (three); DoD names all three; guard issues PASS
    part stpaDiagramInTheBinaryCloseOutGateR1 : TestResult { :>> id = "408f2518-95f6-4d94-a63d-d9eff9cca116"; :>> outcome = VerdictKind::pass; :>> judgedAgainst = "34e0ae3a1ef0970b0a72fb703b4ff74b87897e63"; :>> judgedAt = "2026-09-10T20:40:42Z"; :>> judgedBy = "claudeOpus5"; }
    verification stpaDiagramInTheBinaryRetroGate : Test { :>> id = "a0e06d6c-f1f5-443e-83ea-1856c3e089a4"; :>> title = "Sprint 659 retro gate (autonomous, D0049)"; :>> createdAt = "2026-09-10"; :>> createdBy = "claudeOpus5"; :>> method = VerificationMethod::analyze; :>> procedureText = "Autonomous retro (D0049). AVOIDABLE-ISSUE SCAN: three Issues this sprint. issue463, the touched set measured to HEAD while the verifier runs before the commit: avoidable - the D0432 text says the set is computed from the changed paths and the implementation chose the committed ones; caught only because the verifier reported the receipt's counts (0 passed, 0 failed, outcome empty) instead of echoing the claim, which is precisely the D0425 division of labour doing its work; the control is the_changed_set_is_the_working_trees_not_heads - a scratch repo with a clean tree (known-negative, no stem) and then an uncommitted edit plus an untracked module (known-positive), probed against the old compute (fails on the positive) before the fix was stated. issue461, the lens's row order depending on HashMap seed: avoidable in principle - every lens that pushes rows from a map walk has this exposure - and not caught because nothing compared two runs of any lens byte for byte until a port needed to; the control is the test, and the class-wide question (which other lenses walk a map into rows) is a candidate backlog item rather than a fix smuggled in here. issue462, the generic viewpoint panel stripping only keel from a renderer string: avoidable by a test that fetched every declared viewpoint's renderer through the panel's own path; no such test exists, so the fix is a two-token regex and the residual is that the console's JS has no runtime test in the suite. Finding 3, about D0425: the verifier-recorder split held for the second sprint running and the primary's time went to the port; the one place the split leaked was the clippy census, which the primary ran itself because it needed the messages to fix the code - that is substance, not checking. Finding 5, found at the commit: the verifier's keel guard --no-receipt ran over the unstaged tree and reported ALL PASS, and the pre-commit hook refused the same edits on process-change - the index-reading guards scan git diff --cached, so before git add they scan nothing (issue464, in-field, High; resolver dcGuardReadsTheWorkingTreeOutsideTheHook: outside a hook the locked-surface guards read the working tree). The stpa-diagram process file's renderer doc-sync needed a marked Decision, recorded as D0433 and co-committed. Finding 4, hygiene: the one heredoc denial (a backslash-n in a Python patch) was followed immediately by the Write tool; every other patch went through textpatch with an anchor and none missed."; }
    // RAN: verifier receipt 2026-09-10T20:40:42Z: retro section recorded in FILE (three-issue avoidable scan incl. issue463 touched-set); guard ceremony PASS; all 14 verifier items no discrepancy
    part stpaDiagramInTheBinaryRetroGateR1 : TestResult { :>> id = "9ac6b18e-99de-40cb-9d7d-836642ad39b2"; :>> outcome = VerdictKind::pass; :>> judgedAgainst = "34e0ae3a1ef0970b0a72fb703b4ff74b87897e63"; :>> judgedAt = "2026-09-10T20:40:42Z"; :>> judgedBy = "claudeOpus5"; }
}
