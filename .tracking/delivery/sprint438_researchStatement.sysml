// ProjectDeliveryS438 — Sprint 438: the RESEARCH statement becomes a first-class flag (D0207 completion): keel record decision --research, rendered in the issue and required by guard 48. EXECUTE. 1 pts.
package ProjectDeliveryS438 {
    private import EngineElement::*;
    private import EngineWork::*;
    private import EngineVerification::*;
    private import EngineRelationships::*;

    #CharteredBy dependency from researchStatementStory to d0207;

    part researchStatementStory : Story {
        :>> id = "666bf8c1-8eb3-4bf3-a025-95811b9e7062";
        :>> title = "Sprint 438: the ask states its homework (1 pts)";
        :>> createdAt = "2026-08-24"; :>> createdBy = "claudeFable5"; :>> kind = WorkKind::code; :>> priority = WorkPriority::p0; :>> owner = "claudeFable5"; :>> estimatedPoints = 1;
    }

    action def DeliveryRunS438 {
        action storyResearchStatement;
        verification storyResearchStatementDoD : Test { :>> id = "ac0ef6c9-fc8d-40fa-9af7-2981d87d6f2e"; :>> method = VerificationMethod::test; :>> procedureText = "DELIVERED: the research-statement leg of D0207 clause 3, discovered missing the moment a real fork (D0208 redTeamScope) needed to reach out. keel record decision gains --research: a first-class flag emitting a structured // RESEARCH: comment (not a frozen-schema field, invariant 5) that BOTH guard 48 and keel decision-card read, so 'what did you look at before asking' travels all the way to the human's GitHub issue. Guard 48 tightened from 'the token RESEARCH appears anywhere' to 'a // RESEARCH: line of >= 40 substantive chars' - a hollow token no longer passes. decision-card extracts it; open_decision_issues.py renders a **Research:** section in the issue body. PROVEN on the first real user: D0208 redTeamScope - the control-evaluation SCOPE fork the process-value panel called the cheapest high-value gap - recorded through the flag, clears guard 48 (short name redTeamScope, 3 options each with a COST, 541-char research statement citing Redwood/Greenblatt and ControlConf), and lands as this push's GitHub issue. The two prior call sites (main, serve) updated; serve passes None (a console-recorded decision states research in its own flow when it has one)."; }
        part storyResearchStatementDoDR1 : TestResult { :>> id = "9e796aae-636d-40f9-b958-3749105737ab"; :>> outcome = VerdictKind::pass; :>> judgedAgainst = "ea641a4ec59028fe5674dfc364c60d496db19ac1"; :>> judgedAt = "2026-08-23"; :>> judgedBy = "claudeFable5"; }
    }

    verification researchStatementRefineGate : Test { :>> id = "d16270a9-1af0-4ccf-ba7d-3ec72d5989ad"; :>> title = "Sprint 438 refine gate (DoR)"; :>> createdAt = "2026-08-24"; :>> createdBy = "claudeFable5"; :>> method = VerificationMethod::inspect; :>> procedureText = "DoR. Not a new decision - the completion of D0207's own clause 3, whose guard I built before the emitting flag existed; found when D0208 needed to be raised well. 1 point."; }
    part researchStatementRefineGateR1 : TestResult { :>> id = "4d33c223-e0bb-4bda-82a7-6ccaec6461e6"; :>> outcome = VerdictKind::pass; :>> judgedAgainst = "ea641a4ec59028fe5674dfc364c60d496db19ac1"; :>> judgedAt = "2026-08-23"; :>> judgedBy = "claudeFable5"; }
    verification researchStatementStandupGate : Test { :>> id = "315f6b77-564d-4c94-a9da-7b8b965ab2fb"; :>> title = "Sprint 438 standup gate"; :>> createdAt = "2026-08-24"; :>> createdBy = "claudeFable5"; :>> method = VerificationMethod::inspect; :>> procedureText = "Approach: a structured comment, not a schema attribute - frozen core (invariant 5) stays untouched, and one line serves both the guard and the card, so the research statement cannot drift between what is checked and what the human reads. No blockers."; }
    part researchStatementStandupGateR1 : TestResult { :>> id = "621271f7-13be-4d66-bf6b-0aa141d3f2c9"; :>> outcome = VerdictKind::pass; :>> judgedAgainst = "ea641a4ec59028fe5674dfc364c60d496db19ac1"; :>> judgedAt = "2026-08-23"; :>> judgedBy = "claudeFable5"; }
    verification researchStatementImplementGate : Test { :>> id = "f038ff13-774f-4acc-b302-ba8ffee1b642"; :>> title = "Sprint 438 implement gate"; :>> createdAt = "2026-08-24"; :>> createdBy = "claudeFable5"; :>> method = VerificationMethod::test; :>> procedureText = "Verified by running: keel record decision --research on the real D0208 fork; keel guard judgment-request-quality PASS with the substantive-length check live; keel decision-card d0208 shows research 541 chars and 3 options; a bad-fork negative probe still draws four violations; full keel-cli suite green (231 lib + BDD); clippy clean; validate 486 + all 48 guards green."; }
    part researchStatementImplementGateR1 : TestResult { :>> id = "7238b9ca-0c0d-43bb-a5d3-3fe0d5949ce5"; :>> outcome = VerdictKind::pass; :>> judgedAgainst = "ea641a4ec59028fe5674dfc364c60d496db19ac1"; :>> judgedAt = "2026-08-23"; :>> judgedBy = "claudeFable5"; }
    verification researchStatementReviewGate : Test { :>> id = "89a04596-1d71-471e-8449-cec92889c0c3"; :>> title = "Sprint 438 review gate — three passes per D0172"; :>> createdAt = "2026-08-24"; :>> createdBy = "claudeFable5"; :>> method = VerificationMethod::inspect; :>> procedureText = "PASS 1, CLAIMS: the D0208 card read-back (options 3, research 541) is quoted output. PASS 2, BOUNDARY: research is presence-and-length-checked, not quality-checked - a 40-char hollow statement passes the guard, and only the human's rejection teaches that; stated as the honest floor, same limit the panel's UX lens named for any text bar. PASS 3, OWN DIFF: I shipped guard 48 checking for a RESEARCH token in the sprint that created D0207, but no flag emitted one - the guard could only have been satisfied by hand-editing the token in, which is exactly the forgettable-marker friction D0193/issue213 fixed for #ProspectiveChange; this closes the same gap for research. The lesson: a guard and the write path that satisfies it must ship together. WHAT A REVIEWER SHOULD ATTACK: the 40-char floor is a judgment constant."; }
    part researchStatementReviewGateR1 : TestResult { :>> id = "c12f180e-3e24-48ef-83e9-3c297e46edfd"; :>> outcome = VerdictKind::pass; :>> judgedAgainst = "ea641a4ec59028fe5674dfc364c60d496db19ac1"; :>> judgedAt = "2026-08-23"; :>> judgedBy = "claudeFable5"; }
    verification researchStatementCloseOutGate : Test { :>> id = "782425f2-1d9f-4184-901c-a01e0e8f5af6"; :>> title = "Sprint 438 closeOut gate (autonomous, D0049)"; :>> createdAt = "2026-08-24"; :>> createdBy = "claudeFable5"; :>> method = VerificationMethod::inspect; :>> procedureText = "Autonomous closeOut (D0049). D0207 clause 3 is now fully operational; D0208 rides this push to the human as a well-formed fork issue; validate + all 48 guards green."; }
    part researchStatementCloseOutGateR1 : TestResult { :>> id = "c631f1e7-5a64-478f-823d-074b2f4ca461"; :>> outcome = VerdictKind::pass; :>> judgedAgainst = "ea641a4ec59028fe5674dfc364c60d496db19ac1"; :>> judgedAt = "2026-08-23"; :>> judgedBy = "claudeFable5"; }
    verification researchStatementRetroGate : Test { :>> id = "a58d9935-2880-41e7-843f-b53d831881e6"; :>> title = "Sprint 438 retro gate (autonomous, D0049)"; :>> createdAt = "2026-08-24"; :>> createdBy = "claudeFable5"; :>> method = VerificationMethod::analyze; :>> procedureText = "Autonomous retro (D0049). AVOIDABLE-ISSUE SCAN under rcRecurrence: the guard-without-its-write-path class (build the check, forget the tool that satisfies it) - now closed for research as it was for markers; the durable practice, recorded: when a guard requires a field, the same sprint ships the flag that emits it, or the guard is unusable friction. WELL: the gap surfaced by USING the process for real (raising D0208) rather than by audit - the channel exercising itself found its own missing piece. Estimate 1 pt, delivered 1."; }
    part researchStatementRetroGateR1 : TestResult { :>> id = "41e094f6-8deb-44ae-b52f-3153d14a08af"; :>> outcome = VerdictKind::pass; :>> judgedAgainst = "ea641a4ec59028fe5674dfc364c60d496db19ac1"; :>> judgedAt = "2026-08-23"; :>> judgedBy = "claudeFable5"; }
}
