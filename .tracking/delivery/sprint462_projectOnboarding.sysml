// ProjectDeliveryS462 — Sprint 462: a project chooses its process set by being asked about its work, and every process declares the situation it applies to. EXECUTE. 5 pts.
package ProjectDeliveryS462 {
    private import EngineElement::*;
    private import EngineWork::*;
    private import EngineVerification::*;
    private import EngineRelationships::*;

    #CharteredBy dependency from projectOnboardingStory to d0225;
    // D0226 is the process's FIRST USE - chartering keel's own set - so one story charters both.
    #CharteredBy dependency from projectOnboardingStory to d0226;

    part projectOnboardingStory : Story {
        :>> id = "ef702c04-7617-45ef-accc-87b5452fb3ee";
        :>> title = "Sprint 462: onboarding, and the menu it must not offer (5 pts)";
        :>> createdAt = "2026-08-25"; :>> createdBy = "claudeFable5"; :>> kind = WorkKind::code; :>> priority = WorkPriority::p0; :>> owner = "claudeFable5"; :>> estimatedPoints = 5;
    }

    action def DeliveryRunS462 {
        action storyProjectOnboarding;
        verification storyProjectOnboardingDoD : Test { :>> id = "c1963304-be3c-49ab-9125-d559d7d085e4"; :>> method = VerificationMethod::test; :>> procedureText = "DELIVERED: dcProjectOnboarding (resolves issue257, HIGH, discoveredInField; D0225 and D0226). The author set this as a precondition on adopting keel onto a second repository - an onboarding process for when processes have not been defined, that works out what they need or researches good practice and picks a set - and named the range it has to serve: hardware, software, both, business processes, safety-related, art, video games, construction plans, whatever. THE DESIGN PROBLEM was that D0216 forbids offering a menu, because a chosen option is evidence about the menu rather than about the chooser's work, while picking a process set from a catalogue IS a menu. The resolution: onboarding never asks which processes you want. It asks about the WORK - what is being built, what would be expensive to get wrong, who has to be convinced and with what, what has to be provable and to whom - records those answers verbatim as Statements, matches them against a condition each process declares about ITSELF, researches the domains the engine has no process for, and then argues for a set the author can strike lines from. The conditions are SITUATIONS and never domain labels, which is what makes 'whatever' serveable: an element being wrong is expensive is equally true of a bridge drawing, a dosing algorithm and a contract, so element-critique reaches a domain no table ever named. They live BESIDE each process because a central table cannot travel with one unit - the same defect that made 23 of 24 units land red on adoption two sprints ago. Also built: keel onboard as the computed view of charter state, guard 50 process-applicability so a new process cannot arrive without a condition, charteredBy in activation.toml, and D0226 chartering keel's own set - which is how the new view's first act was to report that its own project had never made the choice it exists to elicit."; }
        part storyProjectOnboardingDoDR1 : TestResult { :>> id = "de020c1d-c661-4e1c-a810-1d527829b706"; :>> outcome = VerdictKind::pass; :>> judgedAgainst = "64f2dea"; :>> judgedAt = "2026-08-24"; :>> judgedBy = "claudeFable5"; }
        part storyProjectOnboardingDoDR2 : TestResult { :>> id = "14021b18-2536-4a81-9f16-31d10bdf6507"; :>> outcome = VerdictKind::pass; :>> judgedAgainst = "64f2dea614166747b60f17c9fe97d283f8f06dbe"; :>> judgedAt = "2026-08-24"; :>> judgedBy = "claudeFable5"; }
    }

    verification projectOnboardingRefineGate : Test { :>> id = "9bbb1dec-bdbb-4f62-ae2f-64304d56cc98"; :>> title = "Sprint 462 refine gate (DoR)"; :>> createdAt = "2026-08-25"; :>> createdBy = "claudeFable5"; :>> method = VerificationMethod::inspect; :>> procedureText = "DoR. Resolves issue257, raised by the author as an explicit precondition on the penumbra migration: build this, then we migrate. Scope: the process, the declared conditions, the view, the control, and the first real use. 5 points."; }
    part projectOnboardingRefineGateR1 : TestResult { :>> id = "c755d4cf-95c8-4f32-a986-36210af936d4"; :>> outcome = VerdictKind::pass; :>> judgedAgainst = "64f2dea"; :>> judgedAt = "2026-08-24"; :>> judgedBy = "claudeFable5"; }
    part projectOnboardingRefineGateR2 : TestResult { :>> id = "7e3f3c7f-79bd-4c66-aeb3-15d1c45a96a0"; :>> outcome = VerdictKind::pass; :>> judgedAgainst = "64f2dea614166747b60f17c9fe97d283f8f06dbe"; :>> judgedAt = "2026-08-24"; :>> judgedBy = "claudeFable5"; }
    verification projectOnboardingStandupGate : Test { :>> id = "041f1086-fe7a-430e-87e2-615c1587f474"; :>> title = "Sprint 462 standup gate"; :>> createdAt = "2026-08-25"; :>> createdBy = "claudeFable5"; :>> method = VerificationMethod::inspect; :>> procedureText = "Approach: resolve the menu tension FIRST, because it decides the whole shape - ask about work, recommend afterwards, show the reasoning. Declare the condition beside each process rather than centrally, applying the D0222 lesson instead of relearning it. Make the view a view: D0098 forbids gating completeness, and refusing to work until someone answers questions is exactly the friction this removes. guards.rs, .engine/processes/ and .engine/skills/ are keystone-locked, so D0225 and D0226 co-commit. No blockers."; }
    part projectOnboardingStandupGateR1 : TestResult { :>> id = "b8ffa031-6025-4fa8-a5a4-65a80c75c4e2"; :>> outcome = VerdictKind::pass; :>> judgedAgainst = "64f2dea"; :>> judgedAt = "2026-08-24"; :>> judgedBy = "claudeFable5"; }
    part projectOnboardingStandupGateR2 : TestResult { :>> id = "06ca58e0-d326-41e7-ae66-7baab7c67344"; :>> outcome = VerdictKind::pass; :>> judgedAgainst = "64f2dea614166747b60f17c9fe97d283f8f06dbe"; :>> judgedAt = "2026-08-24"; :>> judgedBy = "claudeFable5"; }
    verification projectOnboardingImplementGate : Test { :>> id = "440ee6c7-056c-4c19-97ba-9287afd950ae"; :>> title = "Sprint 462 implement gate"; :>> createdAt = "2026-08-25"; :>> createdBy = "claudeFable5"; :>> method = VerificationMethod::test; :>> procedureText = "Verified by RUNNING it, not by reading it. 25 processes declare a condition and the guard passes 25 scanned; a Process file without one FAILS it, tested in both directions with a non-Process file confirmed out of scope; a FRESH keel init scaffold ships all 25 conditions, reports NOT CHARTERED and passes every guard; process audit reports project-onboarding TRAVELS WHOLE at 3 files; keel onboard reports CHARTERED by d0226 on this project. validate 514 + all 50 guards + check-engine + rules 0 violations + clippy clean; 267 + 9 + 1 + 32 tests across every target."; }
    part projectOnboardingImplementGateR1 : TestResult { :>> id = "9eff9c32-58cc-4765-b4a2-7082ca06497e"; :>> outcome = VerdictKind::pass; :>> judgedAgainst = "64f2dea"; :>> judgedAt = "2026-08-24"; :>> judgedBy = "claudeFable5"; }
    part projectOnboardingImplementGateR2 : TestResult { :>> id = "68dede35-c71f-4772-902c-fe7530776c31"; :>> outcome = VerdictKind::pass; :>> judgedAgainst = "64f2dea614166747b60f17c9fe97d283f8f06dbe"; :>> judgedAt = "2026-08-24"; :>> judgedBy = "claudeFable5"; }
    verification projectOnboardingReviewGate : Test { :>> id = "f0b21f72-acc7-43d2-90af-0d5060bc4b42"; :>> title = "Sprint 462 review gate — three passes per D0172"; :>> createdAt = "2026-08-25"; :>> createdBy = "claudeFable5"; :>> method = VerificationMethod::inspect; :>> procedureText = "PASS 1, CLAIMS: every count is a quoted read-back - 25 scanned, 3 files, the fresh-scaffold run. PASS 2, BOUNDARY: (i) THE RESEARCH STEP IS THE WEAKEST LINK and is written as such - an AI asked about an unfamiliar domain's practice can fabricate a standard, and the only defence shipped is instruction (record the source, never attribute a practice to a body that did not publish it, say plainly when research was unavailable). That is a rule and not a control, which this session has twice shown to be insufficient; a control would need to check citations against something, and nothing here can. (ii) The conditions are MY WORDING for 25 processes the author has never read, so a condition that is subtly wrong will mis-recommend silently - the guard checks that one EXISTS, never that it is right. (iii) keel adopting everything means the recommendation machinery is exercised here only in the direction of yes; the first real test of a recommendation AGAINST is the penumbra migration, and that gap is named in D0226 rather than papered over. PASS 3, OWN DIFF: the honest finding is that I built a view whose first output was that my own project had never done the thing the view exists to elicit - the self-build cannot feel this defect, which is precisely why it survived 462 sprints. WHAT A REVIEWER SHOULD ATTACK: whether an APPLIES-WHEN line written by the same author as the process is evidence at all, or just the process's purpose restated in the interrogative."; }
    part projectOnboardingReviewGateR1 : TestResult { :>> id = "a850353d-19f4-4309-8186-a1d5a3c82d13"; :>> outcome = VerdictKind::pass; :>> judgedAgainst = "64f2dea"; :>> judgedAt = "2026-08-24"; :>> judgedBy = "claudeFable5"; }
    part projectOnboardingReviewGateR2 : TestResult { :>> id = "8b6ef3ac-d573-4594-b4c5-1126df9282c5"; :>> outcome = VerdictKind::pass; :>> judgedAgainst = "64f2dea614166747b60f17c9fe97d283f8f06dbe"; :>> judgedAt = "2026-08-24"; :>> judgedBy = "claudeFable5"; }
    verification projectOnboardingCloseOutGate : Test { :>> id = "12bd647c-84d4-48d1-ba6f-865f6fe26b1c"; :>> title = "Sprint 462 closeOut gate (autonomous, D0049)"; :>> createdAt = "2026-08-25"; :>> createdBy = "claudeFable5"; :>> method = VerificationMethod::inspect; :>> procedureText = "Autonomous closeOut (D0049). issue257 resolved. A scaffolded project is now asked what it is building before it inherits 25 disciplines, and every process states the situation it is for. The author's precondition on the penumbra migration is met. validate + all 50 guards + check-engine + rules green at 64f2dea."; }
    part projectOnboardingCloseOutGateR1 : TestResult { :>> id = "3eaf167d-6902-447f-aabb-cbca499c600c"; :>> outcome = VerdictKind::pass; :>> judgedAgainst = "64f2dea"; :>> judgedAt = "2026-08-24"; :>> judgedBy = "claudeFable5"; }
    part projectOnboardingCloseOutGateR2 : TestResult { :>> id = "8d656ac9-20c8-4a5f-a9cc-8df03196ac0c"; :>> outcome = VerdictKind::pass; :>> judgedAgainst = "64f2dea614166747b60f17c9fe97d283f8f06dbe"; :>> judgedAt = "2026-08-24"; :>> judgedBy = "claudeFable5"; }
    verification projectOnboardingRetroGate : Test { :>> id = "9e25f3e3-833d-4abe-ad9c-d8aca27c31e6"; :>> title = "Sprint 462 retro gate (autonomous, D0049)"; :>> createdAt = "2026-08-25"; :>> createdBy = "claudeFable5"; :>> method = VerificationMethod::analyze; :>> procedureText = "Autonomous retro (D0049). AVOIDABLE-ISSUE SCAN under rcRecurrence: (1) THE PATTERN WORTH NAMING: this defect was invisible to the self-build by construction. keel wants every process on, so it never experiences the choice, and no amount of internal critique would have surfaced it - only adopting onto a second repository did. Two of the last three sprints were the same shape (issue251, issue253, now issue257), which says the highest-yield audit available right now is not another critique pass but another adoption. (2) I applied the D0222 lesson unprompted this time - the condition went beside its process rather than into a central table - which is the first time a lesson from this session prevented its own recurrence rather than being relearned. (3) The heredoc class recurred an eighth time and cost a Rust file; the Write tool was used for syntax-bearing content thereafter, as the rule already said. WELL: the design tension (D0216 forbids the menu, the task IS a menu) was found before building rather than after, and it produced a better shape than either horn. Estimate 5 pts, delivered 5."; }
    part projectOnboardingRetroGateR1 : TestResult { :>> id = "70cfdd6d-8da1-42a8-9384-0b2320a9ac9e"; :>> outcome = VerdictKind::pass; :>> judgedAgainst = "64f2dea"; :>> judgedAt = "2026-08-24"; :>> judgedBy = "claudeFable5"; }
    part projectOnboardingRetroGateR2 : TestResult { :>> id = "e3254652-a136-466c-a5be-4bb6fa06c4f2"; :>> outcome = VerdictKind::pass; :>> judgedAgainst = "64f2dea614166747b60f17c9fe97d283f8f06dbe"; :>> judgedAt = "2026-08-24"; :>> judgedBy = "claudeFable5"; }
}
