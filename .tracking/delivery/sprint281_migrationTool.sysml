// ProjectDeliveryS281 — Sprint 281: `keel migrate` — bring a downstream project up to this binary's
// engine vintage (dcProjectMigrationTool, D0067). EXECUTE. 8 pts.
package ProjectDeliveryS281 {
    private import EngineElement::*;
    private import EngineWork::*;
    private import EngineVerification::*;
    private import EngineRelationships::*;

    #CharteredBy dependency from migrationToolStory to d0144;

    part migrationToolStory : Story {
        :>> id = "0d80013b-0814-613b-9b3e-00000030013b";
        :>> title = "Sprint 281: keel migrate — versioned, idempotent, refusing (8 pts)";
        :>> createdAt = "2026-08-14"; :>> createdBy = "claudeOpus5"; :>> kind = WorkKind::code; :>> priority = WorkPriority::p0; :>> owner = "claudeOpus5"; :>> estimatedPoints = 8;
    }

    action def DeliveryRunS281 {
        action storyMigrationTool;
        verification storyMigrationToolDoD : Test { :>> id = "0d80013c-0814-613c-9b3e-00000030013c"; :>> method = VerificationMethod::demo; :>> procedureText = "Delivers dcProjectMigrationTool; resolves issue107. DESIGN, and the consumer check changed it: `keel init` writes NO version marker (main.rs cmd_init), so the vintage cannot be READ — it is DETECTED by every step being a pure `plan(root) -> StepPlan` over the tree's content. A step whose pattern no longer matches plans zero edits, which delivers vintage detection, idempotency and dry-run fidelity from ONE property rather than three mechanisms; a stored stamp would be strictly worse, since it can drift from the tree it describes and is absent from every project inited before it existed. FIVE STEPS: engine-resync (the binary CARRIES the engine via include_dir, so for engine-owned content this is a write, not a transform — preserving `.engine/decisions/`, the instance-specific manifest, and any unshipped file, which is reported and never deleted); process-as-action (D0143); processstep-order (the deleted attribute, with successions deliberately NOT synthesised — guessing order from a dropped attribute would fabricate an authored fact); release-as-occurrence (D0142); removed-types, which produces BLOCKERS only, since twelve types were deleted with no mechanical target. VERIFIED ON A REAL FIXTURE, a project inited from this binary then rolled back to the pre-pass schema/core (b92875d) with old-shape instance data: dry run reported 16 files / 19 edits / 2 blockers and wrote nothing; blockers resolved by hand per the printed advice; apply wrote 16 files and the post-apply RE-PLAN came back empty; a second run reports `CURRENT — no step applies`; the migrated project passes its OWN full gate — validate clean, check-engine clean, all 28 guards ALL PASS. Refusals each verified by exit code: dirty tree 2, non-git 2, self-build repo 2, blockers present 1 with nothing written. clippy clean; 172 tests."; }
        part storyMigrationToolDoDR1 : TestResult { :>> id = "0d80013d-0814-613d-9b3e-00000030013d"; :>> outcome = VerdictKind::pass; :>> judgedAgainst = "8b785ff"; :>> judgedAt = "2026-08-14"; :>> judgedBy = "claudeOpus5"; }
    }

    verification mtRefineGate : Test { :>> id = "0d80013e-0814-613e-9b3e-00000030013e"; :>> title = "Sprint 281 refine gate (DoR)"; :>> createdAt = "2026-08-14"; :>> createdBy = "claudeOpus5"; :>> method = VerificationMethod::inspect; :>> procedureText = "DoR. CONSUMER CHECK (dorConsumer, D0144), and it produced the design rather than confirming it. Two consumers, each answering a question I would otherwise have assumed: (1) the tool's own input — reading cmd_init showed no version is ever stamped, which killed the stamp-and-compare design before it was written and replaced it with content detection; (2) the tool's OUTPUT — its consumer is keel-parser, and the migrated file must be readable by it. That second check is what caught the defect below. Removal set derived by diffing schema/core at b92875d against HEAD rather than from memory of what the sweep removed. estimatedPoints=8. DoR met."; }
    part mtRefineGateR1 : TestResult { :>> id = "0d80013f-0814-613f-9b3e-00000030013f"; :>> outcome = VerdictKind::pass; :>> judgedAgainst = "8b785ff"; :>> judgedAt = "2026-08-14"; :>> judgedBy = "claudeOpus5"; }

    verification mtStandupGate : Test { :>> id = "0d800140-0814-6140-9b3e-000000300140"; :>> title = "Sprint 281 standup gate"; :>> createdAt = "2026-08-14"; :>> createdBy = "claudeOpus5"; :>> method = VerificationMethod::inspect; :>> procedureText = "Approach: build the fixture FIRST — a project inited from this binary, rolled back to the pre-pass schema, with instance data using the old shapes — so every claim about the tool is a run against a real tree rather than a unit test over strings. The DoD's own words settle what counts: the migrated project must pass ITS OWN gate, because that is the state a downstream user is actually in. No blockers."; }
    part mtStandupGateR1 : TestResult { :>> id = "0d800141-0814-6141-9b3e-000000300141"; :>> outcome = VerdictKind::pass; :>> judgedAgainst = "8b785ff"; :>> judgedAt = "2026-08-14"; :>> judgedBy = "claudeOpus5"; }

    verification mtImplementGate : Test { :>> id = "0d800142-0814-6142-9b3e-000000300142"; :>> title = "Sprint 281 implement gate"; :>> createdAt = "2026-08-14"; :>> createdBy = "claudeOpus5"; :>> method = VerificationMethod::test; :>> procedureText = "TWO DEFECTS FOUND IN MY OWN WORK, both by the checks this project already had. FIRST, a composition bug: each step read its file from DISK and produced a whole-file result, so on a file needing two steps — a ProcessStep needs both the retype and the order drop — applying them in sequence discarded the earlier one. Fixed with a `Working` overlay so each step reads what the previous staged. The post-apply re-plan would have caught it loudly rather than corrupting, but it would have failed on every multi-step file; note that the obvious test, 'a second run is a no-op', does NOT catch it, because the second run reads the clobbered file and re-plans the same edit forever. The regression test asserts the FINAL CONTENT instead. SECOND, and worse: the migrated project passed validate and all 28 guards while `parser-coverage` warned that its `occurrence v1 : Release` was skipped by the parser — the migration was emitting a construct that makes the migrated item invisible to every view, which is issue102's failure mode delivered by the very tool meant to repair a project. Fixed in the parser, and fixing it turned a false-clean into a true diagnostic on the fixture (an unresolved `Release` import that invisibility had been hiding)."; }
    part mtImplementGateR1 : TestResult { :>> id = "0d800143-0814-6143-9b3e-000000300143"; :>> outcome = VerdictKind::pass; :>> judgedAgainst = "8b785ff"; :>> judgedAt = "2026-08-14"; :>> judgedBy = "claudeOpus5"; }

    verification mtReviewGate : Test { :>> id = "0d800144-0814-6144-9b3e-000000300144"; :>> title = "Sprint 281 review gate"; :>> createdAt = "2026-08-14"; :>> createdBy = "claudeOpus5"; :>> method = VerificationMethod::inspect; :>> procedureText = "Reviewed. Chasing the skipped `occurrence` uncovered a second, older skip: `abstract action def TrackedAction` had been invisible since the Process-as-behaviour conversion four sprints ago, because the dispatch arm read `TokenKind::Action if !had_abstract`. Both are fixed with regression tests and `parser-coverage` is now 0 skipped across all 491 files — the first time it has been at zero. Recorded as issue107 with the part that matters: the guard had been warning about it on every run since, and I read its exit code rather than its message. LIMITATION, stated rather than glossed: the step set covers what THIS pass changed. An older vintage than b92875d is not covered, and the tool cannot know that — it will report `CURRENT` and be wrong. The DoD's rule that each conversion sprint contributes its own step is what keeps that from growing, and it starts being honoured from here."; }
    part mtReviewGateR1 : TestResult { :>> id = "0d800145-0814-6145-9b3e-000000300145"; :>> outcome = VerdictKind::pass; :>> judgedAgainst = "8b785ff"; :>> judgedAt = "2026-08-14"; :>> judgedBy = "claudeOpus5"; }

    verification mtCloseOutGate : Test { :>> id = "0d800146-0814-6146-9b3e-000000300146"; :>> title = "Sprint 281 closeOut gate (autonomous, D0049)"; :>> createdAt = "2026-08-14"; :>> createdBy = "claudeOpus5"; :>> method = VerificationMethod::inspect; :>> procedureText = "Autonomous closeOut (D0049). dcProjectMigrationTool carries a passing DoD TestResult; issue107 resolves; issue108 recorded and deliberately left for its own sprint. Doc-sync rides this commit: `.engine/docs/usage.md` gains a 'keeping a project current' section and the downstream CLAUDE.md template gains the upgrade step, since a migration tool nobody is told about is not a control. clippy clean; 172 tests; validate 302 clean; check-engine clean; all 28 guards green with parser-coverage at 0 skipped. No gate bypassed."; }
    part mtCloseOutGateR1 : TestResult { :>> id = "0d800147-0814-6147-9b3e-000000300147"; :>> outcome = VerdictKind::pass; :>> judgedAgainst = "8b785ff"; :>> judgedAt = "2026-08-14"; :>> judgedBy = "claudeOpus5"; }

    verification mtRetroGate : Test { :>> id = "0d800148-0814-6148-9b3e-000000300148"; :>> title = "Sprint 281 retro gate (autonomous, D0049)"; :>> createdAt = "2026-08-14"; :>> createdBy = "claudeOpus5"; :>> method = VerificationMethod::analyze; :>> procedureText = "Autonomous retro (D0049) under D0131's retroTrack. WELL: (1) the dorConsumer gate paid for itself twice in one sprint — checking the tool's INPUT killed a stamp-and-compare design before it was written, and checking its OUTPUT caught the tool emitting a construct the parser could not read; (2) the fixture was built before the code, so every claim is a run against a real tree, and it is what surfaced the composition bug and both parser skips; (3) the post-apply RE-PLAN as the reconciliation check means idempotency is verified at runtime on every migration rather than asserted in a comment. AVOIDABLE-ISSUE 1: I wrote five steps that each read from disk, which silently made them mutually exclusive on any shared file. The design error was treating steps as independent when the second consumer of a step's output is the NEXT step — the same consumer-blindness D0144 exists for, applied inside a sprint that was running D0144. NO NEW ITEM, reason stated: caught before commit by a test written for it, and it is an instance of the class issue107 and D0144 already carry. AVOIDABLE-ISSUE 2, the substantive one: `parser-coverage` warned `action×1` on every run for four sprints and I reported `guard exit=0` each time — a true statement that hid the finding, and the defect surfaced only because a fixture pushed the count to 2 and made me read the message. TRACKED as issue107, which names the residual precisely: `guard exit=0` is the summary I act on, so a persistently non-zero warning count reads as background. The backlog is now at zero skipped statements for the first time, which is the moment these warnings could become blocking; that call is a CHANGE and belongs to the human, not to this retro. Estimate 8 pts, delivered."; }
    part mtRetroGateR1 : TestResult { :>> id = "0d800149-0814-6149-9b3e-000000300149"; :>> outcome = VerdictKind::pass; :>> judgedAgainst = "8b785ff"; :>> judgedAt = "2026-08-14"; :>> judgedBy = "claudeOpus5"; }
}
