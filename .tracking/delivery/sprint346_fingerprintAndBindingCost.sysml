// ProjectDeliveryS346 — Sprint 346: instrumented first, as the DoD demanded, and the instrument
// contradicted my own diagnosis. The parsed model was ALREADY cached; the cache KEY was the cost.
// EXECUTE. 5 pts.
package ProjectDeliveryS346 {
    private import EngineElement::*;
    private import EngineWork::*;
    private import EngineVerification::*;
    private import EngineRelationships::*;

    #CharteredBy dependency from perfInstrumentStory to d0129;

    part perfInstrumentStory : Story {
        :>> id = "0d800550-0814-6550-9b3e-000000300550";
        :>> title = "Sprint 346: KEEL_PERF instrumentation; the fingerprint epoch memo (issue145) and the double-compute (issue146) (5 pts)";
        :>> createdAt = "2026-08-19"; :>> createdBy = "claudeOpus5"; :>> kind = WorkKind::code; :>> priority = WorkPriority::p0; :>> owner = "claudeOpus5"; :>> estimatedPoints = 5;
    }

    action def DeliveryRunS346 {
        action storyPerfInstrument;
        verification storyPerfInstrumentDoD : Test { :>> id = "0d800551-0814-6551-9b3e-000000300551"; :>> method = VerificationMethod::test; :>> procedureText = "INSTRUMENTED FIRST, WHICH THE DoD DEMANDED, AND THE INSTRUMENT IMMEDIATELY CONTRADICTED MY OWN DIAGNOSIS. issue142 recorded that 'only the JSON OUTPUT is cached, never the parsed model' and dcSharedParsedModel asked me to share one parsed model across the 74 call sites. BOTH WERE WRONG: `MODEL_CACHE` and `MODEL_BUILD_LOCK` have memoized `Model::build` by fingerprint all along, and the requested work was already done. THE COST WAS THE CACHE KEY. `fingerprint()` walks two trees and stats every file (~40ms, 582 stats) and ran on EVERY build call, cache hit included: `assured` built the model 37 times, hit the cache 36, and spent 1472ms keying it to avoid a 160ms parse - 21,534 stats, 74 walks. The cache key cost NINE TIMES what the cache saved, and the better the cache worked the worse the key got. It also existed TWICE, identical in view.rs and serve.rs. DELIVERED: `crate::perf` (opt-in via KEEL_PERF=1, stderr so it can never corrupt the JSON on stdout), `crate::fingerprint` as the single home with an EPOCH memo, and the `computed_binding` split that ended a per-request double computation of every console view. MEASURED, warmed binary, same session: assured fingerprint 1472ms to 41ms, stats to 582, walks to 2; console warm burst 7197ms to 979/1227/1291ms; cold 12066ms to 5185/5277/5505ms. validate 374 clean; check-engine clean; 36 guards ALL PASS; 188 tests; clippy clean."; }
        part storyPerfInstrumentDoDR1 : TestResult { :>> id = "0d800552-0814-6552-9b3e-000000300552"; :>> outcome = VerdictKind::pass; :>> judgedAgainst = "dfd2677"; :>> judgedAt = "2026-08-19"; :>> judgedBy = "claudeOpus5"; }
    }

    verification piRefineGate : Test { :>> id = "0d800553-0814-6553-9b3e-000000300553"; :>> title = "Sprint 346 refine gate (DoR)"; :>> createdAt = "2026-08-19"; :>> createdBy = "claudeOpus5"; :>> method = VerificationMethod::inspect; :>> procedureText = "DoR. Followed the ranked frontier: dcSharedParsedModel, whose own DoD says INSTRUMENT FIRST because three wall-clock inferences had already been wrong. The human's disposition is the authorising direction and is quoted verbatim in the standup gate. Read the code before writing any, which is what surfaced that the DoD's premise was false - and reading first is the only reason this sprint did not begin by building a cache that already existed. estimatedPoints=5."; }
    part piRefineGateR1 : TestResult { :>> id = "0d800554-0814-6554-9b3e-000000300554"; :>> outcome = VerdictKind::pass; :>> judgedAgainst = "dfd2677"; :>> judgedAt = "2026-08-19"; :>> judgedBy = "claudeOpus5"; }

    verification piStandupGate : Test { :>> id = "0d800555-0814-6555-9b3e-000000300555"; :>> title = "Sprint 346 standup gate"; :>> createdAt = "2026-08-19"; :>> createdBy = "claudeOpus5"; :>> method = VerificationMethod::inspect; :>> procedureText = "The human authorised caching with a CONDITION, verbatim: 'building cache isn't the same as authoring duplicate/stale facts. max cache to improve speed here is just fine, if there's a good mechanism to piece-wise update the cache when changes are detected.' That condition drove the design and rejected the easy version: the memo is keyed by an EXPLICIT EPOCH and never by elapsed time, because a timer is precisely a mechanism that does NOT detect changes - it guesses how long staleness is tolerable. A CLI process is one epoch because it is one-shot and read-only; serve bumps per HTTP request, so each request sees one snapshot and the request after any write re-reads, and a write is a request so no write path must remember to invalidate; the SSE change detector reads UNCACHED because it is the detector. No blockers."; }
    part piStandupGateR1 : TestResult { :>> id = "0d800556-0814-6556-9b3e-000000300556"; :>> outcome = VerdictKind::pass; :>> judgedAgainst = "dfd2677"; :>> judgedAt = "2026-08-19"; :>> judgedBy = "claudeOpus5"; }

    verification piImplementGate : Test { :>> id = "0d800557-0814-6557-9b3e-000000300557"; :>> title = "Sprint 346 implement gate"; :>> createdAt = "2026-08-19"; :>> createdBy = "claudeOpus5"; :>> method = VerificationMethod::test; :>> procedureText = "THREE FINDINGS, ALL FROM THE INSTRUMENT RATHER THAN FROM READING. (1) issue145, THE CACHE KEY: measured above; fixed with one home plus an epoch memo; invalidation EXERCISED against the running server (edit .tracking/issues.sysml, fingerprint changes) rather than asserted, because the human's condition was about invalidation and asserting it would have been the one thing they asked me not to do. (2) issue146, THE DOUBLE COMPUTE, and it is MY OWN defect from sprint 339: `api_computed` called `computed_view` to decide whether to 404, discarded the result, then computed the same view again through `cached()`. Every request paid a full uncached computation whether the cache hit or not, so the per-fingerprint cache its own doc comment advertised could never take effect. THE ROOT CAUSE IS A CONFLATED SIGNATURE, not a careless call: `Option<Result<String, _>>` folded IS THIS BOUND together with WHAT DOES IT COMPUTE, so the only way to ask the cheap question was to answer the expensive one. Split into `computed_binding -> Option<ComputedFn>`. (3) issue147, THE REAL REMAINING COST: `assured` spawns 483 git subprocesses for 15,078ms of a ~21,000ms run, ~31ms each, one per element for D0084 staleness. So assurance is a PROCESS-SPAWN problem, not a parsing or caching one, and `git cat-file --batch` collapses 483 spawns into 1. Recorded as open work with a FAILING result, not quietly listed. A MEASUREMENT ATTEMPT THAT FAILED AND IS WORTH RECORDING: I tried counting git calls with a PATH shim before instrumenting in code. Rust's `Command::new` uses CreateProcess, which ignores PATHEXT, so a `git.cmd` shim is never found and the log stayed empty - which read at first glance like 'no git calls'."; }
    part piImplementGateR1 : TestResult { :>> id = "0d800558-0814-6558-9b3e-000000300558"; :>> outcome = VerdictKind::pass; :>> judgedAgainst = "dfd2677"; :>> judgedAt = "2026-08-19"; :>> judgedBy = "claudeOpus5"; }

    verification piReviewGate : Test { :>> id = "0d800559-0814-6559-9b3e-000000300559"; :>> title = "Sprint 346 review gate"; :>> createdAt = "2026-08-19"; :>> createdBy = "claudeOpus5"; :>> method = VerificationMethod::inspect; :>> procedureText = "Reviewed. WHAT I WILL NOT CLAIM: that CLI commands got faster. `assured` reads ~21s before and after, because git spawns dominate it, and `orient` and `coverage` show no wall-clock change I can attribute - I never took a CLI baseline BEFORE the fingerprint fix in this session, so for the CLI I have only the INSTRUMENT reading (1472ms of fingerprinting removed) and not a clock delta. That instrument reading is a direct measurement of work removed and is better evidence than a clock, but it is not the same claim and is not written as one. The server numbers ARE a valid before/after: same harness, same corpus, minutes apart, three samples each side. I ALSO CANNOT SEPARATE the two server fixes in the burst number, and said so in the backlog DoD rather than attributing the whole gain to either. WHAT THE 20s vs 9.9s SCARE TAUGHT ME: `assured` measured 9.9s in sprint 342 and 21s today, which looked like a catastrophic regression from my own change. It is not - the instrument shows parse and fingerprint together are 191ms of it - but I could not have known that from a clock, and the sprint-342 figure was one of the numbers that sprint already flagged as unreliable. A cross-day wall-clock comparison on this host is not evidence, and this is the second time that has nearly sent me chasing a phantom."; }
    part piReviewGateR1 : TestResult { :>> id = "0d80055a-0814-655a-9b3e-00000030055a"; :>> outcome = VerdictKind::pass; :>> judgedAgainst = "dfd2677"; :>> judgedAt = "2026-08-19"; :>> judgedBy = "claudeOpus5"; }

    verification piCloseOutGate : Test { :>> id = "0d80055b-0814-655b-9b3e-00000030055b"; :>> title = "Sprint 346 closeOut gate (autonomous, D0049)"; :>> createdAt = "2026-08-19"; :>> createdBy = "claudeOpus5"; :>> method = VerificationMethod::inspect; :>> procedureText = "Autonomous closeOut (D0049). issue145 and issue146 recorded, triaged and RESOLVED by dcFingerprintEpoch and dcComputedBindingSplit respectively; issue147 recorded, triaged to dcBatchGitReads and left OPEN with a failing result, because 15 seconds of measured spawn cost is not something to close by describing. issue142's false claim is corrected in issue145's own text rather than edited away, so the correction is legible next to what it corrects. dcSharedParsedModel's DoD asked for work that was already done, which is now stated in issue145. The human's condition on caching was met by construction and exercised end to end. NOT DONE AND NOT PRETENDED: CLI assurance is still ~21s. pendingAcceptances d0159, d0161, d0162 - unchanged, since nothing here needed a Decision: caching was authorised by their disposition and the rest is defect repair. validate 374 clean; check-engine clean; 36 guards ALL PASS; 188 tests; clippy clean."; }
    part piCloseOutGateR1 : TestResult { :>> id = "0d80055c-0814-655c-9b3e-00000030055c"; :>> outcome = VerdictKind::pass; :>> judgedAgainst = "dfd2677"; :>> judgedAt = "2026-08-19"; :>> judgedBy = "claudeOpus5"; }

    verification piRetroGate : Test { :>> id = "0d80055d-0814-655d-9b3e-00000030055d"; :>> title = "Sprint 346 retro gate (autonomous, D0049)"; :>> createdAt = "2026-08-19"; :>> createdBy = "claudeOpus5"; :>> method = VerificationMethod::analyze; :>> procedureText = "Autonomous retro (D0049) under D0131's retroTrack. THE FINDING THAT MATTERS: my sprint-342 diagnosis was wrong about the code, and it was wrong in the confident direction - it asserted that the parsed model was never cached, when a cache with its own build lock and doc comment sat forty lines above the function I was diagnosing. I reached that conclusion by reasoning about what the timings implied instead of reading the function. Sprint 342 then wrote it into an Issue description and a backlog DoD, where it would have directed the next session to build a cache that already existed. TWO CONSECUTIVE SPRINTS OF WRONG PERFORMANCE CLAIMS, and the pattern is the same both times: I inferred structure from timing. The rule now has evidence behind it - INSTRUMENT BEFORE DIAGNOSING, not before optimising - and the instrument found in one run three things that days of wall-clock reasoning had missed, including one defect I had introduced myself and never suspected. WELL: (1) the DoD's own instruction to instrument first is what caught its own false premise, which is the process working on its author; (2) invalidation was exercised against a live server because the human's authorisation was conditional on it; (3) the 483-spawn finding is recorded with its measurement scope stated (two of ~25 sites, so the number understates) rather than as a round figure; (4) I refused to claim a CLI improvement I could not evidence, and refused to attribute the server gain to one of two simultaneous fixes; (5) a failed measurement attempt - the PATHEXT shim that silently logged nothing - is recorded, because an empty log that looks like a zero is exactly the trap that produced the earlier bad numbers. Estimate 5 pts, delivered."; }
    part piRetroGateR1 : TestResult { :>> id = "0d80055e-0814-655e-9b3e-00000030055e"; :>> outcome = VerdictKind::pass; :>> judgedAgainst = "dfd2677"; :>> judgedAt = "2026-08-19"; :>> judgedBy = "claudeOpus5"; }
}
