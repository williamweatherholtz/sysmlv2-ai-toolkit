// ProjectDeliveryS427 — Sprint 427: the claim lane's two panel-found holes close: land warns on held items, and guard 47 bounds claim dates by git ancestry (issue229). EXECUTE. 1 pts.
package ProjectDeliveryS427 {
    private import EngineElement::*;
    private import EngineWork::*;
    private import EngineVerification::*;
    private import EngineRelationships::*;

    #CharteredBy dependency from claimLandCheckStory to d0187;

    part claimLandCheckStory : Story {
        :>> id = "4f0d5ec3-4132-41b7-afc5-2bcdb5443aea";
        :>> title = "Sprint 427: claims meet the clock (1 pts)";
        :>> createdAt = "2026-08-23"; :>> createdBy = "claudeFable5"; :>> kind = WorkKind::code; :>> priority = WorkPriority::p0; :>> owner = "claudeFable5"; :>> estimatedPoints = 1;
    }

    action def DeliveryRunS427 {
        action storyClaimLandCheck;
        verification storyClaimLandCheckDoD : Test { :>> id = "897c7894-6368-4a8c-bb35-045d02b27de6"; :>> method = VerificationMethod::test; :>> procedureText = "DELIVERED: dcClaimLandCheck (resolves issue229, the process-value panel's multi-agent findings with concrete interleavings). HOLE 1 - claims gated selection but not landing: keel land now runs a pre-push holdership check - if an outgoing commit touches the declaring file of an item another actor holds LIVE, it warns loudly with the holder's name and the D0108 remedy (record the contention Issue, never self-resolve). WARN, never block, by design: a refused land strands facts, which is worse than a visible contention; file-granular by design (coarse in the safe direction - it can over-warn about a shared file, never stay silent about a held item's own file). HOLE 2 - claimedAt was authored and trusted where nothing else in the system is: guard 47 claim-ancestry applies D0013 (git ancestry is the clock) to claims - a claimedAt that predates its own INTRODUCING COMMIT by more than the expiry window is refused; uncommitted claims are skipped because they influence no other clone. STATED LIMIT, not hidden: backdating WITHIN the expiry window remains possible - the guard narrows the theft window from unbounded to the expiry span. VERIFIED: a scratch-git-repo test plants a 2020-dated claim committed today (guard RED, message quoting the lead) and a same-day claim (green); the live tree scans its 1 committed claim green; full suite 10/10 result-ok; clippy clean; guards.md synced; 47 guards run ALL PASS."; }
        part storyClaimLandCheckDoDR1 : TestResult { :>> id = "62d025cd-74ee-46ce-b985-f4c4bc96bb56"; :>> outcome = VerdictKind::pass; :>> judgedAgainst = "d57af6a2024dcf60a4b552b3d4612671b4e7f40c"; :>> judgedAt = "2026-08-22"; :>> judgedBy = "claudeFable5"; }
    }

    verification claimLandCheckRefineGate : Test { :>> id = "19371e27-f9d1-483c-b39e-1813a16f1bc7"; :>> title = "Sprint 427 refine gate (DoR)"; :>> createdAt = "2026-08-23"; :>> createdBy = "claudeFable5"; :>> method = VerificationMethod::inspect; :>> procedureText = "DoR. Chartered from the panel's issue229. In scope: the land warning and the ancestry guard. Out of scope (stated): unifying claim staleness with commit-activity (the panel's commitment-protocol recommendation) - a semantics change deserving its own decision if wanted. 1 point."; }
    part claimLandCheckRefineGateR1 : TestResult { :>> id = "97391cfe-7ad7-408f-92e9-0d9cf589c816"; :>> outcome = VerdictKind::pass; :>> judgedAgainst = "d57af6a2024dcf60a4b552b3d4612671b4e7f40c"; :>> judgedAt = "2026-08-22"; :>> judgedBy = "claudeFable5"; }
    verification claimLandCheckStandupGate : Test { :>> id = "f58089d9-9790-4125-ba39-94083898f5fc"; :>> title = "Sprint 427 standup gate"; :>> createdAt = "2026-08-23"; :>> createdBy = "claudeFable5"; :>> method = VerificationMethod::inspect; :>> procedureText = "Approach: warn-never-block at land (the claim lane must not make work unlandable); the ancestry bound reuses the existing expiry constant so there is ONE window semantics; the negative probe runs against a real scratch git repo rather than mocks, because the guard's core is a git -S lookup and mocking it would test nothing."; }
    part claimLandCheckStandupGateR1 : TestResult { :>> id = "935dbf46-c824-4219-a939-f8c0a55c31f6"; :>> outcome = VerdictKind::pass; :>> judgedAgainst = "d57af6a2024dcf60a4b552b3d4612671b4e7f40c"; :>> judgedAt = "2026-08-22"; :>> judgedBy = "claudeFable5"; }
    verification claimLandCheckImplementGate : Test { :>> id = "c945fb21-d93c-4101-8a19-79c58dcd02c1"; :>> title = "Sprint 427 implement gate"; :>> createdAt = "2026-08-23"; :>> createdBy = "claudeFable5"; :>> method = VerificationMethod::test; :>> procedureText = "Verified by running: cargo test (the new backdated_claim_is_refused_and_honest_claim_passes builds a scratch repo, commits a 2020-dated claim, reads guard RED with 'predates its introducing commit', then a same-day claim green); keel guard claim-ancestry on the live tree: 1 scanned, PASS; full workspace suite 10 result-ok lines; clippy pedantic+nursery clean; all 47 guards green."; }
    part claimLandCheckImplementGateR1 : TestResult { :>> id = "28b74d84-58b9-47b2-ad8e-58925b95a555"; :>> outcome = VerdictKind::pass; :>> judgedAgainst = "d57af6a2024dcf60a4b552b3d4612671b4e7f40c"; :>> judgedAt = "2026-08-22"; :>> judgedBy = "claudeFable5"; }
    verification claimLandCheckReviewGate : Test { :>> id = "c0fa0f44-9ef6-43de-954e-d15fa2bb4ddd"; :>> title = "Sprint 427 review gate — three passes per D0172"; :>> createdAt = "2026-08-23"; :>> createdBy = "claudeFable5"; :>> method = VerificationMethod::inspect; :>> procedureText = "PASS 1, CLAIMS: guard outputs and test names quoted from this session's runs. PASS 2, BOUNDARY: two limits stated in the shipped text itself - the land check is file-granular (may over-warn on shared files) and the ancestry bound leaves an expiry-window-sized backdating residual; both are the honest cut between cheap-and-real and expensive-and-perfect. PASS 3, OWN DIFF: item_files returns a Vec and my first lookup pretended it was a map - compiler-caught, converted at the call site. WHAT A REVIEWER SHOULD ATTACK: warn-never-block means a contributor can ignore the contention cue; if the control-evaluation sprint shows warnings being ignored in practice, promotion to a recorded-obligation (not a block) is the next step and D0197's evidence discipline applies."; }
    part claimLandCheckReviewGateR1 : TestResult { :>> id = "4646b779-b705-4371-9426-040f1a9f7f98"; :>> outcome = VerdictKind::pass; :>> judgedAgainst = "d57af6a2024dcf60a4b552b3d4612671b4e7f40c"; :>> judgedAt = "2026-08-22"; :>> judgedBy = "claudeFable5"; }
    verification claimLandCheckCloseOutGate : Test { :>> id = "d76bc376-fd5d-41c3-9eda-b1e14d6bddaf"; :>> title = "Sprint 427 closeOut gate (autonomous, D0049)"; :>> createdAt = "2026-08-23"; :>> createdBy = "claudeFable5"; :>> method = VerificationMethod::inspect; :>> procedureText = "Autonomous closeOut (D0049). issue229 resolves; guard count 47 with the new guard negative-tested; validate + guards green."; }
    part claimLandCheckCloseOutGateR1 : TestResult { :>> id = "91080fad-6f7b-461f-b748-e15d146f4dc6"; :>> outcome = VerdictKind::pass; :>> judgedAgainst = "d57af6a2024dcf60a4b552b3d4612671b4e7f40c"; :>> judgedAt = "2026-08-22"; :>> judgedBy = "claudeFable5"; }
    verification claimLandCheckRetroGate : Test { :>> id = "66580a1b-dca1-4b7c-a45c-1db198f52e36"; :>> title = "Sprint 427 retro gate (autonomous, D0049)"; :>> createdAt = "2026-08-23"; :>> createdBy = "claudeFable5"; :>> method = VerificationMethod::analyze; :>> procedureText = "Autonomous retro (D0049). AVOIDABLE-ISSUE SCAN under rcRecurrence: no new class - the trusted-authored-timestamp defect is the same family the impossible-evidence-date guard closed for TestResults; the lesson recorded there (bound every authored date by git ancestry) has now been applied to the second surface it was always going to bite, and grep says no third authored-date surface remains unbounded (createdAt is advisory, not ranking). WELL: the panel's interleaving-level findings translated directly into a test fixture - the scratch-repo pattern is reusable for the control-evaluation sprint. Estimate 1 pt, delivered 1."; }
    part claimLandCheckRetroGateR1 : TestResult { :>> id = "18416ad7-958f-4996-8a75-2f8d13827ac8"; :>> outcome = VerdictKind::pass; :>> judgedAgainst = "d57af6a2024dcf60a4b552b3d4612671b4e7f40c"; :>> judgedAt = "2026-08-22"; :>> judgedBy = "claudeFable5"; }
}
