// ProjectDeliveryS479 - Sprint 479: the graph finally PUSHES. Agreement scoring, a confidence bar so silence beats noise, and three ways to switch it off. EXECUTE. 5 pts.
package ProjectDeliveryS479 {
    private import EngineElement::*;
    private import EngineWork::*;
    private import EngineVerification::*;
    private import EngineRelationships::*;

    #CharteredBy dependency from injectStory to d0242;
    #CharteredBy dependency from injectStory to d0243;

    part injectStory : Story {
        :>> id = "8740bee0-060d-4e24-8407-a4f6a2b77ddd";
        :>> title = "Sprint 479: the prompt path injects recalled facts behind a confidence bar, with three kill switches (5 pts)";
        :>> createdAt = "2026-08-27"; :>> createdBy = "claudeOpus5"; :>> kind = WorkKind::code; :>> priority = WorkPriority::p1; :>> owner = "claudeOpus5"; :>> estimatedPoints = 5;
    }

    action def DeliveryRunS479 {
        action storyInject;
        verification storyInjectDoD : Test { :>> id = "3a2373c1-d084-48db-b0bd-ab734f9158d6"; :>> method = VerificationMethod::test; :>> procedureText = "DELIVERED: kgPromptPathInjects (D0242 part 3), the eighth spine step and the one whose absence made the store measurably useless. hook user-prompt now READS the prompt, recalls, and pushes the facts ahead of the routing reminder with a visible count and duration. Ranking is by AGREEMENT - how many distinct prompt tokens reach the same element - which needs no vocabulary and fixed the noise the human saw in the sample. Injection is gated on a CONFIDENCE verdict with three criteria, each added because a real prompt was classified wrongly without it. Three kill switches at the human's request: the declared D0138 unit deactivation, KEEL_RECALL=off, and LOW-confidence silence. Fail-open throughout, with a latency cap that REPORTS."; }
    // RAN: cargo test --release => 14 suites 0 failures, incl confidence_admits_the_precise_and_refuses_the_diffuse (one case per measured misclassification) | cargo clippy --release --all-targets => 0 errors | AGREEMENT, same prompt before/after: 'should we implement the knowledge graph item now? why did not we earlier?' led with d0086 (the VIEWER's graph renderer) plus two stale critiques matching `earlier`, with d0161 unshown among 366; it now leads with d0153 and d0161 carrying their decision text, at agreement 2 | THE REAL HOOK end to end: HIGH prompt => '[keel recall - pushed before the model, 809ms]' then d0134, hooksInBinaryStory, issue116, issue270 and st013 ('UUIDs should be minted programmatically, not by AI diligence' - the human's own statement, surfaced by the word diligence) | LOW ('please tidy up the workspace') and uninformative ('can you change the gate please') => routing reminder only | KILL SWITCH 1: keel deactivate knowledge-graph-memory => 0 recall lines, keel why STILL works, reactivate => 1 again | KILL SWITCH 2: KEEL_RECALL=off on the keel process => suppressed | KILL SWITCH 3: LOW confidence => silent | cap forced to 1ms => '[keel recall] SKIPPED - recall took 1002ms (cap 1ms)' exit 0, routing intact | .knowledge/ deleted => hook still injects, validate 532 clean, 0 of 52 guards failing.
        part storyInjectDoDR1 : TestResult { :>> id = "5a783d1a-9b67-41dc-b5db-24e24d0e735f"; :>> outcome = VerdictKind::pass; :>> judgedAgainst = "2bec54d"; :>> judgedAt = "2026-08-27"; :>> judgedBy = "claudeOpus5"; }
    }

    verification injectRefineGate : Test { :>> id = "8e340908-1f38-41ad-9177-2d9f35270d0c"; :>> title = "Sprint 479 refine gate (DoR)"; :>> createdAt = "2026-08-27"; :>> createdBy = "claudeOpus5"; :>> method = VerificationMethod::inspect; :>> procedureText = "DoR: the human asked to SEE a sample before this was wired, and the sample is why this sprint exists in the shape it does. On a real prompt about the knowledge graph, recall led with a decision about the VIEWER's graph renderer and two stale critiques matching `earlier`, while d0161 sat unshown among 366 reached - noise that would have cost tokens and taught nothing. Showing it first turned a wiring task into a ranking task. Resolver: kgPromptPathInjects. estimatedPoints=5. #CharteredBy d0242, d0243."; }
    part injectRefineGateR1 : TestResult { :>> id = "0b0cad7f-1250-4471-9f39-2e3cd1998d06"; :>> outcome = VerdictKind::pass; :>> judgedAgainst = "2bec54d"; :>> judgedAt = "2026-08-27"; :>> judgedBy = "claudeOpus5"; }
    verification injectStandupGate : Test { :>> id = "ef11e0c7-5623-42fe-9eed-00254cfb5bf2"; :>> title = "Sprint 479 standup gate"; :>> createdAt = "2026-08-27"; :>> createdBy = "claudeOpus5"; :>> method = VerificationMethod::inspect; :>> procedureText = "Approach: ranking by agreement, then a confidence bar, then wire. Agreement was tested as a HYPOTHESIS before being built - for the failing prompt, 46 elements matched `knowledge` alone, 23 matched `graph` alone, and exactly 9 matched BOTH: d0153, d0161, d0242, dcKnowledgeGraphStore and the process itself, which is the correct answer set. Building it was then confirmation rather than hope. On the kill switch the human asked a good question - or do we just not use keel why? - and the answer is that they are different things: pull needs no switch because not calling it costs nothing, while push is unskippable and must be switchable. keel already had the switch: the process is a deactivatable UNIT (D0138), so no new mechanism was invented."; }
    part injectStandupGateR1 : TestResult { :>> id = "4551e92c-bc05-433f-b3c5-c71af4b44ade"; :>> outcome = VerdictKind::pass; :>> judgedAgainst = "2bec54d"; :>> judgedAt = "2026-08-27"; :>> judgedBy = "claudeOpus5"; }
    verification injectImplementGate : Test { :>> id = "2ff652e7-4988-4d81-81f9-6449d0f156af"; :>> title = "Sprint 479 implement gate"; :>> createdAt = "2026-08-27"; :>> createdBy = "claudeOpus5"; :>> method = VerificationMethod::test; :>> procedureText = "Implemented, and the CONFIDENCE RULE was corrected twice by measurement, both times against my own examples. First, with only identifier-or-agreement, the BEST payload of the three sampled prompts - the pre-model-hooks question, which returns D0134 and the sprint that moved the hooks into the binary - scored LOW and would have been suppressed; its quality came from having 9 seeds, not from agreement, and a rule that rejects its own best example is wrong about what it measures. Adding a focused-seed criterion then created a FALSE POSITIVE: 'what about the thing we discussed yesterday' scored HIGH because `thing` matched 2 elements inside one Issue's title PROSE. Fixed by requiring a NAME match rather than by expanding the filler-word list, which would have been whack-a-mole and would not generalise to another corpus."; }
    // RAN: cargo test --release => 14 suites 0 failures, incl confidence_admits_the_precise_and_refuses_the_diffuse (one case per measured misclassification) | cargo clippy --release --all-targets => 0 errors | AGREEMENT, same prompt before/after: 'should we implement the knowledge graph item now? why did not we earlier?' led with d0086 (the VIEWER's graph renderer) plus two stale critiques matching `earlier`, with d0161 unshown among 366; it now leads with d0153 and d0161 carrying their decision text, at agreement 2 | THE REAL HOOK end to end: HIGH prompt => '[keel recall - pushed before the model, 809ms]' then d0134, hooksInBinaryStory, issue116, issue270 and st013 ('UUIDs should be minted programmatically, not by AI diligence' - the human's own statement, surfaced by the word diligence) | LOW ('please tidy up the workspace') and uninformative ('can you change the gate please') => routing reminder only | KILL SWITCH 1: keel deactivate knowledge-graph-memory => 0 recall lines, keel why STILL works, reactivate => 1 again | KILL SWITCH 2: KEEL_RECALL=off on the keel process => suppressed | KILL SWITCH 3: LOW confidence => silent | cap forced to 1ms => '[keel recall] SKIPPED - recall took 1002ms (cap 1ms)' exit 0, routing intact | .knowledge/ deleted => hook still injects, validate 532 clean, 0 of 52 guards failing.
    part injectImplementGateR1 : TestResult { :>> id = "58941d90-e138-46a5-b59d-0a7cc8a54fcd"; :>> outcome = VerdictKind::pass; :>> judgedAgainst = "2bec54d"; :>> judgedAt = "2026-08-27"; :>> judgedBy = "claudeOpus5"; }
    verification injectReviewGate : Test { :>> id = "70beec08-79dc-4500-8c8c-f963773b53b7"; :>> title = "Sprint 479 review gate"; :>> createdAt = "2026-08-27"; :>> createdBy = "claudeOpus5"; :>> method = VerificationMethod::inspect; :>> procedureText = "Diff reviewed. The kill-switch semantics are the part worth checking and they are right: deactivating the unit removes the PUSH while `keel why` keeps working, so the capability is not destroyed by turning off the automation. Stated in the code and the DoD rather than left implied: deleting `.knowledge/` is NO LONGER a kill switch, because D0243 made seeding corpus-derived - it used to be the removability story, and a reader who remembered the old answer would be wrong. The latency cap REPORTS when hit rather than silently skipping, because a recall that quietly doubles every turn's latency is the kind of cost discovered months later."; }
    part injectReviewGateR1 : TestResult { :>> id = "effc4f8b-621a-4404-871e-e360c58487f7"; :>> outcome = VerdictKind::pass; :>> judgedAgainst = "2bec54d"; :>> judgedAt = "2026-08-27"; :>> judgedBy = "claudeOpus5"; }
    verification injectCloseOutGate : Test { :>> id = "818353fd-01d9-492d-846a-fd4c223f5dbd"; :>> title = "Sprint 479 closeOut gate (autonomous, D0049)"; :>> createdAt = "2026-08-27"; :>> createdBy = "claudeOpus5"; :>> method = VerificationMethod::inspect; :>> procedureText = "Autonomous closeOut (D0049): the DoD is recorded pass with its RAN receipt; the frontier was read back from keel whats-next. Four of the five D0242 items are done. NO CLAIM IS MADE HERE ABOUT ANSWER QUALITY OR SPEED - the mechanism now pushes, and whether pushing helps is kgInjectionProvenOnTheTrap, which carries the honest-outcome clause: if the trap shows no reduction in tool-calls-to-answer, record that and keep the command tier rather than ship injection because it was planned. Self-evidencing (D0051): no human confirmation claimed."; }
    part injectCloseOutGateR1 : TestResult { :>> id = "501e2095-4874-4c64-9f59-7279f97b7380"; :>> outcome = VerdictKind::pass; :>> judgedAgainst = "2bec54d"; :>> judgedAt = "2026-08-27"; :>> judgedBy = "claudeOpus5"; }
    verification injectRetroGate : Test { :>> id = "5e585ab2-ec48-4838-bdca-88f2a970bcc0"; :>> title = "Sprint 479 retro gate (autonomous, D0049)"; :>> createdAt = "2026-08-27"; :>> createdBy = "claudeOpus5"; :>> method = VerificationMethod::analyze; :>> procedureText = "Autonomous retro (D0049). WELL: the human asking to see a sample before wiring was the highest-value intervention in this whole arc. The mechanism was READY and the payload was noise; wiring it first would have shipped a feature that made every turn worse while looking done, and the sample cost one command. That generalises past this feature: for anything that changes every turn, show the artefact before installing the automation. FINDING: my confidence rule was wrong twice and BOTH errors were found by running it over the same six prompts rather than by reasoning about it - once rejecting its own best example, once admitting a prompt about nothing. A threshold rule needs a labelled set, however small, or it encodes the author's intuition and calls it a measure. AVOIDABLE-ISSUE SCAN: six prompts is a tiny set and I tuned three criteria against it, which is overfitting by any honest standard - the trap item is the only thing that will show whether these thresholds generalise, and it should use prompts NOT in this six. Estimate 5 pts held."; }
    part injectRetroGateR1 : TestResult { :>> id = "92a4a880-6683-4fe0-84d3-c4e692383975"; :>> outcome = VerdictKind::pass; :>> judgedAgainst = "2bec54d"; :>> judgedAt = "2026-08-27"; :>> judgedBy = "claudeOpus5"; }
}
