// ProjectDeliveryS201 — Sprint 201: surfaceDodDescription (issue064) — the keel serve console now shows a
// task's DoD procedureText as its description, instead of "no authored attrs" + the structural NextWork
// contains-edge. Field-discovered via serve dogfood. EXECUTE (display; no view-meaning change). 1 pt. AUTONOMOUS (D0049).
package ProjectDeliveryS201 {
    private import EngineElement::*;
    private import EngineWork::*;
    private import EngineVerification::*;
    private import EngineRequirements::*;
    private import EngineRelationships::*;

    #CharteredBy dependency from surfaceDodDescriptionStory to issue064;

    part surfaceDodDescriptionStory : Story {
        :>> id = "63940516-2c7d-4e8f-c201-51627384c001";
        :>> title = "Sprint 201: surfaceDodDescription (1 pt) - console shows a task's DoD procedureText as its description (issue064)";
        :>> createdAt = "2026-07-14"; :>> createdBy = "wweatherholtz"; :>> kind = WorkKind::code; :>> priority = WorkPriority::p2; :>> owner = "claudeOpus"; :>> estimatedPoints = 1;
    }

    action def DeliveryRunS201 {
        action storySurfaceDodDescription;
        verification storySurfaceDodDescriptionDoD : Test { :>> id = "63940516-2c7d-4e8f-c201-51627384c002"; :>> method = VerificationMethod::test; :>> procedureText = "Resolves issue064 (field-discovered via keel serve). An `action <name>;` task carries NO authored attrs — correct — but its human description lives in the verify-linked <name>DoD Test's procedureText, which the console never surfaced; it showed the low-value `contains` edge from the NextWork action-def container, so a fully-specified task LOOKED empty. FIX: (1) view.rs item_detail resolves <name>DoD and emits a `dod` field {method, procedureText}; the Model->JSON core extracted as item_detail_json for unit-testing (D0047). (2) console.html openItem renders a prominent 'Definition of Done' block when d.dod is present + softens the empty-attrs note. Display-only — item_detail's existing fields are unchanged, so no computed-view MEANING change (EXECUTE, not CHANGE). VERIFIED LIVE: /api/item/proveProcessDeployment now returns attrs=0 + dod.method=inspect + dod.procedureText='Resolves issue061...'. VERIFY: unit test item_detail_surfaces_dod_procedure_text (a task WITH a DoD surfaces its text; a task WITHOUT one carries no dod); clippy -D clean; cargo test (80 lib) green; keel validate + guard green."; }
        part storySurfaceDodDescriptionDoDR1 : TestResult { :>> id = "63940516-2c7d-4e8f-c201-51627384c003"; :>> outcome = VerdictKind::pass; :>> judgedAgainst = "f4ae61b"; :>> judgedAt = "2026-07-14"; :>> judgedBy = "claudeOpus"; }
    }

    verification sddRefineGate : Test { :>> id = "63940516-2c7d-4e8f-c201-51627384c004"; :>> title = "Sprint 201 refine gate (DoR)"; :>> createdAt = "2026-07-14"; :>> createdBy = "claudeOpus"; :>> method = VerificationMethod::inspect; :>> procedureText = "DoR: issue064 triaged (resolver surfaceDodDescription in NextWork); the fix is a bounded display change (item_detail `dod` field + console render), no view-meaning change. estimatedPoints=1. #CharteredBy issue064. DoR met."; }
    part sddRefineGateR1 : TestResult { :>> id = "63940516-2c7d-4e8f-c201-51627384c005"; :>> outcome = VerdictKind::pass; :>> judgedAgainst = "f4ae61b"; :>> judgedAt = "2026-07-14"; :>> judgedBy = "claudeOpus"; }
    verification sddStandupGate : Test { :>> id = "63940516-2c7d-4e8f-c201-51627384c006"; :>> title = "Sprint 201 standup gate"; :>> createdAt = "2026-07-14"; :>> createdBy = "claudeOpus"; :>> method = VerificationMethod::inspect; :>> procedureText = "Approach: extract item_detail_json (testable); resolve <name>DoD -> `dod` field; render the DoD block in console.html openItem. No blockers."; }
    part sddStandupGateR1 : TestResult { :>> id = "63940516-2c7d-4e8f-c201-51627384c007"; :>> outcome = VerdictKind::pass; :>> judgedAgainst = "f4ae61b"; :>> judgedAt = "2026-07-14"; :>> judgedBy = "claudeOpus"; }
    verification sddImplementGate : Test { :>> id = "63940516-2c7d-4e8f-c201-51627384c008"; :>> title = "Sprint 201 implement gate"; :>> createdAt = "2026-07-14"; :>> createdBy = "claudeOpus"; :>> method = VerificationMethod::test; :>> procedureText = "item_detail_json + `dod` field + console DoD block landed; unit test green; verified live against the real repo (/api/item/proveProcessDeployment shows its DoD). clippy -D clean; cargo test (80 lib) green; keel validate + guard green."; }
    part sddImplementGateR1 : TestResult { :>> id = "63940516-2c7d-4e8f-c201-51627384c009"; :>> outcome = VerdictKind::pass; :>> judgedAgainst = "f4ae61b"; :>> judgedAt = "2026-07-14"; :>> judgedBy = "claudeOpus"; }
    verification sddReviewGate : Test { :>> id = "63940516-2c7d-4e8f-c201-51627384c00a"; :>> title = "Sprint 201 review gate"; :>> createdAt = "2026-07-14"; :>> createdBy = "claudeOpus"; :>> method = VerificationMethod::inspect; :>> procedureText = "Reviewed. Small, correct, high-legibility fix: the console no longer misrepresents a well-specified task as empty — it shows the DoD criterion, which IS the task's description in this model. The item_detail contract is additive (a new `dod` field; existing fields unchanged), so no consumer breaks and no computed-view meaning shifts. Extracting item_detail_json made the core unit-testable (D0047). Honest scope: only the <name>DoD convention is resolved (the canonical task-description source); other item types are unaffected. Clean."; }
    part sddReviewGateR1 : TestResult { :>> id = "63940516-2c7d-4e8f-c201-51627384c00b"; :>> outcome = VerdictKind::pass; :>> judgedAgainst = "f4ae61b"; :>> judgedAt = "2026-07-14"; :>> judgedBy = "claudeOpus"; }
    verification sddCloseOutGate : Test { :>> id = "63940516-2c7d-4e8f-c201-51627384c00c"; :>> title = "Sprint 201 closeOut gate (autonomous, D0049)"; :>> createdAt = "2026-07-14"; :>> createdBy = "claudeOpus"; :>> method = VerificationMethod::inspect; :>> procedureText = "Autonomous closeOut (D0049): DoD pass; issue064 resolved (surfaceDodDescription done). clippy + cargo test + keel validate + guard green. Self-evidencing (D0051). NEXT: Sprint 202 = fixServeOrientPerf (issue063 — spawn_blocking + trim the ~15 fallback git spawns, guarded by a byte-identical-orient test)."; }
    part sddCloseOutGateR1 : TestResult { :>> id = "63940516-2c7d-4e8f-c201-51627384c00d"; :>> outcome = VerdictKind::pass; :>> judgedAgainst = "f4ae61b"; :>> judgedAt = "2026-07-14"; :>> judgedBy = "claudeOpus"; }
    verification sddRetroGate : Test { :>> id = "63940516-2c7d-4e8f-c201-51627384c00e"; :>> title = "Sprint 201 retro gate (autonomous, D0049)"; :>> createdAt = "2026-07-14"; :>> createdBy = "claudeOpus"; :>> method = VerificationMethod::analyze; :>> procedureText = "Autonomous retro (D0049). WELL: a field-dogfood finding (the human using keel serve) went issue -> triaged -> fixed -> verified-live in one loop; the fix surfaces data the model already had (the DoD text) rather than adding authored fields — legibility, not new truth. AVOIDABLE-ISSUE SCAN: the root was a serve-view gap, not a data gap — a reminder that 'the console shows nothing' usually means 'the view doesn't resolve the linked item', not 'no data'. LESSON: when a task looks empty, resolve its DoD before assuming. Estimate 1 pt held. NEXT: fixServeOrientPerf (issue063). Note the A-issue framing was CORRECTED mid-analysis (measured 19 git spawns, not hundreds) — honest-measurement-before-fix paid off."; }
    part sddRetroGateR1 : TestResult { :>> id = "63940516-2c7d-4e8f-c201-51627384c00f"; :>> outcome = VerdictKind::pass; :>> judgedAgainst = "f4ae61b"; :>> judgedAt = "2026-07-14"; :>> judgedBy = "claudeOpus"; }
}
