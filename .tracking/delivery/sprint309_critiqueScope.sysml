// ProjectDeliveryS309 — Sprint 309: three computed views now agree on what is in scope.
// EXECUTE. 3 pts.
package ProjectDeliveryS309 {
    private import EngineElement::*;
    private import EngineWork::*;
    private import EngineVerification::*;
    private import EngineRelationships::*;

    #CharteredBy dependency from critiqueScopeStory to issue127;

    part critiqueScopeStory : Story {
        :>> id = "0d800300-0814-6300-9b3e-000000300300";
        :>> title = "Sprint 309: exclude superseded elements from critique-coverage (3 pts)";
        :>> createdAt = "2026-08-15"; :>> createdBy = "claudeOpus5"; :>> kind = WorkKind::code; :>> priority = WorkPriority::p0; :>> owner = "claudeOpus5"; :>> estimatedPoints = 3;
    }

    action def DeliveryRunS309 {
        action storyCritiqueScope;
        verification storyCritiqueScopeDoD : Test { :>> id = "0d800301-0814-6301-9b3e-000000300301"; :>> method = VerificationMethod::test; :>> procedureText = "Delivers dcCritiqueCoverageSupersede, resolving issue127 and issue131. AUTHORISED BY THE HUMAN'S RECORDED DISPOSITION: issue127 is dispositioned ACT by wweatherholtz, which is the sign-off the item's own DoD required before a change to what a computed view counts. THE DEFECT: `compute_coverage` and `compute_tier_satisfaction` both build a descoped set from supersede edges and filter their targets by it; `critique_coverage` filtered only by the governed charter-time rule, so a RETIRED element stayed in the denominator permanently and its critique had to be maintained to stop the number falling. Three computed views disagreeing about what is in scope is dual truth about scope itself. BOTH COUNTS REPORTED, as the DoD demanded — Decision 70 governed/24 covered -> 69/24; Need 39/3 -> 34/3; SystemRequirement 70/10 -> 65/5; gaps 137 -> 136. The SR covered count HALVES, and that is the honest consequence rather than a regression: the five it counted are the serve-discipline originals sprint 306 superseded, whose critiques remain readable and #Verify-linked but which are no longer live requirements the view is asked about. VERIFIED: a regression test asserts every supersede-targeted element in this repo's own model reports governed=false, so the three views cannot silently diverge again. clippy clean; 218 tests; validate 334 clean; 33 guards green."; }
        part storyCritiqueScopeDoDR1 : TestResult { :>> id = "0d800302-0814-6302-9b3e-000000300302"; :>> outcome = VerdictKind::pass; :>> judgedAgainst = "bc8097f"; :>> judgedAt = "2026-08-15"; :>> judgedBy = "claudeOpus5"; }
    }

    verification csRefineGate : Test { :>> id = "0d800303-0814-6303-9b3e-000000300303"; :>> title = "Sprint 309 refine gate (DoR)"; :>> createdAt = "2026-08-15"; :>> createdBy = "claudeOpus5"; :>> method = VerificationMethod::inspect; :>> procedureText = "DoR. This change was written once before and REVERTED, because a blanket `git add -A` landed it without the sign-off its own DoD required (issue131). It returns here with that sign-off recorded as a typed ACT disposition naming the human, and with both the before and after counts stated in the record rather than left for a reader to reconstruct. estimatedPoints=3."; }
    part csRefineGateR1 : TestResult { :>> id = "0d800304-0814-6304-9b3e-000000300304"; :>> outcome = VerdictKind::pass; :>> judgedAgainst = "bc8097f"; :>> judgedAt = "2026-08-15"; :>> judgedBy = "claudeOpus5"; }

    verification csStandupGate : Test { :>> id = "0d800305-0814-6305-9b3e-000000300305"; :>> title = "Sprint 309 standup gate"; :>> createdAt = "2026-08-15"; :>> createdBy = "claudeOpus5"; :>> method = VerificationMethod::inspect; :>> procedureText = "Approach: reuse the descoped-set construction the two sibling views already use, rather than inventing a second way to express the same predicate; assert the agreement as a test so it holds after the next change. No blockers."; }
    part csStandupGateR1 : TestResult { :>> id = "0d800306-0814-6306-9b3e-000000300306"; :>> outcome = VerdictKind::pass; :>> judgedAgainst = "bc8097f"; :>> judgedAt = "2026-08-15"; :>> judgedBy = "claudeOpus5"; }

    verification csImplementGate : Test { :>> id = "0d800307-0814-6307-9b3e-000000300307"; :>> title = "Sprint 309 implement gate"; :>> createdAt = "2026-08-15"; :>> createdBy = "claudeOpus5"; :>> method = VerificationMethod::test; :>> procedureText = "THE TEST CAUGHT MY OWN FIX BEING INCOMPLETE, AND THEN CAUGHT THE TEST BEING WRONG. First draft asserted a superseded element's name appeared NOWHERE in the view's JSON; it failed on `nViewerMultiStakeholder`. The failure was real information but the assertion was wrong: the `elements` array lists every element and marks scope per row, which is exactly what makes the view auditable, and a superseded element appearing there with `governed: false` is correct. Had I taken the failure at face value and 'fixed' the code, I would have driven it to HIDE retired elements rather than descope them — trading an inflated denominator for an unauditable view. The corrected assertion is the property that actually matters: a supersede-targeted element reports `governed: false` and is absent from the GAP set, while remaining visible in the detail. That distinction — descoped versus hidden — is the whole difference between a view a reader can check and one they have to trust."; }
    part csImplementGateR1 : TestResult { :>> id = "0d800308-0814-6308-9b3e-000000300308"; :>> outcome = VerdictKind::pass; :>> judgedAgainst = "bc8097f"; :>> judgedAt = "2026-08-15"; :>> judgedBy = "claudeOpus5"; }

    verification csReviewGate : Test { :>> id = "0d800309-0814-6309-9b3e-000000300309"; :>> title = "Sprint 309 review gate"; :>> createdAt = "2026-08-15"; :>> createdBy = "claudeOpus5"; :>> method = VerificationMethod::inspect; :>> procedureText = "Reviewed. The numbers moving DOWN on `covered` is the part most likely to be misread later, so the reason is written into the code comment and not only into this record: the five SRs that stopped counting as covered are retired requirements, and a retired requirement being 'covered' was never the question `critique-coverage` is asked. The critiques on those originals are untouched and still #Verify-linked, which is what keeps the sprint 305 findings and the sprint 306 corrections legible together."; }
    part csReviewGateR1 : TestResult { :>> id = "0d80030a-0814-630a-9b3e-00000030030a"; :>> outcome = VerdictKind::pass; :>> judgedAgainst = "bc8097f"; :>> judgedAt = "2026-08-15"; :>> judgedBy = "claudeOpus5"; }

    verification csCloseOutGate : Test { :>> id = "0d80030b-0814-630b-9b3e-00000030030b"; :>> title = "Sprint 309 closeOut gate (autonomous, D0049)"; :>> createdAt = "2026-08-15"; :>> createdBy = "claudeOpus5"; :>> method = VerificationMethod::inspect; :>> procedureText = "Autonomous closeOut (D0049); authorised by the human's ACT disposition on issue127. issue127 and issue131 resolve through dcCritiqueCoverageSupersede. The ready frontier is now EMPTY and every >= Medium finding in the model carries a typed human disposition. clippy clean; 218 tests; validate 334 clean; check-engine clean; 33 guards green."; }
    part csCloseOutGateR1 : TestResult { :>> id = "0d80030c-0814-630c-9b3e-00000030030c"; :>> outcome = VerdictKind::pass; :>> judgedAgainst = "bc8097f"; :>> judgedAt = "2026-08-15"; :>> judgedBy = "claudeOpus5"; }

    verification csRetroGate : Test { :>> id = "0d80030d-0814-630d-9b3e-00000030030d"; :>> title = "Sprint 309 retro gate (autonomous, D0049)"; :>> createdAt = "2026-08-15"; :>> createdBy = "claudeOpus5"; :>> method = VerificationMethod::analyze; :>> procedureText = "Autonomous retro (D0049) under D0131's retroTrack. WELL: (1) the change returned through the front door — reverted when it landed unauthorised, then re-landed on a recorded disposition with both counts stated, which is the only way a metric change stays trustworthy; (2) the regression test earned its keep twice in five minutes, first by finding the fix incomplete and then by being WRONG in a way that would have driven a worse fix, and the distinction it forced (descoped, not hidden) is now written down. AVOIDABLE-ISSUE: none new. THE SESSION-LEVEL OBSERVATION, recorded because it is the through-line of the whole day: nearly every defect found today was a tool reporting a confident WRONG answer rather than an error — an empty registry for a nonexistent path, PASS over 80% of a corpus never read, 0 of 10 edges from a case mismatch, 169 files 'missing' that were never named, a downstream project's critical code ranked below cosmetic. The counter-check that caught all of them is the same one: compare the tool's own number against a number established independently, BEFORE reading its verdict. Estimate 3 pts, delivered."; }
    part csRetroGateR1 : TestResult { :>> id = "0d80030e-0814-630e-9b3e-00000030030e"; :>> outcome = VerdictKind::pass; :>> judgedAgainst = "bc8097f"; :>> judgedAt = "2026-08-15"; :>> judgedBy = "claudeOpus5"; }
}
