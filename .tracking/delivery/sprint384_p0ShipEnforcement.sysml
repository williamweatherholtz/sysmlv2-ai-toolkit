// ProjectDeliveryS384 — Sprint 384: P0 - the enforcement ships: init parity, fail-loud, declared profiles, the fire-ledger. EXECUTE. 13 pts.
package ProjectDeliveryS384 {
    private import EngineElement::*;
    private import EngineWork::*;
    private import EngineVerification::*;
    private import EngineRelationships::*;

    #CharteredBy dependency from p0ShipEnforcementStory to d0174;

    part p0ShipEnforcementStory : Story {
        :>> id = "417cb6f2-52a2-4c0c-af1c-01789a166520";
        :>> title = "Sprint 384: P0 - a downstream keel init gets the self-build's enforcement (13 pts)";
        :>> createdAt = "2026-08-21"; :>> createdBy = "claudeFable5"; :>> kind = WorkKind::code; :>> priority = WorkPriority::p0; :>> owner = "claudeFable5"; :>> estimatedPoints = 13;
    }

    action def DeliveryRunS384 {
        action storyP0ShipEnforcement;
        verification storyP0ShipEnforcementDoD : Test { :>> id = "071550cb-4be0-4849-9a38-4832b92bb514"; :>> method = VerificationMethod::test; :>> procedureText = "DELIVERED BACKLOG ITEMS: p0ClaudeScaffold, p0SyncClaude, p0FailLoud, p0Profiles, p0InstallDocs, p0SubagentStop, p0HardeningInventory. THE SURFACE: keel-cli/src/claude_surface.rs is the ONE generator for the keel-owned .claude/ subset - settings.json with FIVE hook events (SubagentStop added), the keel output style embedded from the self-build's own copy (K3 parity by construction), one .claude/skills/<name>/SKILL.md per registry entry (36 = 36 asserted at init AND in init_smoke), the optional CI template (rules step activates with P1), and the protected-path deny list as data (PROTECTED_PATHS, each refusal naming its sanctioned command per K13). SYNC: keel sync-claude deep-merges keel-owned entries only - proven by test that a foreign hook group, a foreign permission, and a foreign top-level key survive byte-for-byte, that a stale keel entry is REPLACED not duplicated, and that merge is idempotent; --check IS guard 41 (claude-surface-drift), version skew a warning, drift a violation. FAIL-LOUD (K2): every hook resolves KEEL_BIN then PATH (a test bans the cwd-relative target probe), missing binary warns visibly naming the install URL; the scaffolded pre-commit now EXITS 1 without the binary with the remedy line; the pure-shell PreToolUse test DENIES protected-path writes with no binary at all; orient warns loudly when hooksPath is unset. PROFILES (P0.4): --profile strict|guided declared never inferred - empty dir defaults strict, existing content REFUSES without the flag (exit 2, run live), the fact recorded in .engine/contracts/adoption-profile.toml. FIRE-LEDGER (P0.1/D0180 plumbing): every hook fire appends one JSONL line (ts, session, event, decision, exit, ms) to .keel/metrics/hooks.jsonl, and a session's first non-subagent-stop fire stores the tree-fingerprint baseline. SUBAGENT-STOP (P0.6): gates only when the tree changed during the subagent's lifetime - no baseline = systemMessage advisory, unchanged = silent pass, changed = the full turn gate; ALL FOUR BRANCHES RUN LIVE on a scaffold copy, including a red tree producing the block JSON. INVENTORY (P0.7/K2): the hardening enforcementPoints lens enumerates every enforcement point with absent/error/timeout behavior - its FIRST RUN found the self-build's own open point (no SubagentStop), fixed by adopting our own surface via sync-claude (personal deny entries survived the merge, drift guard green). INSTALL DOCS (P0.5/d0175): README documents the release-channel install, the declared-profile flow, and the harness-support matrix (the D0186 trigger enabler). 218 tests; clippy 0; guard 41 registered everywhere a guard lives."; }
        part storyP0ShipEnforcementDoDR1 : TestResult { :>> id = "9d59fbfc-24c0-4d71-853a-966737f7829c"; :>> outcome = VerdictKind::pass; :>> judgedAgainst = "11f4cac"; :>> judgedAt = "2026-08-21"; :>> judgedBy = "claudeFable5"; }
    }

    verification p0ShipEnforcementRefineGate : Test { :>> id = "fb15c00b-8712-4771-a9c1-7dfddf02496c"; :>> title = "Sprint 384 refine gate (DoR)"; :>> createdAt = "2026-08-21"; :>> createdBy = "claudeFable5"; :>> method = VerificationMethod::inspect; :>> procedureText = "DoR. The head of the ranked frontier, unblocked this turn by the human's signature on all fifteen program Decisions (their words: accepted all). Scope = the seven p0 backlog items authored by the panel session, each with a behavioral DoD; the proposal sizes P0 at ~1 sprint. estimatedPoints=13."; }
    part p0ShipEnforcementRefineGateR1 : TestResult { :>> id = "11c0401c-05c9-4c4c-b2b0-0cdb425eda35"; :>> outcome = VerdictKind::pass; :>> judgedAgainst = "11f4cac"; :>> judgedAt = "2026-08-21"; :>> judgedBy = "claudeFable5"; }
    verification p0ShipEnforcementStandupGate : Test { :>> id = "344ed4cc-8bd3-44be-8bcb-42c56d7353a4"; :>> title = "Sprint 384 standup gate"; :>> createdAt = "2026-08-21"; :>> createdBy = "claudeFable5"; :>> method = VerificationMethod::inspect; :>> procedureText = "Approach: ONE generator module for the whole keel-owned surface, consumed by init, sync-claude, and the drift guard - the one-implementation-one-surface rule from D0174 itself. The self-build ADOPTS its own output (sync-claude run here, SubagentStop + KEEL_BIN resolver + fire-ledger now live locally), so parity is exercised in both directions. Honest limit, stated: the spawned-claude-p fire-ledger acceptance and the Linux half of the behavioral matrix ride the NEXT live sessions and CI - the ledger plumbing is unit- and live-exercised here on Windows; a fire-ledger line from a real spawned session is P5's launcher acceptance where spawning exists."; }
    part p0ShipEnforcementStandupGateR1 : TestResult { :>> id = "7c256973-5f75-4f80-a08a-d379bb71bcb4"; :>> outcome = VerdictKind::pass; :>> judgedAgainst = "11f4cac"; :>> judgedAt = "2026-08-21"; :>> judgedBy = "claudeFable5"; }
    verification p0ShipEnforcementImplementGate : Test { :>> id = "29c4b008-8d91-4f03-8694-b0ce75333dee"; :>> title = "Sprint 384 implement gate"; :>> createdAt = "2026-08-21"; :>> createdBy = "claudeFable5"; :>> method = VerificationMethod::test; :>> procedureText = "Every branch RUN, not read: fresh init (5 events, 36=36 skills, strict declared, CI template, profile refusal exit 2); pre-write deny JSON on a protected path in a strict scaffold and silence on a non-protected one; ledger lines and baseline written; subagent-stop all four branches including the red-tree block JSON; sync-claude then --check green on both the scaffold and the SELF-BUILD after adoption. TWO DEFECTS CAUGHT BY RUNNING: the wrapper wrote the baseline before dispatching subagent-stop itself, so the no-baseline advisory could never fire (a subagent whose first fire is its own stop would have baselined the post-work tree and skipped the gate); and the enforcementPoints lens found the self-build missing SubagentStop on its first run. Clippy caught two panic paths in the merge (indexing, expect) - rewritten total."; }
    part p0ShipEnforcementImplementGateR1 : TestResult { :>> id = "194fed30-e728-4f76-ae5a-2430edef6416"; :>> outcome = VerdictKind::pass; :>> judgedAgainst = "11f4cac"; :>> judgedAt = "2026-08-21"; :>> judgedBy = "claudeFable5"; }
    verification p0ShipEnforcementReviewGate : Test { :>> id = "26621e76-676e-407d-8559-6789ffd96ebf"; :>> title = "Sprint 384 review gate — three passes per D0172"; :>> createdAt = "2026-08-21"; :>> createdBy = "claudeFable5"; :>> method = VerificationMethod::inspect; :>> procedureText = "PASS 1, CLAIMS vs emitted/computed: settings read back from the WRITTEN file (events, style, no target/ probe); counts from init output and init_smoke assertions; inventory rows from the lens's own JSON; 218 tests, clippy 0, 41 guards. PASS 2, BOUNDARY: merge probed with a foreign group + stale keel entry + non-object settings; profile probed with the empty dir, the existing-content dir, and a bad value; ledger write failure prints rather than swallows (K2). PASS 3, OWN DIFF: the baseline-before-dispatch ordering defect was THIS sprint's own code, found by exercising the branch it killed. WHAT A REVIEWER SHOULD ATTACK: is_keel_hook identifies ownership by command-content heuristics - a user hook that itself invokes keel hook would be claimed as keel-owned and replaced on sync; accepted as the cost of content-based ownership, stated here rather than discovered."; }
    part p0ShipEnforcementReviewGateR1 : TestResult { :>> id = "b677c615-c47e-4f31-97be-ddd1df54975b"; :>> outcome = VerdictKind::pass; :>> judgedAgainst = "11f4cac"; :>> judgedAt = "2026-08-21"; :>> judgedBy = "claudeFable5"; }
    verification p0ShipEnforcementCloseOutGate : Test { :>> id = "940c9ecb-4579-46e5-bb35-70555387b7a8"; :>> title = "Sprint 384 closeOut gate (autonomous, D0049)"; :>> createdAt = "2026-08-21"; :>> createdBy = "claudeFable5"; :>> method = VerificationMethod::inspect; :>> procedureText = "Autonomous closeOut (D0049). Seven p0 DoDs flipped to pass at the judging HEAD; guard 41 in GUARD_NAMES/dispatch/guards.md/CLAUDE.md counts; CLAUDE.md's in-loop paragraph and README's quickstart doc-synced in the same change; the self-build's .claude/ regenerated by its own binary and committed. validate clean; 41 guards ALL PASS; 218 tests; clippy 0."; }
    part p0ShipEnforcementCloseOutGateR1 : TestResult { :>> id = "9a7b8e5d-c2dc-4385-b7d9-19c21b203d5e"; :>> outcome = VerdictKind::pass; :>> judgedAgainst = "11f4cac"; :>> judgedAt = "2026-08-21"; :>> judgedBy = "claudeFable5"; }
    verification p0ShipEnforcementRetroGate : Test { :>> id = "960e4f4c-d631-4cc8-a566-d35d68e40364"; :>> title = "Sprint 384 retro gate (autonomous, D0049)"; :>> createdAt = "2026-08-21"; :>> createdBy = "claudeFable5"; :>> method = VerificationMethod::analyze; :>> procedureText = "Autonomous retro (D0049). AVOIDABLE-ISSUE SCAN under rcRecurrence: (1) the ordering defect (baseline written by the event that reads it) is the state-initialized-by-its-own-consumer class - first occurrence, killed in-sprint by branch-exercising, which the implement gate now names as the standing practice; (2) literal-replacement authoring failed to match THREE times this sprint (em-dash and escape mismatches in python replace needles plus one heredoc parse break) - the authoring-mangling family, and per D0172 second-occurrence the preventing change is now mechanical practice: fills go through a written script file with assert-guarded replaces, never an inline heredoc. WELL: (1) the inventory lens found a real open point on its first run - a control that catches its own author's tree is earning its keep; (2) the self-build eating its own scaffold output turned K3 parity from a claim into a diff; (3) the panel's per-item DoDs were followable as written - the decomposition survived contact with implementation. Estimate 13 pts, delivered."; }
    part p0ShipEnforcementRetroGateR1 : TestResult { :>> id = "4f18eefc-8f3b-4888-993a-442c1a50d764"; :>> outcome = VerdictKind::pass; :>> judgedAgainst = "11f4cac"; :>> judgedAt = "2026-08-21"; :>> judgedBy = "claudeFable5"; }
}
