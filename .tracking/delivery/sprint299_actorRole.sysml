// ProjectDeliveryS299 — Sprint 299: D0146 applied — `Actor.role` exists, enrollment requires it, and
// authority is checked against a DECLARED policy. Plus `keel accept`, the CLI the single human gate
// never had. CHANGE + EXECUTE. 8 pts.
package ProjectDeliveryS299 {
    private import EngineElement::*;
    private import EngineWork::*;
    private import EngineVerification::*;
    private import EngineRelationships::*;

    #CharteredBy dependency from actorRoleStory to d0146;

    part actorRoleStory : Story {
        :>> id = "0d800262-0814-6262-9b3e-000000300262";
        :>> title = "Sprint 299: Actor.role + declared attestation policy + keel accept (8 pts)";
        :>> createdAt = "2026-08-15"; :>> createdBy = "claudeOpus5"; :>> kind = WorkKind::code; :>> priority = WorkPriority::p0; :>> owner = "claudeOpus5"; :>> estimatedPoints = 8;
    }

    action def DeliveryRunS299 {
        action storyActorRole;
        verification storyActorRoleDoD : Test { :>> id = "0d800263-0814-6263-9b3e-000000300263"; :>> method = VerificationMethod::test; :>> procedureText = "Applies D0146 (accepted by wweatherholtz 2026-08-15) and closes the ROLE half of srDcEnrollment and srDcAuthorityFromRegistry; resolves issue110. FIRST, A GAP FOUND WHILE TRYING TO RECORD THE ACCEPTANCE ITSELF: `write::accept_decision` existed and was reachable ONLY through `keel serve`'s HTTP API, so recording the one attestation this engine treats as irreducibly human meant running a web server or hand-editing the decision file. Same defect as `record issue` (sprint 291) — a mandated path with no implementation — and here it applies to the gate the entire autonomous loop pauses for. Built `keel accept <decision> --note --by --date` FIRST, then used it for all three acceptances, per D0040 (recurring task with no command => build the command). It cannot be used to self-accept: `confirmation-authenticity` independently checks the judge is a Person. DELIVERED: (1) `attribute role : String[0..1]` on `part def Actor` — a free String, not an enum, because the process explicitly permits a project-declared role and a closed vocabulary in FROZEN core would force every project through a schema sign-off to name its own; optional so no existing actor needs migrating. Kernel-checked: validate_schema 15/15. (2) `keel enroll --role` is REQUIRED — the process says of kind and role that 'neither may be defaulted' — and role is written for BOTH kinds, because it is what an actor DOES rather than what they ARE. (3) `.engine/contracts/attestation-policy.toml`, a DECLARED policy per attestation class, because srDcAuthorityFromRegistry asks for the check to be 'against the declared policy' and a policy compiled into the binary is not declared. `attestation-authority` now reads it. (4) All seven registered actors carry a role: wweatherholtz supervisor, the three AI contributors, the three panel critics reviewer. VERIFIED BOTH DIRECTIONS: demoting the supervisor to contributor FAILS with 'role is contributor and this class permits [supervisor]'; REMOVING the role fails with a DIFFERENT message naming the remedy, because an absent role and a wrong one need different fixes; an AI with the right role still fails a human-only class, so role never launders kind. An absent contract falls back to human-only, so deleting the file cannot disable the check. clippy clean; 141 lib tests; validate 322 clean; 32 guards green."; }
        part storyActorRoleDoDR1 : TestResult { :>> id = "0d800264-0814-6264-9b3e-000000300264"; :>> outcome = VerdictKind::pass; :>> judgedAgainst = "a6b7123"; :>> judgedAt = "2026-08-15"; :>> judgedBy = "claudeOpus5"; }
    }

    verification arRefineGate : Test { :>> id = "0d800265-0814-6265-9b3e-000000300265"; :>> title = "Sprint 299 refine gate (DoR)"; :>> createdAt = "2026-08-15"; :>> createdBy = "claudeOpus5"; :>> method = VerificationMethod::inspect; :>> procedureText = "DoR. The human accepted D0146/D0147/D0148 in one reply and directed the follow-on work, so this is the CHANGE route with the sign-off already in hand. CONSUMER CHECK (dorConsumer, D0144): the consumers of a new `role` attribute are the enrollment command, the authority guard, and the actor registry — all three had to move together, because a schema field nothing reads is the dead schema D0142 spent a sprint removing. estimatedPoints=8. DoR met."; }
    part arRefineGateR1 : TestResult { :>> id = "0d800266-0814-6266-9b3e-000000300266"; :>> outcome = VerdictKind::pass; :>> judgedAgainst = "a6b7123"; :>> judgedAt = "2026-08-15"; :>> judgedBy = "claudeOpus5"; }

    verification arStandupGate : Test { :>> id = "0d800267-0814-6267-9b3e-000000300267"; :>> title = "Sprint 299 standup gate"; :>> createdAt = "2026-08-15"; :>> createdBy = "claudeOpus5"; :>> method = VerificationMethod::inspect; :>> procedureText = "Approach: record the acceptances through a COMMAND rather than by editing three decision files, because the acceptance event is exactly the kind of fact the write API exists to keep uniform — and discovering there was no such command is itself the finding. Then apply the schema, then move every consumer, then populate the registry so the new field carries real data rather than sitting empty. No blockers."; }
    part arStandupGateR1 : TestResult { :>> id = "0d800268-0814-6268-9b3e-000000300268"; :>> outcome = VerdictKind::pass; :>> judgedAgainst = "a6b7123"; :>> judgedAt = "2026-08-15"; :>> judgedBy = "claudeOpus5"; }

    verification arImplementGate : Test { :>> id = "0d800269-0814-6269-9b3e-000000300269"; :>> title = "Sprint 299 implement gate"; :>> createdAt = "2026-08-15"; :>> createdBy = "claudeOpus5"; :>> method = VerificationMethod::test; :>> procedureText = "THE POLICY IS DECLARED, NOT COMPILED, and that distinction is the requirement rather than a preference: srDcAuthorityFromRegistry says the check is 'against the declared policy for that class'. A hardcoded rule cannot be seen by a project, tightened by it, or audited against its own actors. Three properties are load-bearing and each is tested: an EMPTY `roles` list admits an actor with no role, which is what keeps this forward-only — every actor enrolled before D0146 has none, and naming roles in a class starts constraining only from that point (issue068); an ABSENT contract falls back to human-only rather than to no policy, because a missing file must never silently disable an authority check (the issue090 lesson); and KIND is checked before ROLE, so an AI holding the right role still fails a human-only class. A stale message survived the change for one build — the guard still appended 'which is not a registered Person' to what was now a ROLE mismatch — and was corrected to name the actual gap."; }
    part arImplementGateR1 : TestResult { :>> id = "0d80026a-0814-626a-9b3e-00000030026a"; :>> outcome = VerdictKind::pass; :>> judgedAgainst = "a6b7123"; :>> judgedAt = "2026-08-15"; :>> judgedBy = "claudeOpus5"; }

    verification arReviewGate : Test { :>> id = "0d80026b-0814-626b-9b3e-00000030026b"; :>> title = "Sprint 299 review gate"; :>> createdAt = "2026-08-15"; :>> createdBy = "claudeOpus5"; :>> method = VerificationMethod::inspect; :>> procedureText = "Reviewed. The registry was POPULATED rather than left for later, and that is what makes the policy meaningful today: with `roles = [\"supervisor\"]` declared and wweatherholtz recorded as supervisor, the constraint is live and satisfied rather than declared and vacuous. Shipping the contract with empty role lists would have been safer and would have been theatre — a policy that constrains nothing looks exactly like a policy that works. The three panel critics are recorded as `reviewer`, which is the honest description of what they did and keeps `role` carrying information the `kind` field does not already give."; }
    part arReviewGateR1 : TestResult { :>> id = "0d80026c-0814-626c-9b3e-00000030026c"; :>> outcome = VerdictKind::pass; :>> judgedAgainst = "a6b7123"; :>> judgedAt = "2026-08-15"; :>> judgedBy = "claudeOpus5"; }

    verification arCloseOutGate : Test { :>> id = "0d80026d-0814-626d-9b3e-00000030026d"; :>> title = "Sprint 299 closeOut gate (autonomous, D0049)"; :>> createdAt = "2026-08-15"; :>> createdBy = "claudeOpus5"; :>> method = VerificationMethod::inspect; :>> procedureText = "Autonomous closeOut (D0049) — the CHANGE it applies is not autonomous: D0146, D0147 and D0148 all carry wweatherholtz's explicit sign-off, recorded through `keel accept` with their verbatim words. issue110 resolves. Doc-sync rides the commit: the three decision headers said 'PROPOSED — awaiting human sign-off' while their status field said accepted, which is dual truth in the one place it matters most. clippy clean; 141 lib tests; validate 322 clean; check-engine clean; validate_schema 15/15 kernel-side; 32 guards green. No gate bypassed."; }
    part arCloseOutGateR1 : TestResult { :>> id = "0d80026e-0814-626e-9b3e-00000030026e"; :>> outcome = VerdictKind::pass; :>> judgedAgainst = "a6b7123"; :>> judgedAt = "2026-08-15"; :>> judgedBy = "claudeOpus5"; }

    verification arRetroGate : Test { :>> id = "0d80026f-0814-626f-9b3e-00000030026f"; :>> title = "Sprint 299 retro gate (autonomous, D0049)"; :>> createdAt = "2026-08-15"; :>> createdBy = "claudeOpus5"; :>> method = VerificationMethod::analyze; :>> procedureText = "Autonomous retro (D0049) under D0131's retroTrack. WELL: (1) trying to RECORD the acceptance found that the single human gate had no CLI — the gap surfaced by doing the thing rather than by auditing for it, and building the command first (D0040) means the next acceptance is one call instead of three file edits; (2) the registry was populated so the declared policy constrains something real, rather than shipping empty lists that would look like a working control; (3) the empty-list-admits-no-role rule is TESTED, because it is the single property standing between this change and retro-failing every attestation in the repo's history. AVOIDABLE-ISSUE 1: a python replace against `declaration()` silently did not match — escaping again — and the function shipped without writing `role` at all. It BUILT clean, because `cargo build` does not compile tests; only running the tests would have caught it, and I caught it by reading the file the tool echoed back. That is the fourth silent-no-match this pass. NO NEW ITEM, reason stated: the remedy is already established and I keep not applying it — use Edit for source patches, never a python replace — and this instance adds the specific tell: a replace that reports success while the file is unchanged is indistinguishable from one that worked, so the check is to READ THE RESULT, not the exit status. AVOIDABLE-ISSUE 2: clippy's 100-line limit on `main` fired three times in one sprint as I added arms. Each fix was correct and the third finally extracted the 30-line usage block that should never have been inline. NO NEW ITEM: the lint is the control and it worked. Estimate 8 pts, delivered."; }
    part arRetroGateR1 : TestResult { :>> id = "0d800270-0814-6270-9b3e-000000300270"; :>> outcome = VerdictKind::pass; :>> judgedAgainst = "a6b7123"; :>> judgedAt = "2026-08-15"; :>> judgedBy = "claudeOpus5"; }
}
