// ProjectDeliveryS469 — Sprint 469: one git repository may hold several keel projects, and the four things git makes repo-scoped now know it. EXECUTE. 5 pts.
package ProjectDeliveryS469 {
    private import EngineElement::*;
    private import EngineWork::*;
    private import EngineVerification::*;
    private import EngineRelationships::*;

    #CharteredBy dependency from workspaceStory to d0234;

    part workspaceStory : Story {
        :>> id = "924860f0-878b-4ece-91f3-a7cc58487520";
        :>> title = "Sprint 469: the layout that worked, minus four things - two of which were already broken (5 pts)";
        :>> createdAt = "2026-08-26"; :>> createdBy = "claudeFable5"; :>> kind = WorkKind::code; :>> priority = WorkPriority::p0; :>> owner = "claudeFable5"; :>> estimatedPoints = 5;
    }

    action def DeliveryRunS469 {
        action storyWorkspace;
        verification storyWorkspaceDoD : Test { :>> id = "d1b483c2-5f28-47c9-98d0-d864373b5cd7"; :>> method = VerificationMethod::test; :>> procedureText = "DELIVERED: dcWorkspace (issue270), dcStagedFilesAreProjectScoped (issue271), dcKeystoneLockIsAboutChangeNotArrival (issue272) and dcValidateRefusesANonProject (issue269 - validate REFUSING a directory that is not a project, which is one of D0234's four changes and the reason a workspace-root hook can no longer gate nothing while reporting success), all under D0234. The author wants one repo for a handful of small short-term projects and said the layout will recur. I built the arrangement and RAN it rather than reasoning about it: three things already worked - root resolution walks up to .engine, drift is file-scoped per project, the write lock is per model root - and four broke. Decision numbering collides at d0001; the channel cannot tell two projects apart because its marker and GitHub lookup are repo-scoped; git allows ONE core.hooksPath so at most one project is gated, and validate at the parent reported a clean tree over zero files; and land gates one root while pushing the whole repo. A WORKSPACE is now a git repo holding one or more projects, DISCOVERED rather than declared, with keel projects to list them, keel gate --workspace as the commit gate the repo-root hook calls, sync and land gating every project before a push, validate REFUSING a non-project, and the channel qualifying an id as alpha/d0001 only when the repo holds several. THE TWO PRE-EXISTING DEFECTS WERE WORSE THAN THE FEATURE. Every project's guards saw every other project's staged files, because git diff --cached answers for the whole repository regardless of which subdirectory asks - a two-project workspace failed BOTH projects over a file belonging to neither. And a freshly scaffolded project COULD NOT MAKE ITS FIRST COMMIT: init stages every processes file and the keystone lock read that as a control being weakened, so the first thing any new user does failed and told them to record a Decision for a scaffold they had not written."; }
        // RAN: CORRECTED 2026-09-05 (issue283): the live two-project demonstration cited commits 96e680e and 98456c1 in scratch repositories since deleted, so those references did not resolve - a D0129 violation inside the receipt. The reproducible evidence for the same claims is the suite: land_gate.rs::land_refuses_to_push_a_workspace_carrying_a_broken_project (a two-project workspace, the broken project blocks and is named, the fixed one lands), init_smoke.rs::init_scaffolds_a_working_project (a fresh single-project init commits through its scaffolded gate) and no_green_over_nothing.rs (every model command refuses a workspace root). The installed-units.toml version bump 10 -> 12 that rode commit f356770 was adoption_check_can_fail exporting from the LIVE repository root instead of its fixture (issue339, fixed later) - not part of this sprint's work. Also recorded then: keel projects reports 2 in the workspace and 1 here; qualify() -> alpha/d0001 vs beta/d0001, d0231 unchanged; keel guard process-change -> PASS with the co-committed Decision found. cargo test --workspace -> 274+9+2+1+32; clippy 0 errors
        part storyWorkspaceDoDR1 : TestResult { :>> id = "897462ce-d075-4520-97bd-ae8adf033167"; :>> outcome = VerdictKind::pass; :>> judgedAgainst = "f3567704fe492cf91920a24d80e9970ea8abeb20"; :>> judgedAt = "2026-08-26"; :>> judgedBy = "claudeFable5"; }
    }

    verification workspaceRefineGate : Test { :>> id = "6d9977fc-8bce-4e02-bcc7-4c41e0ac0eb0"; :>> title = "Sprint 469 refine gate (DoR)"; :>> createdAt = "2026-08-26"; :>> createdBy = "claudeFable5"; :>> method = VerificationMethod::inspect; :>> procedureText = "DoR. Resolves issue270 as asked, plus issue271 and issue272 which the work uncovered. Scope: make the engine know the difference between a project and the repository holding it, in exactly the four places git forces the distinction. 5 points."; }
    part workspaceRefineGateR1 : TestResult { :>> id = "d393a6b3-d7ed-4904-b2cb-968ec2b4138d"; :>> outcome = VerdictKind::pass; :>> judgedAgainst = "f3567704fe492cf91920a24d80e9970ea8abeb20"; :>> judgedAt = "2026-08-26"; :>> judgedBy = "claudeFable5"; }
    verification workspaceStandupGate : Test { :>> id = "58f79969-bef3-4946-95c3-8031957efde5"; :>> title = "Sprint 469 standup gate"; :>> createdAt = "2026-08-26"; :>> createdBy = "claudeFable5"; :>> method = VerificationMethod::inspect; :>> procedureText = "Approach: BUILD the arrangement and run it before designing anything, because the question was empirical and my prior was wrong twice already this session. Gate every change on is_multi() so a single-project repo is untouched - a feature that alters existing repos is a migration, not an addition. Discover rather than declare, since a manifest is a second place to keep the list true. guards.rs, the hook template and the channel scripts are all keystone-locked, so D0234 co-commits as a SafetyChange. No blockers."; }
    part workspaceStandupGateR1 : TestResult { :>> id = "8b09f7b8-eae0-497b-84c2-e9b1bb23f813"; :>> outcome = VerdictKind::pass; :>> judgedAgainst = "f3567704fe492cf91920a24d80e9970ea8abeb20"; :>> judgedAt = "2026-08-26"; :>> judgedBy = "claudeFable5"; }
    verification workspaceImplementGate : Test { :>> id = "276a191e-bb32-4b93-b519-56469053d0ec"; :>> title = "Sprint 469 implement gate"; :>> createdAt = "2026-08-26"; :>> createdBy = "claudeFable5"; :>> method = VerificationMethod::test; :>> procedureText = "Verified LIVE against real two-project repos, not by reasoning. One repo-root hook gated a commit across BOTH projects and it landed; a broken project BLOCKED the commit while the report named the project it skipped; a fresh single-project first commit, which failed before, now succeeds through the scaffolded hook; the qualification rule returns alpha/d0001 versus beta/d0001 while leaving d0231 byte-identical; this repo still reports exactly one project and its guard output is unchanged. validate 521 + 52 guards ALL PASS + clippy 0 errors + 274 + 9 + 2 + 1 + 32 tests."; }
    // RAN: CORRECTED 2026-09-05 (issue283): the live two-project demonstration cited commits 96e680e and 98456c1 in scratch repositories since deleted, so those references did not resolve - a D0129 violation inside the receipt. The reproducible evidence for the same claims is the suite: land_gate.rs::land_refuses_to_push_a_workspace_carrying_a_broken_project (a two-project workspace, the broken project blocks and is named, the fixed one lands), init_smoke.rs::init_scaffolds_a_working_project (a fresh single-project init commits through its scaffolded gate) and no_green_over_nothing.rs (every model command refuses a workspace root). The installed-units.toml version bump 10 -> 12 that rode commit f356770 was adoption_check_can_fail exporting from the LIVE repository root instead of its fixture (issue339, fixed later) - not part of this sprint's work. Also recorded then: keel projects reports 2 in the workspace and 1 here; qualify() -> alpha/d0001 vs beta/d0001, d0231 unchanged; keel guard process-change -> PASS with the co-committed Decision found. cargo test --workspace -> 274+9+2+1+32; clippy 0 errors
    part workspaceImplementGateR1 : TestResult { :>> id = "19856a16-b6d9-431b-81b9-3acc2d1bcf35"; :>> outcome = VerdictKind::pass; :>> judgedAgainst = "f3567704fe492cf91920a24d80e9970ea8abeb20"; :>> judgedAt = "2026-08-26"; :>> judgedBy = "claudeFable5"; }
    verification workspaceReviewGate : Test { :>> id = "7988fbf0-5825-484c-97fc-981b16d77e57"; :>> title = "Sprint 469 review gate — three passes per D0172"; :>> createdAt = "2026-08-26"; :>> createdBy = "claudeFable5"; :>> method = VerificationMethod::inspect; :>> procedureText = "PASS 1, CLAIMS: every verdict came from running the arrangement - the collision, the vacuous validate, the cross-project guard failure and the blocked first commit were all observed, not predicted. PASS 2, BOUNDARY: (i) decision NUMBERS still collide in the model; only the channel ids are distinct, so two projects' d0001 remain ambiguous to anything that reads the model rather than the channel; (ii) the qualified channel form is verified against the rule and a stub, NOT against live GitHub, so its first real exercise will be someone's second project; (iii) a staged file belonging to no project is reported but covered by no project's gate - named, not solved; (iv) discovery is depth-bounded at three, so a project buried deeper is invisible; (v) the keystone lock now ignores ADDED locked files, and an added process CAN weaken by claiming a core guard - covered by audit-adherence's monotonicity, which is a different check in a different place. PASS 3, OWN DIFF: the gate caught my own regression inside a minute. Filtering staged files to modify-or-delete also hid the co-committed DECISION, because a new Decision file is an addition - so my first attempt at this commit was refused for lacking the very Decision sitting staged beside it. Two lists were needed. I would not have found that by reading. WHAT A REVIEWER SHOULD ATTACK: whether exempting ADDED locked files opens a real hole, given the residual leans entirely on audit-adherence."; }
    part workspaceReviewGateR1 : TestResult { :>> id = "ee9f29ec-1af2-4294-9f8d-e2a52cdfd1f5"; :>> outcome = VerdictKind::pass; :>> judgedAgainst = "f3567704fe492cf91920a24d80e9970ea8abeb20"; :>> judgedAt = "2026-08-26"; :>> judgedBy = "claudeFable5"; }
    verification workspaceCloseOutGate : Test { :>> id = "1d78789a-ac6d-4bea-ac4d-47be93208e05"; :>> title = "Sprint 469 closeOut gate (autonomous, D0049)"; :>> createdAt = "2026-08-26"; :>> createdBy = "claudeFable5"; :>> method = VerificationMethod::inspect; :>> procedureText = "Autonomous closeOut (D0049). issue270, issue271 and issue272 resolved. The author can put several small projects in one repo and get one gate, one push path, and unambiguous decisions - and every existing single-project repo is untouched. validate + 52 guards + check-engine + rules green at f356770."; }
    part workspaceCloseOutGateR1 : TestResult { :>> id = "f182a27a-4ed1-41f7-a650-fd7f19060b6c"; :>> outcome = VerdictKind::pass; :>> judgedAgainst = "f3567704fe492cf91920a24d80e9970ea8abeb20"; :>> judgedAt = "2026-08-26"; :>> judgedBy = "claudeFable5"; }
    verification workspaceRetroGate : Test { :>> id = "17b1a6bc-c67f-4538-a10f-e88f30433bad"; :>> title = "Sprint 469 retro gate (autonomous, D0049)"; :>> createdAt = "2026-08-26"; :>> createdBy = "claudeFable5"; :>> method = VerificationMethod::analyze; :>> procedureText = "Autonomous retro (D0049). AVOIDABLE-ISSUE SCAN under rcRecurrence: (1) THE FINDING, and it is the strongest evidence yet for the sprint-466 thesis: the two worst defects here had NOTHING to do with the feature. A fresh project could not make its first commit, and that has been true for every project ever scaffolded - found only because a workspace experiment made me commit a fresh scaffold. adoption-check runs validate, guard and check-engine but never a COMMIT, so the entire staged-file guard class sits outside it. That is a concrete, cheap extension and the highest-value one available. (2) Eighth consecutive finding that came from USING the thing. Inspection has now produced zero of the last eight. (3) The gate caught my own regression on the same file I was editing, within a minute - the first time this session a control I was actively modifying refused me for a correct reason. WELL: building the arrangement before designing it cost twenty minutes and turned a design question into four measured facts, two of which I would never have predicted. Estimate 5 pts, delivered 5."; }
    part workspaceRetroGateR1 : TestResult { :>> id = "f2bd21d8-0401-4323-a1d3-b2975a23b1c4"; :>> outcome = VerdictKind::pass; :>> judgedAgainst = "f3567704fe492cf91920a24d80e9970ea8abeb20"; :>> judgedAt = "2026-08-26"; :>> judgedBy = "claudeFable5"; }
}
