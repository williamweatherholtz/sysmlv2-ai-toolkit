// ProjectDeliveryS639 — Sprint 639: Sprint 639: CI has been red for six pushes (e902566..afd90d0) and two reports called it green. The citation check of guard cli-surface-declared reads only a tree holding the engine's Decision channel (dcCitationCheckHoldsWhereTheDecisionsLive, issue433, D0419), and keel land names the CI verdict of the base before every push (dcLandNamesTheCiVerdictOfTheBase, issue434, D0420). CHANGE: one enforced guard narrows its scope under a proposed #ProspectiveChange. 2 pts.. EXECUTE. 2 pts.
package ProjectDeliveryS639 {
    private import EngineElement::*;
    private import EngineWork::*;
    private import EngineVerification::*;
    private import EngineRelationships::*;

    #CharteredBy dependency from ciRedCorrectionStory to d0419;

    part ciRedCorrectionStory : Story {
        :>> id = "f8f6fc12-9863-442e-8e51-894aea88c8ba";
        :>> title = "Sprint 639: Sprint 639: CI has been red for six pushes (e902566..afd90d0) and two reports called it green. The citation check of guard cli-surface-declared reads only a tree holding the engine's Decision channel (dcCitationCheckHoldsWhereTheDecisionsLive, issue433, D0419), and keel land names the CI verdict of the base before every push (dcLandNamesTheCiVerdictOfTheBase, issue434, D0420). CHANGE: one enforced guard narrows its scope under a proposed #ProspectiveChange. 2 pts. (2 pts)";
        :>> createdAt = "2026-09-09"; :>> createdBy = "claudeOpus5"; :>> kind = WorkKind::code; :>> priority = WorkPriority::p0; :>> owner = "claudeOpus5"; :>> estimatedPoints = 2;
    }

    action def DeliveryRunS639 {
        action storyCiRedCorrection;
        verification storyCiRedCorrectionDoD : Test { :>> id = "27543df3-0772-4466-aa96-2afce6e719a4"; :>> method = VerificationMethod::test; :>> procedureText = "DELIVERED (dcCitationCheckHoldsWhereTheDecisionsLive resolves issue433; dcLandNamesTheCiVerdictOfTheBase resolves issue434): guards.rs cli_surface_declared applies the citation block only when decision_ids_present(root) contains d0271, with the comment naming issue433 and why keel-cli/Cargo.toml is not the predicate; unit test citations_are_read_only_where_the_engines_decisions_live probes the engine's facts in a temp root - no Decisions -> 0 citation violations, a 0271- file added -> at least 12 - and the_live_synopses_cite_only_live_decisions still holds. status.rs extracts ci_verdict(root, sha) -> (CiVerdict, line) from ci_section; sync.rs cmd_land calls name_ci_verdict_of_base after the held-items warning: one advisory line for origin/<branch>, a second when the base is FAILED, silent on a non-GitHub remote or an unresolved origin/<branch>, never a refusal. guards.md and CLAUDE.md name both rules. RAN on the tree before commit: cargo clippy --workspace --all-targets -D warnings clean; cargo test --release --test adoption_check_can_fail --test push_gate_is_withdrawn -> 4 passed 0 failed read from the log (the first run of the same command had 1 FAILED in the log while the wrapper exited 0 - the issue434 mechanism seen again, this time read from the log); the lib test above ok; keel validate / check-engine clean; keel guard 68 PASS exit 0. The CI verdict of the landing commit is read from gh run list --json conclusion after the push and stated in the milestone report as what that command returned."; }
        // RAN: cargo clippy --workspace --all-targets -D warnings clean; cargo test --release --test adoption_check_can_fail --test push_gate_is_withdrawn -> 4 passed 0 failed (read from tests639b.log); lib test citations_are_read_only_where_the_engines_decisions_live ok; keel validate / check-engine clean; keel guard 68 PASS exit 0; issue433/issue434 recorded; D0419 proposed, D0420 accepted
        part storyCiRedCorrectionDoDR1 : TestResult { :>> id = "cb3fd53f-5e27-4716-929a-42a3a378f0dd"; :>> outcome = VerdictKind::pass; :>> judgedAgainst = "afd90d0"; :>> judgedAt = "2026-09-09"; :>> judgedBy = "claudeOpus5"; }
    }

    verification ciRedCorrectionRefineGate : Test { :>> id = "b2cb0330-78c4-41b9-991a-c6cec2321a5d"; :>> title = "Sprint 639 refine gate (DoR)"; :>> createdAt = "2026-09-09"; :>> createdBy = "claudeOpus5"; :>> method = VerificationMethod::inspect; :>> procedureText = "Definition of Ready: issue433 is Critical and issue434 High, both recorded 2026-09-09 with resolvers whose DoDs name them; each DoD names the property, the DO and the VERIFY with a known-positive and a known-negative (D0388); no fork - the predicate is the fact the check depends on, and the land line is advisory by the six red pushes' own evidence (the fix must land on a red base); 2 points across two small code changes and two Decisions."; }
    // RAN: sprint 639 Refine: cargo clippy --workspace --all-targets -D warnings clean; cargo test --release --test adoption_check_can_fail --test push_gate_is_withdrawn -> 4 passed 0 failed (read from tests639b.log); lib test citations_are_read_only_where_the_engines_decisions_live ok; keel validate / check-engine clean; keel guard 68 PASS exit 0; issue433/issue434 recorded; D0419 proposed, D0420 accepted
    part ciRedCorrectionRefineGateR1 : TestResult { :>> id = "a25f7cab-ff22-4c38-ae9e-d658a2f5766f"; :>> outcome = VerdictKind::pass; :>> judgedAgainst = "afd90d0"; :>> judgedAt = "2026-09-09"; :>> judgedBy = "claudeOpus5"; }
    verification ciRedCorrectionStandupGate : Test { :>> id = "1f35c815-554a-417e-9b6e-2b56c61c0e67"; :>> title = "Sprint 639 standup gate"; :>> createdAt = "2026-09-09"; :>> createdBy = "claudeOpus5"; :>> method = VerificationMethod::inspect; :>> procedureText = "No blocker. One design point settled in the sprint: the first cut of the predicate was suite::is_self_build (keel-cli/Cargo.toml present), and push_gate_is_withdrawn stayed red under it because its fixture is shaped like the self-build and carries no Decisions - the property is about where the cited Decisions live, so the predicate became the presence of D0271, the Decision that authored the surface. record_claim's registry hash is also drifted and has been since sprint 418; not this sprint's, left as arch drift reports it."; }
    // RAN: sprint 639 Standup: cargo clippy --workspace --all-targets -D warnings clean; cargo test --release --test adoption_check_can_fail --test push_gate_is_withdrawn -> 4 passed 0 failed (read from tests639b.log); lib test citations_are_read_only_where_the_engines_decisions_live ok; keel validate / check-engine clean; keel guard 68 PASS exit 0; issue433/issue434 recorded; D0419 proposed, D0420 accepted
    part ciRedCorrectionStandupGateR1 : TestResult { :>> id = "cc370bdb-c26e-4ebd-b913-d60c6ea5ab49"; :>> outcome = VerdictKind::pass; :>> judgedAgainst = "afd90d0"; :>> judgedAt = "2026-09-09"; :>> judgedBy = "claudeOpus5"; }
    verification ciRedCorrectionImplementGate : Test { :>> id = "a49bb224-c849-42b6-8774-5aa23680f1b4"; :>> title = "Sprint 639 implement gate"; :>> createdAt = "2026-09-09"; :>> createdBy = "claudeOpus5"; :>> method = VerificationMethod::test; :>> procedureText = "guards.rs: the citation block wrapped in `if present.contains('d0271')` with the issue433 comment; new unit test beside the live one. status.rs: CiVerdict enum, ci_verdict, ci_section as caller (textpatch land639.py). sync.rs: name_ci_verdict_of_base + its call. code-registry ceLandGate codeHash refreshed to the live 2927d6474c7e5404. Records: dcCitationCheckHoldsWhereTheDecisionsLive, dcLandNamesTheCiVerdictOfTheBase (add-task --dod-from), issue433 Critical, issue434 High (record issue --description-from), D0419 --process-change (proposed, D0337), D0420 (auto-accepted, non-fork). Doc-sync: guards.md cli-surface-declared row, CLAUDE.md integration paragraph."; }
    // RAN: sprint 639 Implement: cargo clippy --workspace --all-targets -D warnings clean; cargo test --release --test adoption_check_can_fail --test push_gate_is_withdrawn -> 4 passed 0 failed (read from tests639b.log); lib test citations_are_read_only_where_the_engines_decisions_live ok; keel validate / check-engine clean; keel guard 68 PASS exit 0; issue433/issue434 recorded; D0419 proposed, D0420 accepted
    part ciRedCorrectionImplementGateR1 : TestResult { :>> id = "cdb22e59-d105-4091-9d54-d0d936ae87cc"; :>> outcome = VerdictKind::pass; :>> judgedAgainst = "afd90d0"; :>> judgedAt = "2026-09-09"; :>> judgedBy = "claudeOpus5"; }
    verification ciRedCorrectionReviewGate : Test { :>> id = "1eca5181-a2ad-4ba2-b07d-ac1725e93226"; :>> title = "Sprint 639 review gate — three passes per D0172"; :>> createdAt = "2026-09-09"; :>> createdBy = "claudeOpus5"; :>> method = VerificationMethod::inspect; :>> procedureText = "Three passes per D0172: (1) the predicate is read from the tree the guard runs in, not from the binary's identity - a fixture, a scaffold and a downstream project all lack d0271 and all get the surface checks and no citation check; (2) the land line is the binary's reading of the conclusion field, shared with keel status through one function, and cannot refuse; (3) the two integration tests that found issue433 are green in the log, and the log is what was read - the wrapper's exit code for the first run was 0 over a FAILED line, which is the issue434 mechanism observed on this very sprint's evidence."; }
    // RAN: sprint 639 Review: cargo clippy --workspace --all-targets -D warnings clean; cargo test --release --test adoption_check_can_fail --test push_gate_is_withdrawn -> 4 passed 0 failed (read from tests639b.log); lib test citations_are_read_only_where_the_engines_decisions_live ok; keel validate / check-engine clean; keel guard 68 PASS exit 0; issue433/issue434 recorded; D0419 proposed, D0420 accepted
    part ciRedCorrectionReviewGateR1 : TestResult { :>> id = "30556c01-9790-4027-9b46-ea6a9fffb8cc"; :>> outcome = VerdictKind::pass; :>> judgedAgainst = "afd90d0"; :>> judgedAt = "2026-09-09"; :>> judgedBy = "claudeOpus5"; }
    verification ciRedCorrectionCloseOutGate : Test { :>> id = "5a455731-445e-4ebf-a97d-0364f2fe1cf1"; :>> title = "Sprint 639 closeOut gate (autonomous, D0049)"; :>> createdAt = "2026-09-09"; :>> createdBy = "claudeOpus5"; :>> method = VerificationMethod::inspect; :>> procedureText = "keel validate . clean, keel check-engine . clean, keel guard 68 PASS exit 0; both backlog DoDs stamped at the pre-commit tree; issue433 and issue434 recorded and triaged through their resolvers; D0419 proposed for the human's word; D0420 accepted at record time."; }
    // RAN: sprint 639 CloseOut: cargo clippy --workspace --all-targets -D warnings clean; cargo test --release --test adoption_check_can_fail --test push_gate_is_withdrawn -> 4 passed 0 failed (read from tests639b.log); lib test citations_are_read_only_where_the_engines_decisions_live ok; keel validate / check-engine clean; keel guard 68 PASS exit 0; issue433/issue434 recorded; D0419 proposed, D0420 accepted
    part ciRedCorrectionCloseOutGateR1 : TestResult { :>> id = "a42ee9cc-0aa1-4c18-82f6-a2f6273215e2"; :>> outcome = VerdictKind::pass; :>> judgedAgainst = "afd90d0"; :>> judgedAt = "2026-09-09"; :>> judgedBy = "claudeOpus5"; }
    verification ciRedCorrectionRetroGate : Test { :>> id = "ac587582-1697-4840-86dd-309e25dbabec"; :>> title = "Sprint 639 retro gate (autonomous, D0049)"; :>> createdAt = "2026-09-09"; :>> createdBy = "claudeOpus5"; :>> method = VerificationMethod::analyze; :>> procedureText = "Avoidable-issue scan: issue433 was a check whose scope was never stated - D0412's consequences named one limit and not the tree the check reads; the guard that would have caught it (a scaffold gate in CI) did catch it, six times, and the reports read a wrapper's exit code instead of the run - issue434. Both are the same shape: a number stood in for a verdict. The control for the second is now in the binary (dcLandNamesTheCiVerdictOfTheBase); what it cannot control is the sentence in the transcript (D0151), which the milestone report states. No new item beyond issue433 and issue434."; }
    // RAN: sprint 639 Retro: cargo clippy --workspace --all-targets -D warnings clean; cargo test --release --test adoption_check_can_fail --test push_gate_is_withdrawn -> 4 passed 0 failed (read from tests639b.log); lib test citations_are_read_only_where_the_engines_decisions_live ok; keel validate / check-engine clean; keel guard 68 PASS exit 0; issue433/issue434 recorded; D0419 proposed, D0420 accepted
    part ciRedCorrectionRetroGateR1 : TestResult { :>> id = "62fc9641-2e93-4fa3-8398-e0f8bd7e7cef"; :>> outcome = VerdictKind::pass; :>> judgedAgainst = "afd90d0"; :>> judgedAt = "2026-09-09"; :>> judgedBy = "claudeOpus5"; }
}
