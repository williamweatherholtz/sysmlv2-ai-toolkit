// ProjectDeliveryS535 — Sprint 535: keel status names the hook hosts and the kill switch. EXECUTE. 1 pt.
package ProjectDeliveryS535 {
    private import EngineElement::*;
    private import EngineWork::*;
    private import EngineVerification::*;
    private import EngineRelationships::*;

    #CharteredBy dependency from hookHostsStory to d0296;

    part hookHostsStory : Story {
        :>> id = "448f0f42-a65f-4fa1-9a24-0094a4f8089a";
        :>> title = "Sprint 535: a hooks section in keel status - which hosts carry the set, whether anything silences them, coloured; the control structure shows both renderings and the launch pin (1 pt)";
        :>> createdAt = "2026-09-03"; :>> createdBy = "claudeOpus5"; :>> kind = WorkKind::code; :>> priority = WorkPriority::p0; :>> owner = "claudeOpus5"; :>> estimatedPoints = 1;
    }

    action def DeliveryRunS535 {
        action storyHookHosts;
        verification storyHookHostsDoD : Test { :>> id = "58177799-9159-4658-85a9-a04b091e6999"; :>> method = VerificationMethod::test; :>> procedureText = "DELIVERED BACKLOG ITEMS: dcStatusReportsHookHosts - the last of D0296's four. DONE: hooks_section in status.rs - kill switch in either repo-scope file is ATTENTION naming file and key; repo settings declared or DRIFTED; plugin rendering present or not; launch pin written or not; managed settings present or not (read, never parsed); no host at all is ATTENTION, never a clean zero; the status tags are coloured per D0287 (OK green, ATTENTION red, UNKNOWN yellow) with padding on the bare text. control-structure lists the plugin rendering as a second source on every event it carries and adds a launchPin action when the pin file exists. VERIFY: two unit tests; live status on this repo (OK) and on the poisoned fixture (ATTENTION)."; }
        // RAN: cargo test --release 463/0; clippy 0; keel status . hooks OK 2 hosts; keel status <poisoned fixture> hooks ATTENTION; show control-structure source = .claude/settings.json; .engine/claude-plugin/hooks/hooks.json; the in-repo plant of settings.local.json was blocked and restored by this session's config-change hook (hooks.jsonl block line) before status read it
        part storyHookHostsDoDR1 : TestResult { :>> id = "0a24748d-dd79-44af-9db7-e6d594e2b6a6"; :>> outcome = VerdictKind::pass; :>> judgedAgainst = "129bbc8"; :>> judgedAt = "2026-09-03"; :>> judgedBy = "claudeOpus5"; }
    }

    verification hookHostsRefineGate : Test { :>> id = "f1d0daca-d37e-4522-8958-041bc1a8cf80"; :>> title = "Sprint 535 refine gate (DoR)"; :>> createdAt = "2026-09-03"; :>> createdBy = "claudeOpus5"; :>> method = VerificationMethod::inspect; :>> procedureText = "READY from D0296 run 5: a hook dead at launch cannot say so, therefore the saying belongs to a command the human runs; status.rs's own rule - nothing-to-report and cannot-tell never look alike - gave the section its shape."; }
    verification hookHostsStandupGate : Test { :>> id = "e0644dc2-9c47-4a72-857e-b2152ef08040"; :>> title = "Sprint 535 standup gate"; :>> createdAt = "2026-09-03"; :>> createdBy = "claudeOpus5"; :>> method = VerificationMethod::inspect; :>> procedureText = "ONE CHOICE: the kill switch decides the verdict before any host is counted - four healthy hosts with the key set is ATTENTION, because a plain claude launch runs none of them. Second: managed settings are reported by presence only; parsing an admin's policy to second-guess it is not keel's business."; }
    verification hookHostsImplementGate : Test { :>> id = "46b425dc-063d-45a0-8da3-e6af117ffdfe"; :>> title = "Sprint 535 implement gate"; :>> createdAt = "2026-09-03"; :>> createdBy = "claudeOpus5"; :>> method = VerificationMethod::test; :>> procedureText = "RAN: script through the Write tool; four clippy items (const fn, map_or, single-pattern match, indexing). The live plant in THIS repository did not show ATTENTION - the session's own ConfigChange hook had already blocked and restored the file; the fixture with no watching session showed it. The control catching its author is the better receipt."; }
    verification hookHostsReviewGate : Test { :>> id = "9c9fa340-0372-4609-96c3-ebcc80222c26"; :>> title = "Sprint 535 review gate — three passes per D0172"; :>> createdAt = "2026-09-03"; :>> createdBy = "claudeOpus5"; :>> method = VerificationMethod::inspect; :>> procedureText = "THREE PASSES. (1) CAN IT LIE CLEAN: no host is ATTENTION; a non-JSON settings file is ATTENTION; UNKNOWN is not used here because every read is local and either succeeds or is a finding. (2) IS COLOUR SAFE FOR COLUMNS: the padding is applied to the bare tag before painting, so piped output and coloured output align identically. (3) WHAT STATUS CANNOT SEE: a user-scope kill switch in ~/.claude - the user's own file, out of D0296's scope, and the launch pin overrides it anyway."; }
    verification hookHostsCloseOutGate : Test { :>> id = "2e617d04-f510-4f90-bd99-7fcadee67b87"; :>> title = "Sprint 535 closeOut gate (autonomous, D0049)"; :>> createdAt = "2026-09-03"; :>> createdBy = "claudeOpus5"; :>> method = VerificationMethod::inspect; :>> procedureText = "CLOSED. D0296's four chartered items are all landed with receipts; CLAUDE.md's status line names the new base."; }
    verification hookHostsRetroGate : Test { :>> id = "4ce32eba-1678-479c-bbf3-93481d932321"; :>> title = "Sprint 535 retro gate (autonomous, D0049)"; :>> createdAt = "2026-09-03"; :>> createdBy = "claudeOpus5"; :>> method = VerificationMethod::analyze; :>> procedureText = "no new item - already tracked: the D0296 programme is complete - issue365 closed, the six-event set in two renderings, refuse-and-restore, the launch pin, and this readout; what remains open is d0296's stated limit (a plain claude launch by the human, and hosts on a filesystem the agent's shell reaches), covered detectively by this section and by the fire-ledger work in dcExternalFactGate. The one lesson worth a line: the first live receipt for this sprint failed because the control from two sprints ago fired first - when a control cannot be observed misbehaving in its own project, test it in a fixture no session watches."; }
}
