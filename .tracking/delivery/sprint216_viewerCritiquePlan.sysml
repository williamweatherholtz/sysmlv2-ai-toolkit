// ProjectDeliveryS216 — Sprint 216: viewerCritiquePlan — the deterministic critique-iteration plan
// (/api/critique-plan): the ordered AXIS (a slice) + per-element type/context/agent-target + lens, that a
// viewer drives the agent bridge over. The keel-side core of viewerIterativeCritique (N-15, the human's
// core goal). API 1.1.0 -> 1.2.0. viewerIterativeCritique stays OPEN (orchestration = viewer app). EXECUTE. 2 pt.
package ProjectDeliveryS216 {
    private import EngineElement::*;
    private import EngineWork::*;
    private import EngineVerification::*;
    private import EngineRequirements::*;
    private import EngineRelationships::*;

    #CharteredBy dependency from viewerCritiquePlanStory to d0114;

    part viewerCritiquePlanStory : Story {
        :>> id = "63940516-2c7d-4e8f-c216-51627384c001";
        :>> title = "Sprint 216: viewerCritiquePlan (2 pt) - /api/critique-plan (axis + context + lens); deterministic core of N-15";
        :>> createdAt = "2026-07-14"; :>> createdBy = "wweatherholtz"; :>> kind = WorkKind::code; :>> priority = WorkPriority::p2; :>> owner = "claudeOpus"; :>> estimatedPoints = 2;
    }

    action def DeliveryRunS216 {
        action storyViewerCritiquePlan;
        verification storyViewerCritiquePlanDoD : Test { :>> id = "63940516-2c7d-4e8f-c216-51627384c002"; :>> method = VerificationMethod::test; :>> procedureText = "The DETERMINISTIC core of viewerIterativeCritique (N-15 / srViewerIterativeCritique). view.rs critique_plan_json: given a seed (slice via configurable_slice), emit the ordered AXIS with, per element, its type + local context (element_neighbourhood names) + the agent-bridge target (/api/agent/stream?action=critique&target=<el>) + the chosen lens. serve.rs: GET /api/critique-plan?seed&depth&edges&dir&lens (default lens best-practice), added to the committed contract; API 1.1.0 -> 1.2.0. This is the deterministic, testable keel-side piece; the viewer app (shape B) drives the existing agent bridge once per axis item + records via apply-review — so it directly powers UC-14 (process + downstream, best-practice) + UC-15 (requirement + downstream, sufficiency). SCOPE HONESTY: viewerIterativeCritique stays OPEN — the running-orchestration loop + the 'N critiques recorded' demonstration are the viewer app + a follow-on; keel now provides ALL the pieces (plan + agent bridge + apply-review). Contract test extended (must advertise /api/slice + /api/critique-plan). VERIFIED LIVE: /api/version 1.2.0/17; /api/critique-plan seed=nViewerSeparation depth=2 -> 8-element axis, each with type/context/target. VERIFY: clippy --workspace --all-targets clean; cargo test (85) green; keel validate + guard + check-engine green."; }
        part storyViewerCritiquePlanDoDR1 : TestResult { :>> id = "63940516-2c7d-4e8f-c216-51627384c003"; :>> outcome = VerdictKind::pass; :>> judgedAgainst = "990a84f"; :>> judgedAt = "2026-07-14"; :>> judgedBy = "claudeOpus"; }
    }

    verification vcpRefineGate : Test { :>> id = "63940516-2c7d-4e8f-c216-51627384c004"; :>> title = "Sprint 216 refine gate (DoR)"; :>> createdAt = "2026-07-14"; :>> createdBy = "claudeOpus"; :>> method = VerificationMethod::inspect; :>> procedureText = "DoR: N-15 is the human's core goal; the deterministic keel-side piece is the iteration plan over a slice (axis+context+target+lens); the run/record loop is the viewer app driving the existing agent bridge. estimatedPoints=2. #CharteredBy d0114. DoR met."; }
    part vcpRefineGateR1 : TestResult { :>> id = "63940516-2c7d-4e8f-c216-51627384c005"; :>> outcome = VerdictKind::pass; :>> judgedAgainst = "990a84f"; :>> judgedAt = "2026-07-14"; :>> judgedBy = "claudeOpus"; }
    verification vcpStandupGate : Test { :>> id = "63940516-2c7d-4e8f-c216-51627384c006"; :>> title = "Sprint 216 standup gate"; :>> createdAt = "2026-07-14"; :>> createdBy = "claudeOpus"; :>> method = VerificationMethod::inspect; :>> procedureText = "Approach: critique_plan_json (reuse configurable_slice + element_neighbourhood) -> /api/critique-plan; contract + version bump; extend the contract test. No blockers."; }
    part vcpStandupGateR1 : TestResult { :>> id = "63940516-2c7d-4e8f-c216-51627384c007"; :>> outcome = VerdictKind::pass; :>> judgedAgainst = "990a84f"; :>> judgedAt = "2026-07-14"; :>> judgedBy = "claudeOpus"; }
    verification vcpImplementGate : Test { :>> id = "63940516-2c7d-4e8f-c216-51627384c008"; :>> title = "Sprint 216 implement gate"; :>> createdAt = "2026-07-14"; :>> createdBy = "claudeOpus"; :>> method = VerificationMethod::test; :>> procedureText = "/api/critique-plan live (8-element axis w/ type/context/target); API 1.2.0/17; contract test extended + green. clippy --workspace --all-targets clean; cargo test (85) green; keel validate + guard + check-engine green."; }
    part vcpImplementGateR1 : TestResult { :>> id = "63940516-2c7d-4e8f-c216-51627384c009"; :>> outcome = VerdictKind::pass; :>> judgedAgainst = "990a84f"; :>> judgedAt = "2026-07-14"; :>> judgedBy = "claudeOpus"; }
    verification vcpReviewGate : Test { :>> id = "63940516-2c7d-4e8f-c216-51627384c00a"; :>> title = "Sprint 216 review gate"; :>> createdAt = "2026-07-14"; :>> createdBy = "claudeOpus"; :>> method = VerificationMethod::inspect; :>> procedureText = "Reviewed. The right shape-B division: keel emits the DETERMINISTIC plan (axis + per-element context + the exact agent-bridge URL + lens) — testable, no LLM in the loop — and the viewer app does the non-deterministic orchestration (loop the agent bridge, record via apply-review). This directly realizes the human's #1/#2 (UC-14/UC-15) by composing existing pieces (slice + agent-critique + apply-review) rather than a new engine. Honestly left viewerIterativeCritique OPEN (the run/record demo is downstream). Clean."; }
    part vcpReviewGateR1 : TestResult { :>> id = "63940516-2c7d-4e8f-c216-51627384c00b"; :>> outcome = VerdictKind::pass; :>> judgedAgainst = "990a84f"; :>> judgedAt = "2026-07-14"; :>> judgedBy = "claudeOpus"; }
    verification vcpCloseOutGate : Test { :>> id = "63940516-2c7d-4e8f-c216-51627384c00c"; :>> title = "Sprint 216 closeOut gate (autonomous, D0049)"; :>> createdAt = "2026-07-14"; :>> createdBy = "claudeOpus"; :>> method = VerificationMethod::inspect; :>> procedureText = "Autonomous closeOut (D0049): DoD pass; /api/critique-plan live (API 1.2.0) — the deterministic core of the human's core goal (N-15). keel now has every piece for iterative critique (plan + agent bridge + apply-review). clippy + cargo test + keel validate + guard + check-engine green. Self-evidencing (D0051). NEXT: viewerInProgramEdit (N-16, reuse apply-review) then the viewer app orchestration (separate project) closes viewerIterativeCritique."; }
    part vcpCloseOutGateR1 : TestResult { :>> id = "63940516-2c7d-4e8f-c216-51627384c00d"; :>> outcome = VerdictKind::pass; :>> judgedAgainst = "990a84f"; :>> judgedAt = "2026-07-14"; :>> judgedBy = "claudeOpus"; }
    verification vcpRetroGate : Test { :>> id = "63940516-2c7d-4e8f-c216-51627384c00e"; :>> title = "Sprint 216 retro gate (autonomous, D0049)"; :>> createdAt = "2026-07-14"; :>> createdBy = "claudeOpus"; :>> method = VerificationMethod::analyze; :>> procedureText = "Autonomous retro (D0049). WELL: reached the human's core goal (iterative critique) by SEPARATING the deterministic part (the plan — keel, testable) from the non-deterministic part (the agent loop — viewer app), which is exactly the shape-B discipline; and it composes existing keel machinery (slice + agent-critique + apply-review) into the human's #1/#2 flows rather than building a new engine. Kept the backlog item honestly OPEN pending the orchestration demo. AVOIDABLE-ISSUE SCAN: none new (authoritative clippy first, habitual). LESSON: emit deterministic plans from the engine; keep the AI loop in the consuming app — testable + reproducible where it can be. Estimate 2 pt held. NEXT: viewerInProgramEdit (N-16)."; }
    part vcpRetroGateR1 : TestResult { :>> id = "63940516-2c7d-4e8f-c216-51627384c00f"; :>> outcome = VerdictKind::pass; :>> judgedAgainst = "990a84f"; :>> judgedAt = "2026-07-14"; :>> judgedBy = "claudeOpus"; }
}
