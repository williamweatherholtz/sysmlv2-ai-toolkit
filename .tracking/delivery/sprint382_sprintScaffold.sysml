// ProjectDeliveryS382 — Sprint 382: `keel new sprint` — the ceremony record is scaffolded by the
// engine, and THIS record is its first output. EXECUTE. 5 pts.
package ProjectDeliveryS382 {
    private import EngineElement::*;
    private import EngineWork::*;
    private import EngineVerification::*;
    private import EngineRelationships::*;

    #CharteredBy dependency from sprintScaffoldStory to d0173;

    part sprintScaffoldStory : Story {
        :>> id = "599edadd-5184-4d61-a8fe-983208b27ee4";
        :>> title = "Sprint 382: keel new sprint - the ceremony record scaffolds itself, unfillable-unpassable (5 pts)";
        :>> createdAt = "2026-08-21"; :>> createdBy = "claudeOpus5"; :>> kind = WorkKind::code; :>> priority = WorkPriority::p0; :>> owner = "claudeOpus5"; :>> estimatedPoints = 5;
    }

    action def DeliveryRunS382 {
        action storySprintScaffold;
        verification storySprintScaffoldDoD : Test { :>> id = "b0bfd391-200b-4d62-9fb9-eebdb358f06b"; :>> method = VerificationMethod::test; :>> procedureText = "DELIVERED BACKLOG ITEMS: dcSprintScaffold. Their st013 applied to its largest consumer: every sprint record hand-authored ~14 uuids plus the 7-gate skeleton. DONE AS SPECIFIED: `keel new sprint <N> <slug> --charter <decision> [--points P]` writes the Story + DoD + six ceremony gates with EVERY id minted (checked in tests against guard 38's own predicate, unique per scaffold), createdAt from the real clock (the one authoring field where the clock IS the truth - judgment dates stay refused-not-defaulted), createdBy/owner from the bound actor and REFUSED when absent, the charter verified to be a DECLARED Decision before the edge is written, sprint-number reuse and overwrite refused, and every judgment-bearing text set to the FILL-ME token. THE TOKEN IS ENFORCED: guard 40 (scaffold-placeholder, hard, in GUARD_NAMES with dispatch, doc row, and the CLAUDE.md counts) plus the fast per-edit tier reject any model file carrying it - an unfilled skeleton cannot pass a gate or be committed, by construction. NO TestResults are generated; results are appended when a gate is actually judged. Exercised LIVE on a copy tree (scaffold, fast-gate rejection exit 1, number-reuse/bad-slug/unknown-charter/missing-charter/unbound-actor refusals) and on THIS tree: this record is the command's first real output, held red by its own guard until these texts were filled. 215 unit tests; clippy 0; 40 guards ALL PASS."; }
        part storySprintScaffoldDoDR1 : TestResult { :>> id = "258e0a24-bb85-43e7-a471-1a5b7a59cf89"; :>> outcome = VerdictKind::pass; :>> judgedAgainst = "74ecefb"; :>> judgedAt = "2026-08-21"; :>> judgedBy = "claudeOpus5"; }
    }

    verification sprintScaffoldRefineGate : Test { :>> id = "f6f2e1bc-10ff-4e7b-903f-e01235c531c0"; :>> title = "Sprint 382 refine gate (DoR)"; :>> createdAt = "2026-08-21"; :>> createdBy = "claudeOpus5"; :>> method = VerificationMethod::inspect; :>> procedureText = "DoR. Second item on the ready frontier (D0052 auto-follow), fully specified by dcSprintScaffoldDoD: command shape, provenance refusals, the placeholder-rejection contract, and the exact tests are all named in the item. estimatedPoints=5."; }
    part sprintScaffoldRefineGateR1 : TestResult { :>> id = "20c21215-ae31-4b05-885b-6233b4b39e7f"; :>> outcome = VerdictKind::pass; :>> judgedAgainst = "74ecefb"; :>> judgedAt = "2026-08-21"; :>> judgedBy = "claudeOpus5"; }
    verification sprintScaffoldStandupGate : Test { :>> id = "7dd175a5-c269-4520-a174-7d4a8f817904"; :>> title = "Sprint 382 standup gate"; :>> createdAt = "2026-08-21"; :>> createdBy = "claudeOpus5"; :>> method = VerificationMethod::inspect; :>> procedureText = "Approach: the scaffold REFUSES TO GUESS - ids minted, author from the bound actor or refused, charter verified against declared Decisions, judgment texts left as a token that guard 40 and the fast tier reject. Structure mirrors the ceremony guard's own recognition rules (verification names ending {G}Gate over GATE_ORDER), so a scaffolded record is judgeable by append-gate-result with no adaptation. No blockers."; }
    part sprintScaffoldStandupGateR1 : TestResult { :>> id = "2fee5b52-15d5-4e1d-a1ac-5ab72b69ba0c"; :>> outcome = VerdictKind::pass; :>> judgedAgainst = "74ecefb"; :>> judgedAt = "2026-08-21"; :>> judgedBy = "claudeOpus5"; }
    verification sprintScaffoldImplementGate : Test { :>> id = "280a8cb1-27df-4fd4-be65-40541216245e"; :>> title = "Sprint 382 implement gate"; :>> createdAt = "2026-08-21"; :>> createdBy = "claudeOpus5"; :>> method = VerificationMethod::test; :>> procedureText = "Every claim from a run: scaffold on a COPY tree, fast gate exit 1 on the unfilled skeleton, all five refusal branches executed against the built binary; then the DOGFOOD - this very record scaffolded on the real tree and held red by its own guard until filled. One measurement error caught and corrected mid-sprint: a pipeline exit code read tail's status, not the gate's - re-measured without the pipe (exit 1 confirmed), the verify-the-right-surface rule applied to shell plumbing. Clippy found one real panic path (args slicing) - replaced with get()."; }
    part sprintScaffoldImplementGateR1 : TestResult { :>> id = "6d244abf-dd15-41de-956b-6830f39dde71"; :>> outcome = VerdictKind::pass; :>> judgedAgainst = "74ecefb"; :>> judgedAt = "2026-08-21"; :>> judgedBy = "claudeOpus5"; }
    verification sprintScaffoldReviewGate : Test { :>> id = "d27565b0-e4e5-4f61-bf65-8812e460cf13"; :>> title = "Sprint 382 review gate — three passes per D0172"; :>> createdAt = "2026-08-21"; :>> createdBy = "claudeOpus5"; :>> method = VerificationMethod::inspect; :>> procedureText = "PASS 1, CLAIMS vs computed/emitted: 215 tests, clippy 0, 40 guards ALL PASS over the real tree with this scaffold present-and-filled; the scaffolded file's ids counted and shape-checked from the FILE, not the generator. PASS 2, BOUNDARY: slug validation refuses non-camelCase (it becomes item names and a filename); sprint-number reuse refuses on PREFIX match so sprint999_a and sprint999_b cannot coexist; the charter check reads declared Decisions rather than trusting the caller. PASS 3, OWN DIFF: the generated gate titles were checked against the ceremony guard's GATE_ORDER suffix matching BEFORE writing the generator - the class of drift where a generator and its consumer disagree, prevented rather than found. WHAT A REVIEWER SHOULD ATTACK: chrono_date is a hand-rolled civil-from-days conversion; verified against the live date today, and wrong-by-one exactly at a UTC date boundary would stamp createdAt one day off - an authoring date, not evidence, so the blast radius is cosmetic."; }
    part sprintScaffoldReviewGateR1 : TestResult { :>> id = "4ad7a4ed-5dce-4d92-9530-363634441f24"; :>> outcome = VerdictKind::pass; :>> judgedAgainst = "74ecefb"; :>> judgedAt = "2026-08-21"; :>> judgedBy = "claudeOpus5"; }
    verification sprintScaffoldCloseOutGate : Test { :>> id = "bdc75093-521c-4f6a-a037-f5d469ca6b2e"; :>> title = "Sprint 382 closeOut gate (autonomous, D0049)"; :>> createdAt = "2026-08-21"; :>> createdBy = "claudeOpus5"; :>> method = VerificationMethod::inspect; :>> procedureText = "Autonomous closeOut (D0049). dcSprintScaffold's DoD result flipped to pass at the judging HEAD; guard 40 registered everywhere a guard lives (GUARD_NAMES, dispatch, guards.md row, CLAUDE.md counts, fast tier); the command advertised in the help catalogue under its coverage test. validate clean; 40 guards ALL PASS; 215 tests; clippy 0."; }
    part sprintScaffoldCloseOutGateR1 : TestResult { :>> id = "7f7d8f88-10a8-48b2-a237-64f3d15ca38c"; :>> outcome = VerdictKind::pass; :>> judgedAgainst = "74ecefb"; :>> judgedAt = "2026-08-21"; :>> judgedBy = "claudeOpus5"; }
    verification sprintScaffoldRetroGate : Test { :>> id = "5f451d48-4c04-457a-b9ab-20d19c745a76"; :>> title = "Sprint 382 retro gate (autonomous, D0049)"; :>> createdAt = "2026-08-21"; :>> createdBy = "claudeOpus5"; :>> method = VerificationMethod::analyze; :>> procedureText = "Autonomous retro (D0049). AVOIDABLE-ISSUE SCAN under rcRecurrence: (1) the pipeline-exit misread is the verify-the-wrong-surface family in miniature - caught in-sprint by re-measuring, no record needed beyond this line unless it recurs; (2) grep -c breaking a && chain on zero matches recurred (a KNOWN trap from the session's own history) - occurrence two of shell-plumbing-misreads THIS SESSION, so per D0172 it now carries its preventing change: measurements that gate a claim run UNPIPED, stated here as the rule the implement gate already applied. WELL: (1) the deliverable judged itself - the record you are reading was held red by the guard it ships, which is the cheapest end-to-end test a control can get; (2) the generator was written AGAINST the ceremony guard's recognition rules read first, not adapted to them after a failure; (3) hand-authoring of sprint identity ends here - sprint 381 minted its ids by pipe, this one by scaffold, and the next one starts from `keel new sprint`. Estimate 5 pts, delivered."; }
    part sprintScaffoldRetroGateR1 : TestResult { :>> id = "6da88729-1a36-4ae7-a616-a6661e4ae1f4"; :>> outcome = VerdictKind::pass; :>> judgedAgainst = "74ecefb"; :>> judgedAt = "2026-08-21"; :>> judgedBy = "claudeOpus5"; }
}
