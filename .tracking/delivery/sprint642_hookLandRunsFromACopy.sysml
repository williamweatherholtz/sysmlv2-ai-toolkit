// ProjectDeliveryS642 — Sprint 642: Sprint 642: the post-commit hook copies the self-build's binary to target/release/keel-land(.exe) and runs keel land from the copy, so an armed touched-test run (D0421) can relink keel.exe (dcHookLandRunsFromACopy, issue436, D0422). CHANGE on the enforcement surface: a hook edit with its co-committed #ProspectiveChange Decision, proposed under D0337. 1 pt.. EXECUTE. 1 pts.
package ProjectDeliveryS642 {
    private import EngineElement::*;
    private import EngineWork::*;
    private import EngineVerification::*;
    private import EngineRelationships::*;

    #CharteredBy dependency from hookLandRunsFromACopyStory to d0422;

    part hookLandRunsFromACopyStory : Story {
        :>> id = "dd96256d-f44a-4a3e-9bf1-a8410361d5f1";
        :>> title = "Sprint 642: Sprint 642: the post-commit hook copies the self-build's binary to target/release/keel-land(.exe) and runs keel land from the copy, so an armed touched-test run (D0421) can relink keel.exe (dcHookLandRunsFromACopy, issue436, D0422). CHANGE on the enforcement surface: a hook edit with its co-committed #ProspectiveChange Decision, proposed under D0337. 1 pt. (1 pts)";
        :>> createdAt = "2026-09-10"; :>> createdBy = "claudeOpus5"; :>> kind = WorkKind::code; :>> priority = WorkPriority::p0; :>> owner = "claudeOpus5"; :>> estimatedPoints = 1;
    }

    action def DeliveryRunS642 {
        action storyHookLandRunsFromACopy;
        verification storyHookLandRunsFromACopyDoD : Test { :>> id = "931e2151-9b59-40f4-98cb-f8b3b41b3d3e"; :>> method = VerificationMethod::test; :>> procedureText = "DELIVERED (dcHookLandRunsFromACopy resolves issue436): .githooks/post-commit, when KEEL resolves to ./target/release/keel or ./target/release/keel.exe, copies it to the keel-land image with cp -f and runs land from the copy; a keel on PATH is untouched; a failed copy falls back to the original. VERIFY: the shell expansion probed on both shapes and the PATH case before the edit (known positives ./target/release/keel.exe -> keel-land.exe and keel -> keel-land, known negative: PATH keel untouched); sh -n parses the hook; the commit that carries this change shows in its own commit log the hook's land running with no own-image line and the push landed; suite::image_collides read at suite.rs:171-181 admits a release/keel-land image (first component is neither keel.exe nor deps). CLAUDE.md names the copy beside the own-image rule; D0422 recorded --process-change."; }
        // RAN: shell expansion probed: ./target/release/keel.exe -> keel-land.exe, keel -> keel-land, PATH keel untouched; sh -n .githooks/post-commit ok; suite.rs:171-181 image_collides admits release/keel-land; keel validate/check-engine clean; keel guard --no-receipt ALL PASS exit 0
        part storyHookLandRunsFromACopyDoDR1 : TestResult { :>> id = "e25b7510-ad80-4d5e-bddd-767717fcaee3"; :>> outcome = VerdictKind::pass; :>> judgedAgainst = "cab7cac"; :>> judgedAt = "2026-09-09"; :>> judgedBy = "claudeOpus5"; }
    }

    verification hookLandRunsFromACopyRefineGate : Test { :>> id = "8b96c0bf-84ec-4abc-977a-f3af19bc1ed3"; :>> title = "Sprint 642 refine gate (DoR)"; :>> createdAt = "2026-09-10"; :>> createdBy = "claudeOpus5"; :>> method = VerificationMethod::inspect; :>> procedureText = "Definition of Ready: issue436 is High, recorded 2026-09-09 with this resolver naming it; the change is a five-line case block with a fallback; its Decision is one clause; 1 point."; }
    // RAN: shell expansion probed: ./target/release/keel.exe -> keel-land.exe, keel -> keel-land, PATH keel untouched; sh -n .githooks/post-commit ok; suite.rs:171-181 image_collides admits release/keel-land; keel validate/check-engine clean; keel guard --no-receipt ALL PASS exit 0
    part hookLandRunsFromACopyRefineGateR1 : TestResult { :>> id = "ccf8fd90-253c-4dcd-9898-cc5185bc535d"; :>> outcome = VerdictKind::pass; :>> judgedAgainst = "cab7cac"; :>> judgedAt = "2026-09-09"; :>> judgedBy = "claudeOpus5"; }
    verification hookLandRunsFromACopyStandupGate : Test { :>> id = "f781e38e-9609-4fd2-8137-94c3e6d67ed7"; :>> title = "Sprint 642 standup gate"; :>> createdAt = "2026-09-10"; :>> createdBy = "claudeOpus5"; :>> method = VerificationMethod::inspect; :>> procedureText = "No blocker. The hook is not templated in the binary (grep KEEL_POST_COMMIT_ACTIVE in keel-cli/src finds nothing), so the file is the one home and no generator or drift guard is involved."; }
    // RAN: shell expansion probed: ./target/release/keel.exe -> keel-land.exe, keel -> keel-land, PATH keel untouched; sh -n .githooks/post-commit ok; suite.rs:171-181 image_collides admits release/keel-land; keel validate/check-engine clean; keel guard --no-receipt ALL PASS exit 0
    part hookLandRunsFromACopyStandupGateR1 : TestResult { :>> id = "84ca1353-4da7-4c70-926f-7e4d8ebd01a2"; :>> outcome = VerdictKind::pass; :>> judgedAgainst = "cab7cac"; :>> judgedAt = "2026-09-09"; :>> judgedBy = "claudeOpus5"; }
    verification hookLandRunsFromACopyImplementGate : Test { :>> id = "4ea338b6-9dfc-4b35-bd53-a7495f11efe6"; :>> title = "Sprint 642 implement gate"; :>> createdAt = "2026-09-10"; :>> createdBy = "claudeOpus5"; :>> method = VerificationMethod::test; :>> procedureText = ".githooks/post-commit case block (hook642.py); D0422 --process-change; CLAUDE.md own-image paragraph (docsync642.py)."; }
    // RAN: shell expansion probed: ./target/release/keel.exe -> keel-land.exe, keel -> keel-land, PATH keel untouched; sh -n .githooks/post-commit ok; suite.rs:171-181 image_collides admits release/keel-land; keel validate/check-engine clean; keel guard --no-receipt ALL PASS exit 0
    part hookLandRunsFromACopyImplementGateR1 : TestResult { :>> id = "54697962-26f4-4fc3-bfcf-0fbb6276f79f"; :>> outcome = VerdictKind::pass; :>> judgedAgainst = "cab7cac"; :>> judgedAt = "2026-09-09"; :>> judgedBy = "claudeOpus5"; }
    verification hookLandRunsFromACopyReviewGate : Test { :>> id = "0054a133-3f22-473d-aeb5-6db3129c2536"; :>> title = "Sprint 642 review gate — three passes per D0172"; :>> createdAt = "2026-09-10"; :>> createdBy = "claudeOpus5"; :>> method = VerificationMethod::inspect; :>> procedureText = "Three passes per D0172: (1) the copy is made only for the self-build's own target path, so a downstream project's hook behaviour is byte-identical; (2) the fallback keeps the old behaviour and the old refusal message when the copy fails - nothing new can be silent; (3) the change rides with its Decision in one commit, as D0209 clause 2 requires, and stays proposed."; }
    // RAN: shell expansion probed: ./target/release/keel.exe -> keel-land.exe, keel -> keel-land, PATH keel untouched; sh -n .githooks/post-commit ok; suite.rs:171-181 image_collides admits release/keel-land; keel validate/check-engine clean; keel guard --no-receipt ALL PASS exit 0
    part hookLandRunsFromACopyReviewGateR1 : TestResult { :>> id = "f0884bda-3bad-4081-9756-a7e614dfa7f8"; :>> outcome = VerdictKind::pass; :>> judgedAgainst = "cab7cac"; :>> judgedAt = "2026-09-09"; :>> judgedBy = "claudeOpus5"; }
    verification hookLandRunsFromACopyCloseOutGate : Test { :>> id = "cb844dd1-2dfb-4015-a7c7-b29aa306b8ad"; :>> title = "Sprint 642 closeOut gate (autonomous, D0049)"; :>> createdAt = "2026-09-10"; :>> createdBy = "claudeOpus5"; :>> method = VerificationMethod::inspect; :>> procedureText = "validate clean, check-engine clean, guard ALL PASS exit 0; dcHookLandRunsFromACopy stamped at the pre-commit tree; issue436 triaged through it; D0422 proposed, to be accepted with or before D0421."; }
    // RAN: shell expansion probed: ./target/release/keel.exe -> keel-land.exe, keel -> keel-land, PATH keel untouched; sh -n .githooks/post-commit ok; suite.rs:171-181 image_collides admits release/keel-land; keel validate/check-engine clean; keel guard --no-receipt ALL PASS exit 0
    part hookLandRunsFromACopyCloseOutGateR1 : TestResult { :>> id = "dc02844d-b961-42ea-bebb-5664d2a8bc71"; :>> outcome = VerdictKind::pass; :>> judgedAgainst = "cab7cac"; :>> judgedAt = "2026-09-09"; :>> judgedBy = "claudeOpus5"; }
    verification hookLandRunsFromACopyRetroGate : Test { :>> id = "b43d278c-557f-4590-b4ff-603108d452d4"; :>> title = "Sprint 642 retro gate (autonomous, D0049)"; :>> createdAt = "2026-09-10"; :>> createdBy = "claudeOpus5"; :>> method = VerificationMethod::analyze; :>> procedureText = "Avoidable-issue scan: issue436 was visible from the design of D0421 - the run relinks the image, the hook runs from the image - and was not seen until the wrong refusal fired. The general question, does the home of a new control run the control, belongs to the CHANGE route's review pass; it is one line in the review of any Decision that adds a run to a path a hook drives. No new item."; }
    // RAN: shell expansion probed: ./target/release/keel.exe -> keel-land.exe, keel -> keel-land, PATH keel untouched; sh -n .githooks/post-commit ok; suite.rs:171-181 image_collides admits release/keel-land; keel validate/check-engine clean; keel guard --no-receipt ALL PASS exit 0
    part hookLandRunsFromACopyRetroGateR1 : TestResult { :>> id = "bc5bc6ae-795e-4b9a-b3e2-11f6d35bb035"; :>> outcome = VerdictKind::pass; :>> judgedAgainst = "cab7cac"; :>> judgedAt = "2026-09-09"; :>> judgedBy = "claudeOpus5"; }
}
