// ProjectDeliveryS645 — Sprint 645: Sprint 645: the guard that sat behind the one sprint 644 cut (issue441). verification-trace at 4.3 s was arithmetic - 6 432 procedures each walking 15 770 items for its latest result - and, once attributed, the priority guard's remaining term was the orient indexer parsing .tracking a second time in the same process. Both readers now share one parsed tree per file through the corpus. 3 pts.. EXECUTE. 3 pts.
package ProjectDeliveryS645 {
    private import EngineElement::*;
    private import EngineWork::*;
    private import EngineVerification::*;
    private import EngineRelationships::*;

    #CharteredBy dependency from verificationTraceCutStory to d0414;

    part verificationTraceCutStory : Story {
        :>> id = "ea6a2d49-ac5d-4f69-b75b-9c6cc4affb32";
        :>> title = "Sprint 645: Sprint 645: the guard that sat behind the one sprint 644 cut (issue441). verification-trace at 4.3 s was arithmetic - 6 432 procedures each walking 15 770 items for its latest result - and, once attributed, the priority guard's remaining term was the orient indexer parsing .tracking a second time in the same process. Both readers now share one parsed tree per file through the corpus. 3 pts. (3 pts)";
        :>> createdAt = "2026-09-10"; :>> createdBy = "claudeOpus5"; :>> kind = WorkKind::code; :>> priority = WorkPriority::p0; :>> owner = "claudeOpus5"; :>> estimatedPoints = 3;
    }

    action def DeliveryRunS645 {
        action storyVerificationTraceCut;
        verification storyVerificationTraceCutDoD : Test { :>> id = "cdedc601-9b79-4d98-b1b1-4df668af15db"; :>> method = VerificationMethod::test; :>> procedureText = "DELIVERED: dcVerificationTraceIsAttributedAndCut resolves issue441 - latest_results builds the verification-to-latest-result index in one pass and untraced_links / thin_attestation_list read it with the outgoing edges grouped by source; untraced_verification_links is attributed by phase (verification-trace:model/phases/scan); corpus::parsed caches the Package per file under the (len, mtime) key the text cache uses, and Model::build_uncached and indexer::extract both read it. VERIFY: KEEL_PERF=1 keel guard --no-receipt names acceptance-binds-to-text as the critical path on three consecutive runs (3211, 2972, 3198 ms) with verification-trace at 1572-1741 ms and frontier:extract 226-385 ms (from 1293-1361 ms), set wall clock 5326, 5073, 5463 ms (from 5940); sorted full guard output identical to the pre-change baseline across 112 lines; lib 453 passed including the new corpus parsed-cache test; orient_bdd and no_green_over_nothing pass; clippy clean."; }
        // RAN: KEEL_PERF=1 keel guard --no-receipt . x3: critical path acceptance-binds-to-text 3211/2972/3198 ms, verification-trace 1572-1741 ms, frontier:extract 226-385 ms; sorted guard output diff vs pre-change baseline: identical (112 lines); cargo test --release -p keel-cli --lib: 453 passed; orient_bdd 2 passed; no_green_over_nothing 2 passed; cargo clippy --workspace --all-targets -D warnings: clean
        part storyVerificationTraceCutDoDR1 : TestResult { :>> id = "63d3f979-fdc9-41cd-a58e-be11f1eb8f85"; :>> outcome = VerdictKind::pass; :>> judgedAgainst = "7fad273"; :>> judgedAt = "2026-09-09T22:40:00-06:00"; :>> judgedBy = "claudeOpus5"; }
    }

    verification verificationTraceCutRefineGate : Test { :>> id = "11852199-4f49-4b0b-8414-f830b462c2d7"; :>> title = "Sprint 645 refine gate (DoR)"; :>> createdAt = "2026-09-10"; :>> createdBy = "claudeOpus5"; :>> method = VerificationMethod::inspect; :>> procedureText = "Definition of Ready: issue441 Medium, recorded 2026-09-09 with resolver dcVerificationTraceIsAttributedAndCut ranked at the frontier head after sprint 644 and read back; the change is bounded to staleness.rs (one new fn), critique.rs (two call sites, three phases), corpus.rs (the parse cache), one call site each in view/mod.rs and indexer.rs; 3 points because the cache touches every model build."; }
    // RAN: sprint 645 Refine: see the gate's procedureText; guard/validate/check-engine green on the pre-commit tree
    part verificationTraceCutRefineGateR1 : TestResult { :>> id = "4327303c-1f21-4e13-b4fc-765bb630fdc0"; :>> outcome = VerdictKind::pass; :>> judgedAgainst = "7fad273"; :>> judgedAt = "2026-09-09T22:40:00-06:00"; :>> judgedBy = "claudeOpus5"; }
    verification verificationTraceCutStandupGate : Test { :>> id = "c97e12bb-0a0d-4b67-99c3-53483e9f1583"; :>> title = "Sprint 645 standup gate"; :>> createdAt = "2026-09-10"; :>> createdBy = "claudeOpus5"; :>> method = VerificationMethod::inspect; :>> procedureText = "No blocker. One false lead: the first indexer hypothesis was the file reopen, and switching it to corpus::read_to_string left frontier:extract at 1.3 s - the term was the second tokenize and parse, not the open. One refusal: corpus.rs sat CRLF in the working tree against its eol=lf attribute and textpatch refused the anchor; the file was normalised to what git commits before patching."; }
    // RAN: sprint 645 Standup: see the gate's procedureText; guard/validate/check-engine green on the pre-commit tree
    part verificationTraceCutStandupGateR1 : TestResult { :>> id = "31a9dea0-82d3-4f13-bab5-2bf89c31e69a"; :>> outcome = VerdictKind::pass; :>> judgedAgainst = "7fad273"; :>> judgedAt = "2026-09-09T22:40:00-06:00"; :>> judgedBy = "claudeOpus5"; }
    verification verificationTraceCutImplementGate : Test { :>> id = "5c86980c-07b3-404c-b9b6-57d4c3f966c0"; :>> title = "Sprint 645 implement gate"; :>> createdAt = "2026-09-10"; :>> createdBy = "claudeOpus5"; :>> method = VerificationMethod::test; :>> procedureText = "vt645b.py (latest_results index in staleness.rs; thin_attestation_list and untraced_links read it, untraced_links groups edges by source), vt645a.py (perf phases on untraced_verification_links), idx645.py (indexer reads through the corpus), ast645.py (corpus::parsed with ParseFailure, PARSE_HITS counter, Model::build_uncached and indexer::extract switched, the corpus test), a fixture fix for the test's package syntax, and the dead parse/tokenize import dropped from view/mod.rs."; }
    // RAN: sprint 645 Implement: see the gate's procedureText; guard/validate/check-engine green on the pre-commit tree
    part verificationTraceCutImplementGateR1 : TestResult { :>> id = "95ec2f6a-f914-4c51-b1ae-b938a0644354"; :>> outcome = VerdictKind::pass; :>> judgedAgainst = "7fad273"; :>> judgedAt = "2026-09-09T22:40:00-06:00"; :>> judgedBy = "claudeOpus5"; }
    verification verificationTraceCutReviewGate : Test { :>> id = "d18734c3-4479-4dde-94da-87d6da6318f1"; :>> title = "Sprint 645 review gate — three passes per D0172"; :>> createdAt = "2026-09-10"; :>> createdBy = "claudeOpus5"; :>> method = VerificationMethod::inspect; :>> procedureText = "Three passes per D0172: (1) the index is exact by construction - a result name splits uniquely as <v>R<maximal trailing digits>, so every item contributes to exactly one verification and the map holds what latest_result returns for each key; the whole guard output was diffed sorted against the pre-change capture and is identical; (2) the parse cache is keyed and windowed exactly as the text cache (same (len, mtime), same 2 s racy window), a failure is never stored, and the test exercises hit, rewrite, broken file and removed file; (3) the remaining terms are named, not cut: acceptance-binds-to-text now bounds the set at 3.0-3.2 s, priority-inversion follows at 2.9-3.1 s, and git spawns sum to 9.4-11 s of thread time across 38 calls under load."; }
    // RAN: sprint 645 Review: see the gate's procedureText; guard/validate/check-engine green on the pre-commit tree
    part verificationTraceCutReviewGateR1 : TestResult { :>> id = "33dd3cb0-1981-4c95-b34b-3f218224f3fb"; :>> outcome = VerdictKind::pass; :>> judgedAgainst = "7fad273"; :>> judgedAt = "2026-09-09T22:40:00-06:00"; :>> judgedBy = "claudeOpus5"; }
    verification verificationTraceCutCloseOutGate : Test { :>> id = "14f3156b-43dc-4d87-bf4a-e59e84e28b34"; :>> title = "Sprint 645 closeOut gate (autonomous, D0049)"; :>> createdAt = "2026-09-10"; :>> createdBy = "claudeOpus5"; :>> method = VerificationMethod::inspect; :>> procedureText = "validate clean, check-engine clean, guard ALL PASS exit 0, sync-claude --check clean; resolver and story stamped at the pre-commit tree 7fad273; issue441 triaged through the resolver; keel-serve.exe refreshed from the new build."; }
    // RAN: sprint 645 CloseOut: see the gate's procedureText; guard/validate/check-engine green on the pre-commit tree
    part verificationTraceCutCloseOutGateR1 : TestResult { :>> id = "b6d26b10-e854-4825-a5a8-9a49c611e7c4"; :>> outcome = VerdictKind::pass; :>> judgedAgainst = "7fad273"; :>> judgedAt = "2026-09-09T22:40:00-06:00"; :>> judgedBy = "claudeOpus5"; }
    verification verificationTraceCutRetroGate : Test { :>> id = "d4615aaa-1e50-45a3-9b9f-211bbdaa4e21"; :>> title = "Sprint 645 retro gate (autonomous, D0049)"; :>> createdAt = "2026-09-10"; :>> createdBy = "claudeOpus5"; :>> method = VerificationMethod::analyze; :>> procedureText = "Avoidable-issue scan: sprint 644's retro folded two threshold candidates into this item - the git-facts file size and the guard critical path - and this sprint found neither is an indicator yet, so no threshold can be declared: indicator-triggers.toml keys an existing indicator and the indicators lens has no latency or cache-size measure. Attribution came first, as the retro said; the indicator is the next step and is recorded as its own tracked item (issue442, resolver dcHookLatencyIsAnIndicator) rather than folded again, because a fold that lands twice in a row is how a measured number stays unowned."; }
    // RAN: sprint 645 Retro: see the gate's procedureText; guard/validate/check-engine green on the pre-commit tree
    part verificationTraceCutRetroGateR1 : TestResult { :>> id = "8510b653-a695-454b-8b18-20d61b199b1b"; :>> outcome = VerdictKind::pass; :>> judgedAgainst = "7fad273"; :>> judgedAt = "2026-09-09T22:40:00-06:00"; :>> judgedBy = "claudeOpus5"; }
}
