// ProjectDeliveryS578 — Sprint 578: one binary probe for every gating surface - the hooks find the pin's own cache, and each says which binary gated. EXECUTE. 3 pts.
package ProjectDeliveryS578 {
    private import EngineElement::*;
    private import EngineWork::*;
    private import EngineVerification::*;
    private import EngineRelationships::*;

    #CharteredBy dependency from oneProbeStory to d0343;

    part oneProbeStory : Story {
        :>> id = "40475f87-c116-4e54-9bb4-1e120f16e48a";
        :>> title = "Sprint 578: one binary probe for every gating surface - the hooks find the pin's own cache, and each says which binary gated (3 pts)";
        :>> createdAt = "2026-09-06"; :>> createdBy = "claudeOpus5"; :>> kind = WorkKind::code; :>> priority = WorkPriority::p0; :>> owner = "claudeOpus5"; :>> estimatedPoints = 3;
    }

    action def DeliveryRunS578 {
        action storyOneProbe;
        verification storyOneProbeDoD : Test { :>> id = "c7ae2ded-5d94-42e0-88e0-7b59856e1d37"; :>> method = VerificationMethod::test; :>> procedureText = "DELIVERED BACKLOG ITEMS: dcOneBinaryResolutionForEverySurface (D0343 proposed, safety-change - waits for the human under D0337; resolves issue378, GH#55). DONE: claude_surface::pin_probe_sh is the one POSIX-sh probe - KEEL_BIN, .keel/bin/keel(.exe), the pin's cache .keel/bin/<engine pin>/<asset> read from engine-version.toml, then PATH; precommit_hook() renders the scaffolded hook from it and every generated Claude hook embeds the same text, held equal by test; the pre-commit hook prints the binary it gated with and its version line; every hook fire records bin and build in the fire-ledger and keel status shows the last fire. VERIFIED: the order test holds the hook and all Claude hook commands to the shared text; the probe run through sh against a directory whose only binary is .keel/bin/9.9.9/keel-linux-x86_64 with PATH=/usr/bin:/bin returns that path; a live keel init scaffold with a planted .keel/bin/0.3.1/keel-windows-x86_64.exe and PATH=/usr/bin (no keel) ran its pre-commit hook against the planted binary and printed via ./.keel/bin/0.3.1/keel-windows-x86_64.exe; a live hook fire in this repository landed a ledger line with bin and build 0fd3173+dirty and keel status read it back."; }
        // RAN: dcOneBinaryResolutionForEverySurface DoD pass on suite578 544/0; the implement section names each run
        part storyOneProbeDoDR1 : TestResult { :>> id = "956ebea0-5839-4700-b101-46cd4c3b5e63"; :>> outcome = VerdictKind::pass; :>> judgedAgainst = "0fd3173d5f34677db321c262d3fbcbe466fc07c6"; :>> judgedAt = "2026-09-06"; :>> judgedBy = "claudeOpus5"; }
    }

    verification oneProbeRefineGate : Test { :>> id = "ca012e74-770a-4e1b-b09f-8e7edc9876c3"; :>> title = "Sprint 578 refine gate (DoR)"; :>> createdAt = "2026-09-06"; :>> createdBy = "claudeOpus5"; :>> method = VerificationMethod::inspect; :>> procedureText = "READY: D0316 had held the ORDER equal by test and both surfaces still probed a path nothing writes; the design question was whether to call keelw (downloads on a miss - a network reach inside a commit hook), teach the hooks the cache layout, or drop PATH (breaks this self-build and every contributor without a pin). The second, with PATH kept and made loud."; }
    verification oneProbeStandupGate : Test { :>> id = "d57c4210-8efa-4ec2-85f7-b175cdd79bdf"; :>> title = "Sprint 578 standup gate"; :>> createdAt = "2026-09-06"; :>> createdBy = "claudeOpus5"; :>> method = VerificationMethod::inspect; :>> procedureText = "A LIST OF STEPS IS NOT A PROBE: the shell text is. Two texts maintained apart agreed on a file that does not exist; now there is one text and two embeddings."; }
    verification oneProbeImplementGate : Test { :>> id = "8ba36cd8-13bc-4eeb-9d77-9d5970209f6e"; :>> title = "Sprint 578 implement gate"; :>> createdAt = "2026-09-06"; :>> createdBy = "claudeOpus5"; :>> method = VerificationMethod::test; :>> procedureText = "RAN: cargo test --lib claude_surface 11/11 incl. the_probe_resolves_the_pins_own_cache_before_path (first run failed on PATH= having no head/sed - the test now uses /usr/bin:/bin); clippy -D warnings clean; keel sync-claude regenerated settings.json and the plugin hooks.json; sync-claude --check clean; the live scaffold and ledger checks above; full suite in suite578.txt."; }
    verification oneProbeReviewGate : Test { :>> id = "0784e296-0c7e-498f-9ca5-d5c16ce40d85"; :>> title = "Sprint 578 review gate — three passes per D0172"; :>> createdAt = "2026-09-06"; :>> createdBy = "claudeOpus5"; :>> method = VerificationMethod::inspect; :>> procedureText = "THREE PASSES. (1) CAN THE TWO SURFACES DRIFT AGAIN: the hook test asserts the git hook CONTAINS pin_probe_sh('.') verbatim and every Claude command probes in RESOLUTION_ORDER. (2) IS THE FALLBACK LOUD: the hook echoes the resolved path and version before gating; the Claude hooks record bin and build per fire. (3) DOES THIS REPOSITORY STILL GATE: it has no pin cache; the probe falls through to PATH as before and the ledger names the build."; }
    verification oneProbeCloseOutGate : Test { :>> id = "4376f5ad-c066-475c-817f-6802a5cb61d8"; :>> title = "Sprint 578 closeOut gate (autonomous, D0049)"; :>> createdAt = "2026-09-06"; :>> createdBy = "claudeOpus5"; :>> method = VerificationMethod::inspect; :>> procedureText = "CLOSED. issue378 resolves on this pass; D0343 is on the human's queue with D0340."; }
    verification oneProbeRetroGate : Test { :>> id = "14a78b49-e0b5-4b82-8d96-396617527838"; :>> title = "Sprint 578 retro gate (autonomous, D0049)"; :>> createdAt = "2026-09-06"; :>> createdBy = "claudeOpus5"; :>> method = VerificationMethod::analyze; :>> procedureText = "no new item - already tracked: issue379 (dcSeededCacheIsVerified, done this day) is the other half - what the cache holds; this is who reads it. The lesson: hold the TEXT equal, not a description of it - D0316's order test passed while the two probes disagreed on the path."; }
}
