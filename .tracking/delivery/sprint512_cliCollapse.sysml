// ProjectDeliveryS512 — Sprint 512: 35 lens verbs become one router, and the old names are gone.
// EXECUTE. 5 pts.
package ProjectDeliveryS512 {
    private import EngineElement::*;
    private import EngineWork::*;
    private import EngineVerification::*;
    private import EngineRelationships::*;

    #CharteredBy dependency from cliCollapseStory to d0273;

    part cliCollapseStory : Story {
        :>> id = "5a1b7c26-8d34-4e09-b7f2-6103d84925ce";
        :>> title = "Sprint 512: the lens family collapses to keel show <lens>, no alias window (5 pts)";
        :>> createdAt = "2026-09-01"; :>> createdBy = "claudeOpus5"; :>> kind = WorkKind::code; :>> priority = WorkPriority::p0; :>> owner = "claudeOpus5"; :>> estimatedPoints = 5;
    }

    action def DeliveryRunS512 {
        action storyCliCollapse;
        verification storyCliCollapseDoD : Test { :>> id = "6b2c8d37-9e45-4f10-c803-72149e5036df"; :>> method = VerificationMethod::test; :>> procedureText = "DELIVERED BACKLOG ITEMS: dcCliSurfaceConsolidation (resolves issue321, and issue330 via the D0067 transform) and dcTestsDoNotWriteTheLiveTree (resolves issue339, found while landing this). Step 4 of 5 in the D0275 plan, and the change the first three exist to make safe. DONE: 35 read-only lens verbs route through one `keel show <lens>`; the old spellings are REMOVED, not aliased, which is the human's choice made against my recommendation; 141 call sites rewritten across 57 files in the SAME commit so no tree ever exists in which a skill names a command the binary lacks. VERIFY, and byte-equality is the criterion that matters because a consolidation that changes an answer is a rewrite wearing a rename's clothes: 31 of 31 comparable lenses byte-identical against outputs captured from the pre-collapse binary. The one that differed was `hardening`, and the diff WAS the change - it counts dispatched commands, 100 to 66. MISSED CRITERION, recorded rather than redefined: D0273's consequences say the visible verb count falls BELOW 25. It is 66. Collapsing the lens family alone does not reach that; the gate, record and audit families were never measured or argued, and 25 was my own overreach in the Decision text."; }
        // RAN: 31/31 byte-identical vs the pre-collapse binary; capability_refusal_bites 5/5; workspace suite 463 passed / 0 failed across 36 binaries; clippy clean; 56 guards pass
        part storyCliCollapseDoDR1 : TestResult { :>> id = "7c3d9e48-0f56-4021-d914-83250f6147e0"; :>> outcome = VerdictKind::pass; :>> judgedAgainst = "cf985ec"; :>> judgedAt = "2026-09-01"; :>> judgedBy = "claudeOpus5"; }
    }

    verification cliCollapseRefineGate : Test { :>> id = "8d4e0f59-1067-4132-ea25-94361a725801"; :>> title = "Sprint 512 refine gate (DoR)"; :>> createdAt = "2026-09-01"; :>> createdBy = "claudeOpus5"; :>> method = VerificationMethod::inspect; :>> procedureText = "READY only because the three prior steps landed. A clean break needs a project to be ABLE to migrate (issue324, step 1) and needs the break to be DETECTABLE downstream by name rather than silent (D0252 clause A, step 2). Both shipped first, deliberately and in that order. The baseline capture is the other readiness fact: byte-equality can only be measured against outputs taken BEFORE the old verbs are removed, so those 34 captures were taken as the first act of this sprint and nothing was deleted until they existed."; }
    verification cliCollapseStandupGate : Test { :>> id = "9e5f1060-2178-4243-fb36-a5472b836912"; :>> title = "Sprint 512 standup gate"; :>> createdAt = "2026-09-01"; :>> createdBy = "claudeOpus5"; :>> method = VerificationMethod::inspect; :>> procedureText = "THE SPRAWL WAS NOT ONLY IN THE CLI, which is the finding that shaped the work. Four separate surfaces each parsed command names their own way and each broke differently: the dispatch itself; guards.rs's PRIVATE VIEW_SUBCOMMANDS list, a second hand-maintained inventory whose own comment recorded a past failure ('never added here, so the first viewpoint naming it failed'); the console's view binder in serve.rs; and that console's coverage test. The console case was the dangerous one - it bound on the renderer's first token, so after the collapse all 35 lenses shared the key `show` and the console would have served the WRONG view rather than refusing, which is worse than the 'no computed view is bound' it replaced. Only a unit test caught it."; }
    verification cliCollapseImplementGate : Test { :>> id = "0f601171-3289-4354-0c47-b6583c947a23"; :>> title = "Sprint 512 implement gate"; :>> createdAt = "2026-09-01"; :>> createdBy = "claudeOpus5"; :>> method = VerificationMethod::test; :>> procedureText = "RAN: 34 lens outputs captured from the pre-collapse binary, then compared after - 31 byte-identical, 1 explained (hardening's own count), 2 skipped as subcommand FAMILIES rather than single lenses (arch, knowledge). cargo test --release --no-fail-fast -> 463 passed, 0 failed across 36 binaries. clippy clean. keel validate 582 clean. All 56 guards pass. THE REMAINING BREAKAGE WAS ALL CALL SITES IN MY OWN TESTS, which is the clean break behaving exactly as designed on the one codebase I can see: capability_refusal_bites' fixtures used `keel orphans` and expected `show` to be missing - both inverted by the collapse; federation F3 invoked `keel business`; and no_green_over_nothing asserted D0241 through bare verbs. That last fix is worth more than a green tick - it now proves the workspace-root refusal holds THROUGH the router, and a router resolving its own root before delegating would answer green over nothing for every lens at once."; }
    verification cliCollapseReviewGate : Test { :>> id = "1a712282-439a-4465-1d58-c7694da58b34"; :>> title = "Sprint 512 review gate — three passes per D0172"; :>> createdAt = "2026-09-01"; :>> createdBy = "claudeOpus5"; :>> method = VerificationMethod::inspect; :>> procedureText = "THREE PASSES. (1) DID THE CONSOLIDATION CHANGE ANY ANSWER: no, and it is asserted rather than assumed - every arm was MOVED VERBATIM into the router, the calls untouched, and 31 of 31 comparable lenses are byte-identical against the pre-collapse binary. (2) DID I EDIT ANYTHING I HAD NO RIGHT TO: yes, caught before commit by the out-of-band-writes hook. The call-site rewrite had changed command names inside 27 ACCEPTED Decision files - text a human attested. Reverted. tool-reference scans processes, skills, docs, contracts, workflows and rules, never decisions, so those files never needed rewriting at all: a Decision names the commands that existed when it was signed, and keeping it current is not a goal. (3) IS THE GUARD STILL AS STRICT: stricter. classify_renderer now resolves the LENS, not the verb - accepting `keel show` alone would let `keel show frobnicate` pass and then fail for whoever ran it, which is the original hole with one extra word in it."; }
    verification cliCollapseCloseOutGate : Test { :>> id = "2b823393-54ab-4576-2e69-d87a5eb69c45"; :>> title = "Sprint 512 closeOut gate (autonomous, D0049)"; :>> createdAt = "2026-09-01"; :>> createdBy = "claudeOpus5"; :>> method = VerificationMethod::inspect; :>> procedureText = "CLOSED with a criterion MISSED and stated: 66 verbs, not the below-25 D0273 promised. issue321 is resolved as to the lens family - the thing the human actually named - and the arithmetic of the remaining families is on the record rather than quietly dropped. D0277 co-committed for the guards.rs change under the keystone lock. Step 5 remains: issue326/issue327, the shipped CI, which is what makes any of this visible downstream."; }
    verification cliCollapseRetroGate : Test { :>> id = "3c934404-65bc-4687-3f70-e96b6fc70d56"; :>> title = "Sprint 512 retro gate (autonomous, D0049)"; :>> createdAt = "2026-09-01"; :>> createdBy = "claudeOpus5"; :>> method = VerificationMethod::analyze; :>> procedureText = "TWO FINDINGS. (1) tracked as issue338: I WROTE A VERIFICATION CRITERION I HAD NOT ARITHMETICALLY CHECKED. D0273's consequences promised 'the visible verb count falls below 25' while the measurement in its own context section - 43 lenses out of ~111 arms - already implied the answer would be near 66. Nobody would have caught it: the criterion sat in an accepted Decision and the work would have been called done. The generalisable rule is narrow and worth keeping: a numeric criterion in a Decision must be DERIVED from the numbers already in that same Decision, or it is a wish with a number attached. (3) tracked as issue339, found while landing: a test exported from the LIVE repository on every run and bumped the real install record - a write side-effect the out-of-band hook flagged as possibly human, which cost a diagnosis. (2) no new item - already tracked: A LIST NOBODY KNOWS TO UPDATE IS THE RECURRING SHAPE OF THIS WHOLE DAY, and each instance is its own Issue (issue322, issue325, issue329) with the class-level control landed in issue329's resolver. VIEW_SUBCOMMANDS was a private mirror of the command surface, and its own comment recorded that it had already failed once for exactly that reason. It is the same shape as the per-instance fixes in issue322, issue325 and issue329, and the same shape as D0252 clause A's command half sitting unbuilt for nine days: in every case a fact had two homes, or a promise had no test, and the failure surfaced only when something happened to touch it. The counter-move that worked here was mechanical - hold the list equal to what it describes BY TEST - and it is now applied to both COMMAND_NAMES and LENS_NAMES."; }
}
