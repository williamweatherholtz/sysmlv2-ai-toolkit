// ProjectDeliveryS407 — Sprint 407: D0193 delivered: the control-event declaration, guard 45, and the three folded fixes - every control event now leaves a counted record. EXECUTE. 2 pts.
package ProjectDeliveryS407 {
    private import EngineElement::*;
    private import EngineWork::*;
    private import EngineVerification::*;
    private import EngineRelationships::*;

    #CharteredBy dependency from controlEventCoverageStory to d0193;
    // D0193's own decree: the three per-instance resolvers are re-chartered under this decision.
    #CharteredBy dependency from dcEnforcementPointSpecPin to d0193;
    #CharteredBy dependency from dcActorRebindLedger to d0193;
    #CharteredBy dependency from dcOverrideCountedOnSuccess to d0193;

    part controlEventCoverageStory : Story {
        :>> id = "bb7b5d0f-eb98-46fe-bd5f-4892c216bfe4";
        :>> title = "Sprint 407: control-event coverage lands as one shape (2 pts)";
        :>> createdAt = "2026-08-22"; :>> createdBy = "claudeFable5"; :>> kind = WorkKind::code; :>> priority = WorkPriority::p0; :>> owner = "claudeFable5"; :>> estimatedPoints = 2;
    }

    action def DeliveryRunS407 {
        action storyControlEventCoverage;
        verification storyControlEventCoverageDoD : Test { :>> id = "6f8cd3ca-a813-476e-a661-d82001570c9d"; :>> method = VerificationMethod::test; :>> procedureText = "DELIVERED (D0193, accepted on their 'approved. keep the momentum going'): dcEnforcementPointSpecPin, dcActorRebindLedger, dcOverrideCountedOnSuccess - the three per-instance resolvers folded under one control exactly as the decision decrees. (1) control-events.toml declares all 12 control-event classes with their required records and the encoding notes (the actor-rebind transition rides the ledger's decision string; the rationale is IN the contract, not in anyone's head). (2) Guard 45 control-event-coverage (WARNING tier): a two-way diff between the declaration and the event names the binary emits - dead declarations and uncounted events both warn; absent contract reports not-adopted (D0136); first run PASSED with 12 scanned and zero warnings, meaning declaration and emitters matched on day one. (3) issue203: the build-time spec-pin point is now in the enforcementPoints inventory with its warn-allow residual stated. (4) issue205: keel actor set leaves a durable record - VERIFIED LIVE: a real rebind appended {event: actor-rebind, decision: claudeFable5->claudeFable5} and enforcement-report counted it (fires: 1). (5) issue207: the happy-path consumption emits override-consumed; pm counts consumed and unsynced separately, bound by a new unit test (3 overrides / 1 unsynced on a synthetic ledger). guards.md + CLAUDE.md 44 -> 45 same commit."; }
        part storyControlEventCoverageDoDR1 : TestResult { :>> id = "a43196dd-22de-4b23-b55b-623ba04b7213"; :>> outcome = VerdictKind::pass; :>> judgedAgainst = "114663c"; :>> judgedAt = "2026-08-21"; :>> judgedBy = "claudeFable5"; }
    }

    verification controlEventCoverageRefineGate : Test { :>> id = "88f5cc86-68d7-4caa-9039-dce2b6701f23"; :>> title = "Sprint 407 refine gate (DoR)"; :>> createdAt = "2026-08-22"; :>> createdBy = "claudeFable5"; :>> method = VerificationMethod::inspect; :>> procedureText = "DoR. Chartered by d0193, accepted this session; the three folded items re-chartered under it by the edges in this file. 2 points."; }
    part controlEventCoverageRefineGateR1 : TestResult { :>> id = "47d52b94-5c78-472d-af6a-353c48317d08"; :>> outcome = VerdictKind::pass; :>> judgedAgainst = "114663c"; :>> judgedAt = "2026-08-21"; :>> judgedBy = "claudeFable5"; }
    verification controlEventCoverageStandupGate : Test { :>> id = "a005ffe3-2949-4050-ab58-e8efe3ab56da"; :>> title = "Sprint 407 standup gate"; :>> createdAt = "2026-08-22"; :>> createdBy = "claudeFable5"; :>> method = VerificationMethod::inspect; :>> procedureText = "Approach per the decision's own shape: declaration first, guard second, fixes third - so the guard's first run cross-checks the fixes the moment they land. The encoding constraints (frozen 6-field ledger schema) forced two recorded choices: the rebind transition in the decision string with session kept clean for the sessions counter, both documented in the contract. No blockers."; }
    part controlEventCoverageStandupGateR1 : TestResult { :>> id = "5de0c48b-de38-423f-ba51-a3fbac955825"; :>> outcome = VerdictKind::pass; :>> judgedAgainst = "114663c"; :>> judgedAt = "2026-08-21"; :>> judgedBy = "claudeFable5"; }
    verification controlEventCoverageImplementGate : Test { :>> id = "441b7e97-4a21-4d20-a3f5-a095549ba1bb"; :>> title = "Sprint 407 implement gate"; :>> createdAt = "2026-08-22"; :>> createdBy = "claudeFable5"; :>> method = VerificationMethod::test; :>> procedureText = "Verified by running: guard 45 first run PASS, 12 scanned, 0 warnings; a REAL rebind produced the ledger line and the report counted it; the spec-pin row reads back from keel hardening; pm unit test asserts 3/1 on a synthetic ledger; cargo test 280 passed (278 + 2 pm), clippy pedantic+nursery clean; validate + check-engine green."; }
    part controlEventCoverageImplementGateR1 : TestResult { :>> id = "19bdafff-4b50-46d4-89f5-e3cbf212bfc5"; :>> outcome = VerdictKind::pass; :>> judgedAgainst = "114663c"; :>> judgedAt = "2026-08-21"; :>> judgedBy = "claudeFable5"; }
    verification controlEventCoverageReviewGate : Test { :>> id = "fada45f3-49ed-421e-a4ca-1486264e99a2"; :>> title = "Sprint 407 review gate — three passes per D0172"; :>> createdAt = "2026-08-22"; :>> createdBy = "claudeFable5"; :>> method = VerificationMethod::inspect; :>> procedureText = "PASS 1, CLAIMS: every verification above is a live run or an executed test quoted from this session's output. PASS 2, BOUNDARY: the guard's EMITTED_LEDGER constant is a hand-maintained list - the exact drift class the guard polices in the contract - so the constant going stale IS caught (a new emitter without the constant shows up as emitted-not-declared only if the contract gains it; a new emitter added nowhere is invisible to the guard). Stated plainly: the two-way diff catches one-sided drift, not both-sided omission; the review discipline for new ledger_emit call sites is the residual, named in the constant's own doc. PASS 3, OWN DIFF: the pm test initially asserted invented field names (overrides/overridesUnsynced) - caught by reading the emitter before running, corrected to the real overrideLedgerEvents/overrideObligationsUnsynced. WHAT A REVIEWER SHOULD ATTACK: the decision-string encoding for rebind transitions - it trades a dedicated field (schema break) for a documented convention; if the ledger schema ever unfreezes, this is the first row to normalize."; }
    part controlEventCoverageReviewGateR1 : TestResult { :>> id = "3c6a4afc-88a9-4219-aae4-0eef6019b507"; :>> outcome = VerdictKind::pass; :>> judgedAgainst = "114663c"; :>> judgedAt = "2026-08-21"; :>> judgedBy = "claudeFable5"; }
    verification controlEventCoverageCloseOutGate : Test { :>> id = "6f93b38f-0361-4754-96ba-5ec8ff4435e2"; :>> title = "Sprint 407 closeOut gate (autonomous, D0049)"; :>> createdAt = "2026-08-22"; :>> createdBy = "claudeFable5"; :>> method = VerificationMethod::inspect; :>> procedureText = "Autonomous closeOut (D0049). Three DoDs flipped on the live verifications; issues 203/205/207 resolve through them; guard 45 in the inventory; validate + all 45 guards green."; }
    part controlEventCoverageCloseOutGateR1 : TestResult { :>> id = "ead99f12-d433-402e-8d9d-b1f7f6ab05a9"; :>> outcome = VerdictKind::pass; :>> judgedAgainst = "114663c"; :>> judgedAt = "2026-08-21"; :>> judgedBy = "claudeFable5"; }
    verification controlEventCoverageRetroGate : Test { :>> id = "99a4acd1-a2cb-42ab-9d76-42f3618cce08"; :>> title = "Sprint 407 retro gate (autonomous, D0049)"; :>> createdAt = "2026-08-22"; :>> createdBy = "claudeFable5"; :>> method = VerificationMethod::analyze; :>> procedureText = "Autonomous retro (D0049). AVOIDABLE-ISSUE SCAN under rcRecurrence: the invented-field-name test defect is the verify-the-wrong-surface family in miniature (asserting a shape not read from the emitter) - caught pre-run by the read-the-emitter-first practice; no recurrence recorded. WELL: folding three fixes under one decision meant one contract, one guard and one review instead of three mechanisms - D0193's premise held in the build. Estimate 2 pts, delivered 2."; }
    part controlEventCoverageRetroGateR1 : TestResult { :>> id = "4886ebc2-b8c9-4832-accf-a4d43be96f67"; :>> outcome = VerdictKind::pass; :>> judgedAgainst = "114663c"; :>> judgedAt = "2026-08-21"; :>> judgedBy = "claudeFable5"; }
}
