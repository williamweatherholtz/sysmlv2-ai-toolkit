// ProjectDeliveryS524 — Sprint 524: exec-summary is removed as a process. CHANGE. 2 pts.
package ProjectDeliveryS524 {
    private import EngineElement::*;
    private import EngineWork::*;
    private import EngineVerification::*;
    private import EngineRelationships::*;

    #CharteredBy dependency from execSummaryRemovedStory to d0288;

    part execSummaryRemovedStory : Story {
        :>> id = "14689802-cbb2-4027-9677-01b9f1b2dd4e";
        :>> title = "Sprint 524: exec-summary removed - process, skill, template, tests, unit record and id gone; five dependents rewritten without tombstones (2 pts)";
        :>> createdAt = "2026-09-03"; :>> createdBy = "claudeOpus5"; :>> kind = WorkKind::modeling; :>> priority = WorkPriority::p0; :>> owner = "claudeOpus5"; :>> estimatedPoints = 2;
    }

    action def DeliveryRunS524 {
        action storyExecSummaryRemoved;
        verification storyExecSummaryRemovedDoD : Test { :>> id = "5ae43bae-a5bb-4c6a-a964-80a6cc741df2"; :>> method = VerificationMethod::test; :>> procedureText = "DELIVERED BACKLOG ITEMS: dcExecSummaryRemoved. The human (st073): remove exec-summary as a process. DONE: deleted .engine/processes/exec-summary.sysml, .engine/skills/exec-summary/, templates/exec-summary/, tests/exec_summary/, the .claude mirror; removed the installed-unit record (a2428932, v3) and the unit id; rewrote decision-surfacing's render step to author the published page directly (same content contract, same-URL republish, deck as second surface), library-stewardship's worked example to decision-channel, stpa-diagram's embed target to the console or the published page, my two live DoDs and one unit-test fixture path; added the one true doc claim (CLAUDE.md section 4: how a fork reaches the human). Incident history naming the unit stays as history. VERIFY: grep over live surfaces finds no reference; all 58 guards pass; 45 skills mirrored; 447 tests pass on the rebuilt binary; the library's v3 copy is untouched and said so."; }
        // RAN: grep -rnE exec-summary|execSummary|se-templates over sysml/toml/md/rs/yml minus history dirs -> process_cmd.rs incident comments, the identity test preamble, done DoD receipts only; keel sync-claude 45/45; keel guard . ALL PASS; cargo build + test 447/0; clippy clean
        part storyExecSummaryRemovedDoDR1 : TestResult { :>> id = "ccb1270a-74a1-4c1c-9c48-d6a887e5c31e"; :>> outcome = VerdictKind::pass; :>> judgedAgainst = "c3dd223"; :>> judgedAt = "2026-09-03"; :>> judgedBy = "claudeOpus5"; }
    }

    verification execSummaryRemovedRefineGate : Test { :>> id = "d76a8105-8ba4-4456-81e5-86f1e7d27783"; :>> title = "Sprint 524 refine gate (DoR)"; :>> createdAt = "2026-09-03"; :>> createdBy = "claudeOpus5"; :>> method = VerificationMethod::inspect; :>> procedureText = "READY after an inventory, not before: 24 files referenced the unit. Sorting them into live claims (rewrite), unit files (delete), records (installed-units, unit-ids: remove) and history (leave) was the whole refine; the one judgment was what decision-surfacing renders WITH once its render step is gone, answered from the process's own text - it already stated the content contract, so the template and its suite were a second home."; }
    verification execSummaryRemovedStandupGate : Test { :>> id = "b06f48c9-ee4f-499d-91e7-c44a6b052440"; :>> title = "Sprint 524 standup gate"; :>> createdAt = "2026-09-03"; :>> createdBy = "claudeOpus5"; :>> method = VerificationMethod::inspect; :>> procedureText = "TWO CHOICES. (1) Delete, not deactivate: D0138 deactivation is a project declining a process the engine still ships; the instruction was that the engine not carry it. (2) The library's published unit is left alone and the Decision says so: it is the human's repository, retiring a unit there is library-stewardship's act, and a downstream importer keeps working. Incident comments in process_cmd.rs that name the unit stay - they say what happened, which the no-tombstones rule protects rather than forbids."; }
    verification execSummaryRemovedImplementGate : Test { :>> id = "795b9b8c-e465-4be7-b7b1-bdd6e5a57a82"; :>> title = "Sprint 524 implement gate"; :>> createdAt = "2026-09-03"; :>> createdBy = "claudeOpus5"; :>> method = VerificationMethod::test; :>> procedureText = "RAN: the removal as one script, run twice - the first run stopped on a regex metacharacter in a literal ('skill + registry'), and the second was idempotent over what the first had already done; a residual grep after each. The keystone lock refused the ten locked files until D0288 carried its marker, and doc-sync asked for a doc claim until CLAUDE.md gained one. Binary rebuilt because .engine is embedded; the suite green on the rebuilt binary."; }
    verification execSummaryRemovedReviewGate : Test { :>> id = "d4d7ede5-e840-4628-8c41-1e5201b19ba1"; :>> title = "Sprint 524 review gate — three passes per D0172"; :>> createdAt = "2026-09-03"; :>> createdBy = "claudeOpus5"; :>> method = VerificationMethod::inspect; :>> procedureText = "THREE PASSES. (1) ANY TOMBSTONE: none - every rewritten sentence states what is, and the removal-path line in decision-surfacing's skill no longer names a thing that stays. (2) ANY DEPENDENT LEFT BROKEN: process-skill, activation-manifest, tool-reference and control-map-reconciled all pass; adoption-check's foreign-tree fixture builds from the embedded engine, which no longer contains the unit. (3) IS ANYTHING LOST: the content contract for a decision page lives in decision-surfacing's steps; the template's browser suite is gone with the template, which is the human's call made."; }
    verification execSummaryRemovedCloseOutGate : Test { :>> id = "0817b605-7a06-4ad7-aebb-ef96e8e539c3"; :>> title = "Sprint 524 closeOut gate (autonomous, D0049)"; :>> createdAt = "2026-09-03"; :>> createdBy = "claudeOpus5"; :>> method = VerificationMethod::inspect; :>> procedureText = "CLOSED. 32 processes ship. The library still lists exec-summary at v3; retiring it there is a stewardship act the human can ask for."; }
    verification execSummaryRemovedRetroGate : Test { :>> id = "5c5a0f11-09aa-44e3-b08e-fe2c55b2517f"; :>> title = "Sprint 524 retro gate (autonomous, D0049)"; :>> createdAt = "2026-09-03"; :>> createdBy = "claudeOpus5"; :>> method = VerificationMethod::analyze; :>> procedureText = "no new item - already tracked: removing a unit has no command - `keel process` lists, exports and imports, and deactivate is not removal - so this was direct edits to two contracts under a Decision. That gap is real but small and the same shape as the port tasks already on the frontier; it is noted here and becomes an item the second time a unit is removed by hand."; }
}
