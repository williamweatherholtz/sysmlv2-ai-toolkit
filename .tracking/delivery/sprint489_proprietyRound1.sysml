// ProjectDeliveryS489 — Sprint 489: the propriety panel exists and its first round convicted its author twice. EXECUTE. 5 pts.
package ProjectDeliveryS489 {
    private import EngineElement::*;
    private import EngineWork::*;
    private import EngineVerification::*;
    private import EngineRelationships::*;

    #CharteredBy dependency from proprietyRound1Story to d0253;

    part proprietyRound1Story : Story {
        :>> id = "0637cc76-c558-4bd3-ab91-9d5798800e34";
        :>> title = "Sprint 489: the control-propriety panel - process, schema, 40 findings, and both unsound verdicts fixed (5 pts)";
        :>> createdAt = "2026-08-29"; :>> createdBy = "claudeOpus5"; :>> kind = WorkKind::code; :>> priority = WorkPriority::p0; :>> owner = "claudeOpus5"; :>> estimatedPoints = 5;
    }

    action def DeliveryRunS489 {
        action storyProprietyRound1;
        verification storyProprietyRound1DoD : Test { :>> id = "8abb8f52-d82e-470c-852f-ddfb781ee1eb"; :>> method = VerificationMethod::test; :>> procedureText = "RESOLVES issue307 and issue308 - both found BY the panel this sprint delivers. DELIVERED: the controlPropriety process (five steps, D0257); the EnginePropriety schema package (five lenses verbatim from st032, eliminative verdicts, atomic ProprietyFinding with mandatory defeater); the control-propriety skill + registry; the propriety TOML view; ROUND 1 - forty findings over the session's eight solutions in .tracking/propriety.sysml; and the fixes for the round's two unsound verdicts (guard 53 traversal shape, guard 54 provenBy resolution). VERIFY: keel validate accepts the new package; keel view propriety computes; both fixes proven armed by injection (84/1 and 23/1 FAIL on planted defects, PASS restored); clippy; full suite; all guards.: DELIVERED BACKLOG ITEMS: <items>. <what done means, verified how>."; }
        // RAN: // RAN: keel validate 550->551 clean (new schema package registers); keel view propriety -> 40 findings; arming injections: traversal key -> g53 FAIL 84/1, dangling provenBy -> g54 FAIL 23/1, both PASS restored; cargo clippy -D warnings clean; cargo test --workspace --release 17 suites 0 FAILED; keel guard 54 guards 0 FAIL; sync-claude 39/39 skills
        part storyProprietyRound1DoDR1 : TestResult { :>> id = "fde8215e-4b79-4d5b-9f4b-1c50d96cc70e"; :>> outcome = VerdictKind::pass; :>> judgedAgainst = "cc58613"; :>> judgedAt = "2026-08-29"; :>> judgedBy = "claudeOpus5"; }
    }

    verification proprietyRound1RefineGate : Test { :>> id = "8caf3f1a-8adc-4c77-92ea-979f9b91337e"; :>> title = "Sprint 489 refine gate (DoR)"; :>> createdAt = "2026-08-29"; :>> createdBy = "claudeOpus5"; :>> method = VerificationMethod::inspect; :>> procedureText = "READY: the human's directive (st032) named the five questions, ordered research first and work-definition first. Research done with sources: mutation-based control assessment, control validation vs compliance, assurance-case defeaters and eliminative induction (Goodenough/Weinstock lineage). Tranche 1 scoped to the session's eight solutions - newest controls, least scrutiny, maximum author bias, so if the method cannot convict here it is decoration."; }
    verification proprietyRound1StandupGate : Test { :>> id = "746689dd-29b1-4b59-9220-56814d9068ba"; :>> title = "Sprint 489 standup gate"; :>> createdAt = "2026-08-29"; :>> createdBy = "claudeOpus5"; :>> method = VerificationMethod::inspect; :>> procedureText = "One design fork settled without the human because the model already answers it: the five lenses are a NEW non-core schema package, not new CritiqueLens members - schema/core is frozen (invariant 5), the questions do not map onto the requirement-quality canon without force-fitting, and the intake rule generalises: a kind the vocabulary cannot express is a change to the vocabulary, never a forced fit. schema/safety is the precedent."; }
    verification proprietyRound1ImplementGate : Test { :>> id = "a0637a56-85e4-4b39-8f13-fe132e0c04fd"; :>> title = "Sprint 489 implement gate"; :>> createdAt = "2026-08-29"; :>> createdBy = "claudeOpus5"; :>> method = VerificationMethod::test; :>> procedureText = "RAN: keel validate (550 clean - the new package registers from disk); keel view propriety (40 rows); arming injections for both fixes; cargo build; clippy; full suite. THE ROUND'S RESULTS: 40 findings = 8 targets x 5 lenses. Verdicts: 2 unsound (pf02 guard-53 traversal, pf33 dangling provenBy), 17 conditional with named standing defeaters, 21 sound with named TRIED refutations. Both unsound verdicts became Issues (307, 308) and were fixed in this same sprint under D0257 clause D, with arming re-proven by injection."; }
    verification proprietyRound1ReviewGate : Test { :>> id = "ae486fbb-c7e6-4ffb-97c0-ee95bb41684c"; :>> title = "Sprint 489 review gate — three passes per D0172"; :>> createdAt = "2026-08-29"; :>> createdBy = "claudeOpus5"; :>> method = VerificationMethod::inspect; :>> procedureText = "THREE PASSES. (1) ELIMINATIVE DISCIPLINE HELD: every one of the 40 findings names its defeater - sound names what was tried (e.g. pf01 lists the three mutated shapes and the UNC residual), conditional names what stands, unsound names the demonstration. A finding without a nameable defeater was returned to assessment (the process's own rule) - none shipped without one. (2) THE FINDINGS DO NOT FLATTER: the panel's targets include the panel author's own two guards from this week, and both took an unsound. The standing conditionals are recorded in the Decision's consequences rather than buried (guard 54's event-emitting-subclass limit, the naming-convention harvest, the strict-vs-guided probe gap, --no-verify). (3) FIX MINIMALITY: the traversal fix is one segment test in the existing predicate; the provenBy fix rides guard 54's existing report rather than a new guard - no new control surface to assess next round."; }
    verification proprietyRound1CloseOutGate : Test { :>> id = "5f1c4bc5-5ad7-4e53-b4c1-5acfe88f5179"; :>> title = "Sprint 489 closeOut gate (autonomous, D0049)"; :>> createdAt = "2026-08-29"; :>> createdBy = "claudeOpus5"; :>> method = VerificationMethod::inspect; :>> procedureText = "CLOSED. The panel exists as process + schema + skill + view; round 1 is recorded; issues 307 and 308 resolve here. DEBT NAMED: tranche 2 (the fifteen mapped controls) and tranche 3 (the proposed solutions D0250-D0252) are inventoried and NOT run - defined work. Candidate probe work the round surfaced without filing (cheap adds named in findings): the non-empty-diff half of finish (pf17), the guided-profile advisory tier (pf22), a lint that every write path takes the model lock (pf12). pf07's event-less-subclass limit is a DISPOSITION candidate for the human: accepting it means accepting that CI-job and remote-config controls are reconciled by hand."; }
    verification proprietyRound1RetroGate : Test { :>> id = "aca346c8-44de-4483-8045-6081a134dd8a"; :>> title = "Sprint 489 retro gate (autonomous, D0049)"; :>> createdAt = "2026-08-29"; :>> createdBy = "claudeOpus5"; :>> method = VerificationMethod::analyze; :>> procedureText = "FINDING 1: the panel paid for itself inside one round - two High defects in week-old controls, both fixed same-day, both found by the exact practice the research predicted (mutate the specimen; hunt the unverified pointer). FINDING 2: the eliminative frame changed the writing, not just the verdicts - forcing a defeater per finding turned 'this is fine' into 'here is what I tried and here is the residual', and the residuals are now the most useful text in the round. FINDING 3, a bias observation recorded per the process's independence step: every target was mine, all 21 sound verdicts are therefore testimonies, and the two convictions do not neutralise that - they show self-audit CAN convict, not that it convicts at the rate an independent critic would. When a second contributor next touches this repo, re-judging the Critical-adjacent sound verdicts (pf14, pf19, pf30) is the cheap independence dividend."; }
}
