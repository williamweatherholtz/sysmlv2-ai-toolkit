// ProjectDeliveryS202 — Sprint 202: fixServeOrientPerf (issue063) — cut orient's git-subprocess count
// (19->9, byte-identical output) + block_in_place so a cold compute never starves the serve worker.
// Field-discovered via keel serve. EXECUTE (perf; no view-meaning change). 2 pt. AUTONOMOUS (D0049).
package ProjectDeliveryS202 {
    private import EngineElement::*;
    private import EngineWork::*;
    private import EngineVerification::*;
    private import EngineRequirements::*;
    private import EngineRelationships::*;

    #CharteredBy dependency from fixServeOrientPerfStory to issue063;

    part fixServeOrientPerfStory : Story {
        :>> id = "63940516-2c7d-4e8f-c202-51627384c001";
        :>> title = "Sprint 202: fixServeOrientPerf (2 pt) - trim orient git spawns 19->9 (byte-identical) + block_in_place (issue063)";
        :>> createdAt = "2026-07-14"; :>> createdBy = "wweatherholtz"; :>> kind = WorkKind::code; :>> priority = WorkPriority::p2; :>> owner = "claudeOpus"; :>> estimatedPoints = 2;
    }

    action def DeliveryRunS202 {
        action storyFixServeOrientPerf;
        verification storyFixServeOrientPerfDoD : Test { :>> id = "63940516-2c7d-4e8f-c202-51627384c002"; :>> method = VerificationMethod::test; :>> procedureText = "Resolves issue063. (a) orient.rs git_criterion_at (the per-task criterion-drift FALLBACK) now does ONE `git grep -h -F` for the DoD's single-line declaration at the commit, instead of `git ls-tree` + a `git show` per .sysml file; -h yields the raw line so the procedureText extraction is IDENTICAL -> orient output byte-identical. (b) serve.rs cached() runs the compute via tokio::task::block_in_place (runtime is new_multi_thread) so a cold compute never starves the axum worker. MEASURED: git spawns 19->9; orient JSON diff clean (byte-identical); A/B n=40 CLI-cold median 1211->847ms / p95 1769->1077ms / max 1820->1145ms; NEW n=100 median 841 / p99 1154 / MAX 1154ms / 0 spikes>3s; live serve /api/item 0.29s while orient computed 1.03s. Honest limit: the 16-23s spikes are ~1/50 external events, too rare to A/B — the win is the distribution shift + halved spawn count. VERIFY: clippy -D clean; cargo test (80) green; keel validate + guard green; byte-identical orient confirmed."; }
        part storyFixServeOrientPerfDoDR1 : TestResult { :>> id = "63940516-2c7d-4e8f-c202-51627384c003"; :>> outcome = VerdictKind::pass; :>> judgedAgainst = "50238fc"; :>> judgedAt = "2026-07-14"; :>> judgedBy = "claudeOpus"; }
    }

    verification fsopRefineGate : Test { :>> id = "63940516-2c7d-4e8f-c202-51627384c004"; :>> title = "Sprint 202 refine gate (DoR)"; :>> createdAt = "2026-07-14"; :>> createdBy = "claudeOpus"; :>> method = VerificationMethod::inspect; :>> procedureText = "DoR: issue063 triaged (resolver fixServeOrientPerf). Root MEASURED before fixing (GIT_TRACE: 19 spawns, not hundreds) — the fallback is the ~15 avoidable spawns. Fix is perf-only (byte-identical orient), so EXECUTE. estimatedPoints=2. #CharteredBy issue063. DoR met."; }
    part fsopRefineGateR1 : TestResult { :>> id = "63940516-2c7d-4e8f-c202-51627384c005"; :>> outcome = VerdictKind::pass; :>> judgedAgainst = "50238fc"; :>> judgedAt = "2026-07-14"; :>> judgedBy = "claudeOpus"; }
    verification fsopStandupGate : Test { :>> id = "63940516-2c7d-4e8f-c202-51627384c006"; :>> title = "Sprint 202 standup gate"; :>> createdAt = "2026-07-14"; :>> createdBy = "claudeOpus"; :>> method = VerificationMethod::inspect; :>> procedureText = "Approach: replace git_criterion_at's ls-tree+N-shows with one `git grep -h -F` (identical extraction); wrap cached() compute in block_in_place. Guard = byte-identical orient output + measured distribution. No blockers."; }
    part fsopStandupGateR1 : TestResult { :>> id = "63940516-2c7d-4e8f-c202-51627384c007"; :>> outcome = VerdictKind::pass; :>> judgedAgainst = "50238fc"; :>> judgedAt = "2026-07-14"; :>> judgedBy = "claudeOpus"; }
    verification fsopImplementGate : Test { :>> id = "63940516-2c7d-4e8f-c202-51627384c008"; :>> title = "Sprint 202 implement gate"; :>> createdAt = "2026-07-14"; :>> createdBy = "claudeOpus"; :>> method = VerificationMethod::test; :>> procedureText = "git grep fallback + block_in_place landed. Byte-identical orient (diff clean). Spawns 19->9. A/B n=40: median 1211->847ms, p95 1769->1077ms, max 1820->1145ms. NEW n=100: MAX 1154ms, 0 spikes. Live serve concurrency verified. clippy -D clean; cargo test (80) green; keel validate + guard green."; }
    part fsopImplementGateR1 : TestResult { :>> id = "63940516-2c7d-4e8f-c202-51627384c009"; :>> outcome = VerdictKind::pass; :>> judgedAgainst = "50238fc"; :>> judgedAt = "2026-07-14"; :>> judgedBy = "claudeOpus"; }
    verification fsopReviewGate : Test { :>> id = "63940516-2c7d-4e8f-c202-51627384c00a"; :>> title = "Sprint 202 review gate"; :>> createdAt = "2026-07-14"; :>> createdBy = "claudeOpus"; :>> method = VerificationMethod::inspect; :>> procedureText = "Reviewed. The fix rests on a MEASUREMENT (19 spawns, not the assumed hundreds) and preserves semantics provably (byte-identical orient output is the regression guard, per the human's 'ensure timing is accurate' + 'spikes were spurious' pushback). The distribution A/B (n=40, whole curve down ~35%) is the honest evidence; the rare-spike claim is stated as mechanism (halved spawns) not proof — no overclaim. block_in_place is the right minimal robustness fix (no async refactor; multi-thread runtime). Clean."; }
    part fsopReviewGateR1 : TestResult { :>> id = "63940516-2c7d-4e8f-c202-51627384c00b"; :>> outcome = VerdictKind::pass; :>> judgedAgainst = "50238fc"; :>> judgedAt = "2026-07-14"; :>> judgedBy = "claudeOpus"; }
    verification fsopCloseOutGate : Test { :>> id = "63940516-2c7d-4e8f-c202-51627384c00c"; :>> title = "Sprint 202 closeOut gate (autonomous, D0049)"; :>> createdAt = "2026-07-14"; :>> createdBy = "claudeOpus"; :>> method = VerificationMethod::inspect; :>> procedureText = "Autonomous closeOut (D0049): DoD pass; issue063 resolved (fixServeOrientPerf done). Byte-identical orient + measured distribution shift + 0/100 spikes. clippy + cargo test + keel validate + guard green. Self-evidencing (D0051). NEXT: Sprint 203 = osAdaptiveCommandGuidance (issue065)."; }
    part fsopCloseOutGateR1 : TestResult { :>> id = "63940516-2c7d-4e8f-c202-51627384c00d"; :>> outcome = VerdictKind::pass; :>> judgedAgainst = "50238fc"; :>> judgedAt = "2026-07-14"; :>> judgedBy = "claudeOpus"; }
    verification fsopRetroGate : Test { :>> id = "63940516-2c7d-4e8f-c202-51627384c00e"; :>> title = "Sprint 202 retro gate (autonomous, D0049)"; :>> createdAt = "2026-07-14"; :>> createdBy = "claudeOpus"; :>> method = VerificationMethod::analyze; :>> procedureText = "Autonomous retro (D0049). WELL: measurement-before-fixing corrected a wrong root cause (I'd claimed 'hundreds of git spawns'; GIT_TRACE showed 19) BEFORE any code — the human's 'timing was spurious, not consistent' pushback drove a proper A/B (n=40) + a 100-run spike hunt, so the perf claim is evidence-backed and honestly caveated (spikes too rare to A/B). Byte-identical orient output was the semantic-preservation guard. AVOIDABLE-ISSUE SCAN: the original issue063 overstatement ('hundreds') was an un-measured guess -> LESSON (reinforces issue063 itself): measure the hot path before asserting its cost; a plausible mechanism is not a measurement. Estimate 2 pt held. NEXT: issue065 (osAdaptiveCommandGuidance) then the issue066 JVM spike."; }
    part fsopRetroGateR1 : TestResult { :>> id = "63940516-2c7d-4e8f-c202-51627384c00f"; :>> outcome = VerdictKind::pass; :>> judgedAgainst = "50238fc"; :>> judgedAt = "2026-07-14"; :>> judgedBy = "claudeOpus"; }
}
