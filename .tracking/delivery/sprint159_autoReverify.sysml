// ProjectDeliveryS159 — Sprint 159: autoReverifyReproducible (CHANGE, D0101) — `keel reverify`: honest
// auto-re-verification of drift-suspect REPRODUCIBLE method=test checks (re-run the configured gate at
// HEAD, stamp a fresh result on green, never fabricate). Answers the human's "why isn't suspicion auto-
// fixed?". EXECUTE (CHANGE). 3 pts. AUTONOMOUS ceremony (D0049); D0101 carries the human acceptance.
package ProjectDeliveryS159 {
    private import EngineElement::*;
    private import EngineWork::*;
    private import EngineVerification::*;
    private import EngineRelationships::*;

    #CharteredBy dependency from autoReverifyStory to autoReverifyReproducible;

    part autoReverifyStory : Story {
        :>> id = "63940516-2c7d-4e8f-c159-51627384c001";
        :>> title = "Sprint 159: autoReverifyReproducible (3 pts, CHANGE/D0101) — keel reverify auto-re-verifies reproducible drift at HEAD";
        :>> createdAt = "2026-06-25"; :>> createdBy = "wweatherholtz"; :>> kind = WorkKind::code; :>> priority = WorkPriority::p2; :>> owner = "claudeOpus"; :>> estimatedPoints = 3;
    }

    action def DeliveryRunS159 {
        action storyAutoReverify;
        verification storyAutoReverifyDoD : Test { :>> id = "63940516-2c7d-4e8f-c159-51627384c002"; :>> method = VerificationMethod::test; :>> procedureText = "CHANGE per D0101 (accepted by wweatherholtz; kernel-validated 117/117). DELIVERED: `keel reverify [--all-drift|--task NAME] [--by ACTOR] [ROOT]` (reverify.rs + main.rs cmd_reverify + lib.rs mod) + `.engine/contracts/reverify.toml` (the reproducible gate: cargo test --workspace --release + clippy -D warnings). It computes drift-suspect deliverable tasks (orient suspect ∩ manifest), runs the gate (isolated into target/reverify so it never clobbers the running keel.exe — fixed a self-replacement lock found on the first run), and on ALL-green appends a fresh judged-at-HEAD TestResult per task via the write API; on failure stamps nothing (honest — never fabricates). Judgment methods (confirmation/inspect/analyze/demo) out of scope. VERIFIED LIVE: `keel reverify --all-drift` at edd7b75 ran the gate GREEN + stamped 14/14 drift tasks fresh (drift 17->0). Unit tests: parse_commands, manifest_task_names. clippy -D warnings + cargo test (67 lib) + keel validate + guard all (12) green; doc-sync CLAUDE.md §1+§5. CI green."; }
        part storyAutoReverifyDoDR1 : TestResult { :>> id = "63940516-2c7d-4e8f-c159-51627384c003"; :>> outcome = VerdictKind::pass; :>> judgedAgainst = "edd7b75"; :>> judgedAt = "2026-06-25"; :>> judgedBy = "claudeOpus"; }
    }

    verification autoReverifyRefineGate : Test { :>> id = "63940516-2c7d-4e8f-c159-51627384c004"; :>> title = "Sprint 159 refine gate (DoR)"; :>> createdAt = "2026-06-25"; :>> createdBy = "claudeOpus"; :>> method = VerificationMethod::inspect; :>> procedureText = "DoR: the human's 'why isn't suspicion auto-fixed?' surfaced a real friction gap (manual re-verify toil, D0054). Design accepted as D0101 (run the reproducible gate, stamp on green, never fabricate; human chose 'Build autoReverify first'). CHANGE: new subcommand + contract (no guard/gate-definition change, so no keystone). estimatedPoints=3. #CharteredBy autoReverifyReproducible. DoR met."; }
    part autoReverifyRefineGateR1 : TestResult { :>> id = "63940516-2c7d-4e8f-c159-51627384c005"; :>> outcome = VerdictKind::pass; :>> judgedAgainst = "edd7b75"; :>> judgedAt = "2026-06-25"; :>> judgedBy = "claudeOpus"; }
    verification autoReverifyStandupGate : Test { :>> id = "63940516-2c7d-4e8f-c159-51627384c006"; :>> title = "Sprint 159 standup gate"; :>> createdAt = "2026-06-25"; :>> createdBy = "claudeOpus"; :>> method = VerificationMethod::inspect; :>> procedureText = "Approach: reverify.rs (parse_commands + manifest_task_names [TDD] + drift_tasks + run); reverify.toml contract; cmd_reverify + dispatch. Stamp via write::append_result. Record D0101 + kernel-validate. Live-run to prove it. No blockers identified at standup (the self-replacement lock was found + fixed during implement)."; }
    part autoReverifyStandupGateR1 : TestResult { :>> id = "63940516-2c7d-4e8f-c159-51627384c007"; :>> outcome = VerdictKind::pass; :>> judgedAgainst = "edd7b75"; :>> judgedAt = "2026-06-25"; :>> judgedBy = "claudeOpus"; }
    verification autoReverifyImplementGate : Test { :>> id = "63940516-2c7d-4e8f-c159-51627384c008"; :>> title = "Sprint 159 implement gate"; :>> createdAt = "2026-06-25"; :>> createdBy = "claudeOpus"; :>> method = VerificationMethod::test; :>> procedureText = "Implemented reverify.rs (3 unit tests) + reverify.toml + cmd_reverify. First live run hit a self-replacement lock (cargo --release tried to overwrite the running keel.exe -> Access denied); FIX: CARGO_TARGET_DIR=target/reverify isolates the gate build (committed edd7b75). Second live run: gate GREEN, stamped 14/14 drift tasks @ edd7b75. clippy -D warnings + cargo test (67 lib) + keel validate (172) + guard all (12) green. D0101 kernel-validated 117/117."; }
    part autoReverifyImplementGateR1 : TestResult { :>> id = "63940516-2c7d-4e8f-c159-51627384c009"; :>> outcome = VerdictKind::pass; :>> judgedAgainst = "edd7b75"; :>> judgedAt = "2026-06-25"; :>> judgedBy = "claudeOpus"; }
    verification autoReverifyReviewGate : Test { :>> id = "63940516-2c7d-4e8f-c159-51627384c00a"; :>> title = "Sprint 159 review gate"; :>> createdAt = "2026-06-25"; :>> createdBy = "claudeOpus"; :>> method = VerificationMethod::inspect; :>> procedureText = "Reviewed. The tool is honest by construction: it stamps ONLY after the real gate passes at HEAD; on red it leaves tasks suspect + reports (proven by the first run, which correctly reported the build failure + stamped nothing). The reverify-command is config-driven (downstream-overridable, like critique-policy.toml), not hardcoded cargo. SCOPE NOTE (honest): reverify covers deliverable-MANIFEST action-tasks; the SR #Verify Tests (sr07/10/12/13Verify) are not manifest tasks, so they were re-verified manually in the A1 sprint (s160) — a noted coverage edge of reverify (it stamps action DoDs, not #Verify Tests). Clean."; }
    part autoReverifyReviewGateR1 : TestResult { :>> id = "63940516-2c7d-4e8f-c159-51627384c00b"; :>> outcome = VerdictKind::pass; :>> judgedAgainst = "edd7b75"; :>> judgedAt = "2026-06-25"; :>> judgedBy = "claudeOpus"; }
    verification autoReverifyCloseOutGate : Test { :>> id = "63940516-2c7d-4e8f-c159-51627384c00c"; :>> title = "Sprint 159 closeOut gate (autonomous, D0049)"; :>> createdAt = "2026-06-25"; :>> createdBy = "claudeOpus"; :>> method = VerificationMethod::inspect; :>> procedureText = "Autonomous closeOut (D0049): DoD pass; `keel reverify` shipped + live-proven (drift 17->0 via one command). clippy + cargo test (67 lib) + keel validate (172) + guard all (12) + D0101 kernel 117/117 + CI green. Self-evidencing (D0051). Supersedes the manual re-verify toil for reproducible deliverable drift going forward. Enables A1 (sprint160)."; }
    part autoReverifyCloseOutGateR1 : TestResult { :>> id = "63940516-2c7d-4e8f-c159-51627384c00d"; :>> outcome = VerdictKind::pass; :>> judgedAgainst = "edd7b75"; :>> judgedAt = "2026-06-25"; :>> judgedBy = "claudeOpus"; }
    verification autoReverifyRetroGate : Test { :>> id = "63940516-2c7d-4e8f-c159-51627384c00e"; :>> title = "Sprint 159 retro gate (autonomous, D0049)"; :>> createdAt = "2026-06-25"; :>> createdBy = "claudeOpus"; :>> method = VerificationMethod::analyze; :>> procedureText = "Autonomous retro (D0049). WELL: a user question ('why not automatic?') turned into a durable tool that honors honest-state (never fabricates) while killing real friction (D0054) — the best kind of CHANGE. The first live run FAILING was actually a WIN: it proved the honest path (report + stamp nothing) AND surfaced the self-replacement lock before it could mislead. AVOIDABLE-ISSUE SCAN: (1) self-replacement lock — FIXED structurally (isolated target dir); class won't recur. (2) I piped `conda run validate_instances.py | tail` and HUNG the kernel (CLAUDE.md §6 explicitly warns: never pipe conda) — swept 5 stale JVMs + re-ran plain. LESSON (reinforced): never pipe conda kernel runs. (3) reverify covers action-task DoDs but not #Verify Tests — noted; the 4 SR verify tests were done manually in s160; a future extension could let reverify refresh #Verify Tests too. Estimate 3 pts held."; }
    part autoReverifyRetroGateR1 : TestResult { :>> id = "63940516-2c7d-4e8f-c159-51627384c00f"; :>> outcome = VerdictKind::pass; :>> judgedAgainst = "edd7b75"; :>> judgedAt = "2026-06-25"; :>> judgedBy = "claudeOpus"; }
}
