// ProjectDeliveryS355 — Sprint 355: the deck stops asking the human to copy their own judgments back.
// The page becomes the document; a tap is the submission. EXECUTE. 3 pts.
package ProjectDeliveryS355 {
    private import EngineElement::*;
    private import EngineWork::*;
    private import EngineVerification::*;
    private import EngineRelationships::*;

    #CharteredBy dependency from liveDocStory to d0093;

    part liveDocStory : Story {
        :>> id = "0d8005e0-0814-65e0-9b3e-0000003005e0";
        :>> title = "Sprint 355: the review deck becomes a live document - a tap is the submission (issue159, 3 pts)";
        :>> createdAt = "2026-08-20"; :>> createdBy = "claudeOpus5"; :>> kind = WorkKind::code; :>> priority = WorkPriority::p0; :>> owner = "claudeOpus5"; :>> estimatedPoints = 3;
    }

    action def DeliveryRunS355 {
        action storyLiveDoc;
        verification storyLiveDocDoD : Test { :>> id = "0d8005e1-0814-65e1-9b3e-0000003005e1"; :>> method = VerificationMethod::demo; :>> procedureText = "Delivered by dcLiveDoc. THEY ASKED WHY THEY HAD TO COPY THEIR OWN JUDGMENTS BACK, AND THERE WAS NO GOOD ANSWER. The deck is now an artifact LIVE DOC (`capabilities: {artifact: {}}`, runtime contract 0.2.9): the page's markup IS the document, so a verdict tap setting `data-verdict` and a note typed into an `<input>` are appended as them and reach the watching session with no export step. The `Copy for Claude` export survives as a fallback for a read-only view, and now copies ON OPEN instead of charging a second click - their second complaint in the same message. Also accepted this turn: D0166, on the revision their NEEDS WORK asked for. validate 385 clean; check-engine clean; 36 guards ALL PASS."; }
        part storyLiveDocDoDR1 : TestResult { :>> id = "0d8005e2-0814-65e2-9b3e-0000003005e2"; :>> outcome = VerdictKind::fail; :>> judgedAgainst = "PENDING"; :>> judgedAt = "2026-08-20"; :>> judgedBy = "claudeOpus5"; }
    }

    verification ldRefineGate : Test { :>> id = "0d8005e3-0814-65e3-9b3e-0000003005e3"; :>> title = "Sprint 355 refine gate (DoR)"; :>> createdAt = "2026-08-20"; :>> createdBy = "claudeOpus5"; :>> method = VerificationMethod::inspect; :>> procedureText = "DoR. Their question was WHY, and the honest answer is that I took the canvas skill's safe default (localStorage plus paste-back) and never revisited it after the deck became their only channel on remote control. The skill says to use the live-doc capability when a real-time round trip is a hard requirement; it became one four exports ago and I kept the default. Scoped as: read the capability contract FIRST, then convert. estimatedPoints=3."; }
    part ldRefineGateR1 : TestResult { :>> id = "0d8005e4-0814-65e4-9b3e-0000003005e4"; :>> outcome = VerdictKind::pass; :>> judgedAgainst = "PENDING"; :>> judgedAt = "2026-08-20"; :>> judgedBy = "claudeOpus5"; }

    verification ldStandupGate : Test { :>> id = "0d8005e5-0814-65e5-9b3e-0000003005e5"; :>> title = "Sprint 355 standup gate"; :>> createdAt = "2026-08-20"; :>> createdBy = "claudeOpus5"; :>> method = VerificationMethod::inspect; :>> procedureText = "Approach: LOAD THE CONTRACT BEFORE WRITING ANY OF IT, because live-doc sync fails SILENTLY in at least four ways and every one of them would look like the page working. The type definitions are authoritative over anything I remember about the API, and reading them changed four decisions rather than confirming them. No blockers."; }
    part ldStandupGateR1 : TestResult { :>> id = "0d8005e6-0814-65e6-9b3e-0000003005e6"; :>> outcome = VerdictKind::pass; :>> judgedAgainst = "PENDING"; :>> judgedAt = "2026-08-20"; :>> judgedBy = "claudeOpus5"; }

    verification ldImplementGate : Test { :>> id = "0d8005e7-0814-65e7-9b3e-0000003005e7"; :>> title = "Sprint 355 implement gate"; :>> createdAt = "2026-08-20"; :>> createdBy = "claudeOpus5"; :>> method = VerificationMethod::test; :>> procedureText = "FOUR CONTRACT RULES, EACH OF WHICH WOULD HAVE BROKEN SYNC WITHOUT ANY VISIBLE SYMPTOM. (1) THE localStorage RESTORE IS DELETED. It mutated `data-verdict` at LOAD, and the contract is explicit that only changes made while a gesture is being handled are saved - a load-time render saves nothing and can switch the element off for the view. Worse, it would have been a SECOND RECORD disagreeing with the document, and the document is the one that reaches Claude. (2) PER-VIEWER CHROME MOVED TO `data-local-open`: which class sections a reader has expanded is theirs, and on a live doc every ordinary attribute change is broadcast - so collapsing a section would have been an edit sent to everyone. (3) NOTES STAY `<input>`: the contract says `<textarea>` values are NOT captured, so the obvious upgrade to a multi-line note field would have silently dropped every note. (4) READ-ONLY IS A REJECTION, NOT AN ASSUMPTION: detected from a BODY-level `claude:sync-off`, because that same event also fires for a single benign region and treating any of them as read-only is the canvas skill's anti-pattern 3. A read-only viewer now gets a banner and the export instead of a page that looks writable and saves nothing. THE SECOND COMPLAINT WAS ONE LINE: `Copy for Claude` opened a panel and made them press Copy. It now copies on open."; }
    part ldImplementGateR1 : TestResult { :>> id = "0d8005e8-0814-65e8-9b3e-0000003005e8"; :>> outcome = VerdictKind::pass; :>> judgedAgainst = "PENDING"; :>> judgedAt = "2026-08-20"; :>> judgedBy = "claudeOpus5"; }

    verification ldReviewGate : Test { :>> id = "0d8005e9-0814-65e9-9b3e-0000003005e9"; :>> title = "Sprint 355 review gate"; :>> createdAt = "2026-08-20"; :>> createdBy = "claudeOpus5"; :>> method = VerificationMethod::inspect; :>> procedureText = "Reviewed. THE COST OF THIS CHANGE IS REAL AND MUST BE STATED: a live doc holds their marks in the PUBLISHED PAGE, so REPUBLISHING A REGENERATED DECK OVERWRITES THEM. The workflow is therefore: they mark up the live page, I read it, I act, and only then do I regenerate - their marks are consumed before replacement, never after. That ordering is now a rule in the skill rather than something I have to remember, because getting it backwards destroys work they have already done. THE PATTERN THIS CLOSES: issue141/143/152/154/155/157/158/159 are one defect in eight costumes - an affordance promising more than it delivers - and this is the first one fixed by REMOVING a step rather than by explaining or relabelling one. The copy button was not confusing; it was unnecessary, and it had been unnecessary since the moment the deck became their channel. WHAT I WILL NOT CLAIM: that a tap now reaches me. The result is FAILING with method=demo until they confirm it, because I cannot execute the page and this would be the ninth unobserved browser assertion of the session."; }
    part ldReviewGateR1 : TestResult { :>> id = "0d8005ea-0814-65ea-9b3e-0000003005ea"; :>> outcome = VerdictKind::pass; :>> judgedAgainst = "PENDING"; :>> judgedAt = "2026-08-20"; :>> judgedBy = "claudeOpus5"; }

    verification ldCloseOutGate : Test { :>> id = "0d8005eb-0814-65eb-9b3e-0000003005eb"; :>> title = "Sprint 355 closeOut gate (autonomous, D0049)"; :>> createdAt = "2026-08-20"; :>> createdBy = "claudeOpus5"; :>> method = VerificationMethod::inspect; :>> procedureText = "Autonomous closeOut (D0049). D0166 ACCEPTED on their verdict, with the instruction that produced the revision quoted in the acceptance - pendingAcceptances is empty. issue159 recorded and triaged to dcLiveDoc, whose result is FAILING with method=demo. THIS SPRINT'S OWN SITTING REVIEW IS THE FIRST THING THEY CAN TAP, which is deliberate: the queue was empty, so the sprint that removed the copy step becomes the item that tests whether removing it worked. validate 385 clean; check-engine clean; 36 guards ALL PASS."; }
    part ldCloseOutGateR1 : TestResult { :>> id = "0d8005ec-0814-65ec-9b3e-0000003005ec"; :>> outcome = VerdictKind::pass; :>> judgedAgainst = "PENDING"; :>> judgedAt = "2026-08-20"; :>> judgedBy = "claudeOpus5"; }

    verification ldRetroGate : Test { :>> id = "0d8005ed-0814-65ed-9b3e-0000003005ed"; :>> title = "Sprint 355 retro gate (autonomous, D0049)"; :>> createdAt = "2026-08-20"; :>> createdBy = "claudeOpus5"; :>> method = VerificationMethod::analyze; :>> procedureText = "Autonomous retro (D0049) under D0131's retroTrack. AVOIDABLE-ISSUE: I made them hand-copy a markdown block FOUR TIMES to submit judgments the page already held, and the capability that removes the step was available the whole time. The skill I was following says to default to localStorage and to reach for the live doc when a real-time round trip is a hard requirement - and it BECAME one the moment the deck was their only channel on remote control. I read a default as a rule and never re-read the condition attached to it. THE GENERAL FORM, and it is the same failure as issue154: a documented default is a starting point, not a finding; when the situation changes, the condition on the default is the thing to re-check. SECOND AVOIDABLE-ISSUE: the export's second click. I wrote a control whose label was `Copy for Claude` and whose behaviour was `open a panel`, which is the affordance-overpromise defect for the eighth time this session and the second time I built it into the same page. WELL: (1) I loaded the capability contract before writing a line, and it changed four decisions rather than confirming them - the localStorage restore, the per-viewer attribute, the input-not-textarea rule, and the read-only signal; (2) the read-only path is designed for rather than discovered, so a viewer without the grant gets a banner and the export instead of a page that looks writable and silently saves nothing; (3) the republish-overwrites-their-marks hazard is written into the skill as an ordering rule instead of left for me to remember; (4) the result is recorded FAIL with method=demo rather than claiming a browser behaviour I cannot observe. Estimate 3 pts, delivered with verification outstanding."; }
    part ldRetroGateR1 : TestResult { :>> id = "0d8005ee-0814-65ee-9b3e-0000003005ee"; :>> outcome = VerdictKind::pass; :>> judgedAgainst = "PENDING"; :>> judgedAt = "2026-08-20"; :>> judgedBy = "claudeOpus5"; }
}
