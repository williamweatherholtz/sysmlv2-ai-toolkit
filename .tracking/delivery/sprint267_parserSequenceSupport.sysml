// ProjectDeliveryS267 — Sprint 267: keel-parser accepts the multi-valued assignment the kernel already
// accepts (issue095), plus the control for the safety property that lifting it removed (issue101).
// EXECUTE. 3 pts.
package ProjectDeliveryS267 {
    private import EngineElement::*;
    private import EngineWork::*;
    private import EngineVerification::*;
    private import EngineRelationships::*;

    #CharteredBy dependency from parserSeqStory to d0139;

    part parserSeqStory : Story {
        :>> id = "0d800054-0814-6054-9b3e-000000300054";
        :>> title = "Sprint 267: multi-valued feature assignment parses; sequence-multiplicity guard (3 pts)";
        :>> createdAt = "2026-08-14"; :>> createdBy = "claudeOpus5"; :>> kind = WorkKind::code; :>> priority = WorkPriority::p0; :>> owner = "claudeOpus5"; :>> estimatedPoints = 3;
    }

    action def DeliveryRunS267 {
        action storyParserSeq;
        verification storyParserSeqDoD : Test { :>> id = "0d800055-0814-6055-9b3e-000000300055"; :>> method = VerificationMethod::test; :>> procedureText = "Covers dcParserSequenceSupport (issue095) and dcSequenceMultiplicityGuard (issue101). keel-parser rejected `:>> f = (a, b, c)` with 'unexpected character (' while the KERNEL accepts it, and the syntax notes had recorded the form as kernel-confirmed WITHOUT noting the rust rejection — so `ref` features looked unusable for any one-to-many edge and metadata markers looked like the only way to express one. DELIVERED: `LParen`/`RParen`/`Comma` tokens, `Value::Seq(Vec<Self>)`, sequence parsing in `parse_value`, and `value_to_string` joining elements so a multi-valued attribute rendered as a scalar shows EVERY element rather than the first. VERIFIED, each case measured through `keel check`: the exact kernel-accepted case now passes; empty `()` accepted (deliberate — the honest way to author a multi-valued feature with no targets); trailing comma accepted (one-per-line lists stay editable); single value unchanged; sequence of strings works; and the NEGATIVE case `(c1 c2)` with a missing comma still FAILS. The compiler found the single exhaustive-match site that needed updating, which is the argument for putting this in the type rather than hacking strings. ALSO DELIVERED because the negative test exposed it: lifting the `(` restriction removed an ACCIDENTAL safety property — a sequence can now be written into a SINGLE-valued attribute, and `createdBy = (\"you\", \"ghost\")` passes validate AND `guard actors`, admitting an unregistered actor. The precise rule needs multiplicity metadata the AST does not carry, so the interim control is a warning-level `sequence-multiplicity` guard reporting every sequence — 0 in the real model, and the hazard case reported with file:line in the probe project. 26 guards (19 hard, 7 warning-only); clippy clean; 161 tests; validate + guard + check-engine green."; }
        part storyParserSeqDoDR1 : TestResult { :>> id = "0d800056-0814-6056-9b3e-000000300056"; :>> outcome = VerdictKind::pass; :>> judgedAgainst = "e733115"; :>> judgedAt = "2026-08-14"; :>> judgedBy = "claudeOpus5"; }
    }

    verification psRefineGate : Test { :>> id = "0d800057-0814-6057-9b3e-000000300057"; :>> title = "Sprint 267 refine gate (DoR)"; :>> createdAt = "2026-08-14"; :>> createdBy = "claudeOpus5"; :>> method = VerificationMethod::inspect; :>> procedureText = "DoR: the human directed jumping straight here from the frontier ('let's push to #4'), skipping the migration tool and census, and accepted that things may be unsafe mid-construction. This is the correct jump: every conversion in the pass needs the parser to READ the target construct first, and this is the smallest well-defined piece of that. estimatedPoints=3. DoR met."; }
    part psRefineGateR1 : TestResult { :>> id = "0d800058-0814-6058-9b3e-000000300058"; :>> outcome = VerdictKind::pass; :>> judgedAgainst = "e733115"; :>> judgedAt = "2026-08-14"; :>> judgedBy = "claudeOpus5"; }

    verification psStandupGate : Test { :>> id = "0d800059-0814-6059-9b3e-000000300059"; :>> title = "Sprint 267 standup gate"; :>> createdAt = "2026-08-14"; :>> createdBy = "claudeOpus5"; :>> method = VerificationMethod::inspect; :>> procedureText = "Approach: add the variant to the TYPE rather than special-casing strings, so the compiler enumerates every consumer that must handle it — one site, found immediately. Then test the edge cases the DoD named (empty, trailing comma, malformed) rather than only the happy path, because 'decided and tested, not incidental' was written into the criterion specifically to prevent shipping accidental behaviour. That is what surfaced issue101. No blockers."; }
    part psStandupGateR1 : TestResult { :>> id = "0d80005a-0814-605a-9b3e-00000030005a"; :>> outcome = VerdictKind::pass; :>> judgedAgainst = "e733115"; :>> judgedAt = "2026-08-14"; :>> judgedBy = "claudeOpus5"; }

    verification psImplementGate : Test { :>> id = "0d80005b-0814-605b-9b3e-00000030005b"; :>> title = "Sprint 267 implement gate"; :>> createdAt = "2026-08-14"; :>> createdBy = "claudeOpus5"; :>> method = VerificationMethod::test; :>> procedureText = "Three choices worth recording. (1) Empty `()` is ACCEPTED: it is the honest way to say a multi-valued feature currently has no targets, and rejecting it would push authors to omit the assignment entirely, which says something different. (2) `value_to_string` JOINS elements rather than taking the first — a lossy scalar view of a sequence is unavoidable, but showing element one and silently dropping the rest is the failure a caller cannot see. (3) The guard is AST-based: the text-scan version matched 4 occurrences that were all prose DISCUSSING sequences, reproducing issue099's self-inflating census in miniature, which is a small but exact demonstration of why the census item exists."; }
    part psImplementGateR1 : TestResult { :>> id = "0d80005c-0814-605c-9b3e-00000030005c"; :>> outcome = VerdictKind::pass; :>> judgedAgainst = "e733115"; :>> judgedAt = "2026-08-14"; :>> judgedBy = "claudeOpus5"; }

    verification psReviewGate : Test { :>> id = "0d80005d-0814-605d-9b3e-00000030005d"; :>> title = "Sprint 267 review gate"; :>> createdAt = "2026-08-14"; :>> createdBy = "claudeOpus5"; :>> method = VerificationMethod::inspect; :>> procedureText = "Reviewed. The DoD's own criterion caught the defect this sprint introduced, which is the strongest argument available for writing edge cases into a criterion before implementing. What remains OPEN and is now the real blocker for the rest of the pass: there is no multiplicity metadata and no attribute-declaration validation at all, so nothing checks an assignment against its declared feature. That gap must close before `ref` features can carry edges — which is the whole point of enabling sequences — so the interim guard buys visibility, not capability. The lexer is still 22 keywords and knows nothing of port/connect/constraint/assert/metadata/occurrence/item/objective/subject, and `skip_item` still discards silently; that is the next sprint and it is larger than this one."; }
    part psReviewGateR1 : TestResult { :>> id = "0d80005e-0814-605e-9b3e-00000030005e"; :>> outcome = VerdictKind::pass; :>> judgedAgainst = "e733115"; :>> judgedAt = "2026-08-14"; :>> judgedBy = "claudeOpus5"; }

    verification psCloseOutGate : Test { :>> id = "0d80005f-0814-605f-9b3e-00000030005f"; :>> title = "Sprint 267 closeOut gate (autonomous, D0049)"; :>> createdAt = "2026-08-14"; :>> createdBy = "claudeOpus5"; :>> method = VerificationMethod::inspect; :>> procedureText = "Autonomous closeOut (D0049). dcParserSequenceSupport and dcSequenceMultiplicityGuard both carry passing DoD TestResults; issue095 and issue101 resolve. Doc-sync: guards.md count 25 -> 26 and 6 -> 7 warning-only plus the catalogue entry, CLAUDE.md §5. clippy clean; 161 tests; validate + all 26 guards + check-engine green. No gate was bypassed at any point — two clippy pedantic failures were fixed rather than allowed through."; }
    part psCloseOutGateR1 : TestResult { :>> id = "0d800060-0814-6060-9b3e-000000300060"; :>> outcome = VerdictKind::pass; :>> judgedAgainst = "e733115"; :>> judgedAt = "2026-08-14"; :>> judgedBy = "claudeOpus5"; }

    verification psRetroGate : Test { :>> id = "0d800061-0814-6061-9b3e-000000300061"; :>> title = "Sprint 267 retro gate (autonomous, D0049)"; :>> createdAt = "2026-08-14"; :>> createdBy = "claudeOpus5"; :>> method = VerificationMethod::analyze; :>> procedureText = "Autonomous retro (D0049) under D0131's retroTrack. WELL: (1) the edge cases were written into the DoD BEFORE implementation and one of them found a real defect the feature introduced — the negative test is the whole reason issue101 exists rather than lying dormant until an authoring mistake in a single-valued attribute went unnoticed; (2) the new variant went into the TYPE, so the compiler enumerated the one consumer needing an update instead of leaving a latent string-handling bug; (3) the guard was built AST-first, and the text-scan alternative was actually tried and shown to return 4 all-prose hits, so the choice is evidenced rather than asserted. AVOIDABLE-ISSUE 1: I wrote a Python surgical patch whose anchor did not match (escaped backslashes in a Rust string literal) and it aborted mid-sprint — the second time this sitting that regex-patching Rust source failed where the Edit tool with exact text succeeded. NO NEW ITEM, reason stated: sprint 265's retro already recorded this exact tooling-choice slip with the same conclusion, and the fix is to reach for Edit on source files rather than to add a control; a guard cannot see how I edited a file. AVOIDABLE-ISSUE 2: three clippy pedantic failures (doc backticks twice, `use_self`, missing `# Errors`) cost three build cycles, all in code I had just written. NO NEW ITEM, reason stated: clippy IS the control and it worked; the cost was iteration, not risk, and the only alternative is running clippy before believing a change is done, which is already the declared reverify gate. Estimate 3 pts, delivered."; }
    part psRetroGateR1 : TestResult { :>> id = "0d800062-0814-6062-9b3e-000000300062"; :>> outcome = VerdictKind::pass; :>> judgedAgainst = "e733115"; :>> judgedAt = "2026-08-14"; :>> judgedBy = "claudeOpus5"; }
}
