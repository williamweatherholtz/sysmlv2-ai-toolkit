// ProjectDeliveryS456 — Sprint 456: every commit in a pushed range is compared, including the first - the monotonicity gate had a blind spot at the most common push shape (issue250, D0218). EXECUTE. 2 pts.
package ProjectDeliveryS456 {
    private import EngineElement::*;
    private import EngineWork::*;
    private import EngineVerification::*;
    private import EngineRelationships::*;

    #CharteredBy dependency from noFalseCleanRangeStory to d0218;

    part noFalseCleanRangeStory : Story {
        :>> id = "d98844d0-5624-4f19-b0bc-e55987df08aa";
        :>> title = "Sprint 456: the gate had never checked the first commit of a push (2 pts)";
        :>> createdAt = "2026-08-24"; :>> createdBy = "claudeFable5"; :>> kind = WorkKind::code; :>> priority = WorkPriority::p0; :>> owner = "claudeFable5"; :>> estimatedPoints = 2;
    }

    action def DeliveryRunS456 {
        action storyNoFalseCleanRange;
        verification storyNoFalseCleanRangeDoD : Test { :>> id = "f9dbf716-84af-472c-9193-ef841dd23416"; :>> method = VerificationMethod::test; :>> procedureText = "DELIVERED: dcNoFalseCleanRange (resolves issue250, HIGH) - and the charter it was built from was WRONG in a way worth recording. The chartered remedy was to make audit-adherence treat a range of fewer than two commits as a usage error, since printing 'nothing to compare. Clean.' is a false clean inside the gate built to prevent false cleans. That would have been a serious mistake: CI invokes --since github.event.before, so a SINGLE-COMMIT PUSH lists exactly one commit, and erroring would have failed CI on the most common push there is - the issue089/issue090 trap of a new hard check breaking every normal case on day one. THE REAL DEFECT, one layer beneath the symptom: the comparison seeded its baseline from shas[0] and then walked windows of two, so shas[0] was only ever a BASELINE and was NEVER ITSELF CHECKED. The first commit of every push escaped the gate, and a single-commit push escaped entirely - meaning a weakening introduced in the first commit of a push has been invisible since this control shipped, in the control built for exactly the issue236 self-modification class, blind at the most common push shape there is. THE FIX: the baseline is the PARENT of the range's first commit, resolved to a real SHA, so every commit in the range including the first is compared against what preceded it; a ROOT commit has no parent and that case is STATED in the output and uses the first commit as its own baseline rather than being silently guessed, because a baseline that quietly becomes itself would reproduce the very false-clean shape being fixed; and only a genuinely EMPTY range reports nothing to do. A display defect found in the same pass is fixed too - the parent was carried as the revision STRING X-caret and shortened to seven characters, which ate the caret and printed a commit as its own parent. VERIFIED: a rule weakened in a SINGLE commit with the hook bypassed returns exit 1 naming capabilityRootednessRule and its real parent SHA, where the identical probe previously reported Clean; real history PASSES at both --since HEAD~1 and --since HEAD~20, so the wider comparison introduces no false positive; 253 lib tests pass; clippy clean."; }
        part storyNoFalseCleanRangeDoDR1 : TestResult { :>> id = "edefa4a2-620b-4b0f-b082-dae90bf3747f"; :>> outcome = VerdictKind::pass; :>> judgedAgainst = "220b1ba5564b4f7128bddc0110634f7ae05b81d4"; :>> judgedAt = "2026-08-24"; :>> judgedBy = "claudeFable5"; }
    }

    verification noFalseCleanRangeRefineGate : Test { :>> id = "ef475035-83a4-4308-bd6d-86a9ef562e7a"; :>> title = "Sprint 456 refine gate (DoR)"; :>> createdAt = "2026-08-24"; :>> createdBy = "claudeFable5"; :>> method = VerificationMethod::inspect; :>> procedureText = "DoR. Closes the last chartered follow-on from the 2026-08-24 panel work, raised by sprint448's own retro after the negative-probe-range error recurred a third time. Scope: make a short range checkable rather than loud. 2 points."; }
    part noFalseCleanRangeRefineGateR1 : TestResult { :>> id = "069779fe-956d-44f7-947c-3f6afd4116ee"; :>> outcome = VerdictKind::pass; :>> judgedAgainst = "220b1ba5564b4f7128bddc0110634f7ae05b81d4"; :>> judgedAt = "2026-08-24"; :>> judgedBy = "claudeFable5"; }
    verification noFalseCleanRangeStandupGate : Test { :>> id = "e7d5bd06-e3b4-4ef0-831d-de7226560a7e"; :>> title = "Sprint 456 standup gate"; :>> createdAt = "2026-08-24"; :>> createdBy = "claudeFable5"; :>> method = VerificationMethod::inspect; :>> procedureText = "Approach: treat the symptom as a lead, not a spec. The chartered usage-error fix was checked against the CI invocation FIRST and rejected because it would fail every single-commit push; extending the baseline to the range's parent removes the symptom by making the case checkable, which is strictly more coverage rather than more noise. adherence.rs is on the frozen enforcement surface, so D0218 co-commits. No blockers."; }
    part noFalseCleanRangeStandupGateR1 : TestResult { :>> id = "3361d5e7-a303-42f5-aaaa-a3fa409ce52b"; :>> outcome = VerdictKind::pass; :>> judgedAgainst = "220b1ba5564b4f7128bddc0110634f7ae05b81d4"; :>> judgedAt = "2026-08-24"; :>> judgedBy = "claudeFable5"; }
    verification noFalseCleanRangeImplementGate : Test { :>> id = "9bb932e7-33ba-40e5-9d18-c1da3e3c939d"; :>> title = "Sprint 456 implement gate"; :>> createdAt = "2026-08-24"; :>> createdBy = "claudeFable5"; :>> method = VerificationMethod::test; :>> procedureText = "Verified by running the freshness-checked binary and by a probe built to be capable of failing: in a throwaway worktree, weakening a blocking rule to a warning in a SINGLE commit with the hook bypassed (--no-verify plus a PER-COMMAND core.hooksPath override, per issue249) returns exit 1 naming the rule and its real parent SHA; the same probe against the pre-fix binary reported Clean. Real history passes at --since HEAD~1 and --since HEAD~20. cargo clippy --workspace --all-targets -D warnings clean after three lint passes (map+unwrap_or_else, unnecessary boolean not, if-let/else to map_or_else); full lib suite 253 pass; validate 507 + all 49 guards + check-engine + rules green."; }
    part noFalseCleanRangeImplementGateR1 : TestResult { :>> id = "0132385e-0db3-45cd-a717-13c62c9dac38"; :>> outcome = VerdictKind::pass; :>> judgedAgainst = "220b1ba5564b4f7128bddc0110634f7ae05b81d4"; :>> judgedAt = "2026-08-24"; :>> judgedBy = "claudeFable5"; }
    verification noFalseCleanRangeReviewGate : Test { :>> id = "920541cf-ae1a-4bf8-ac3a-e9f83594ffcb"; :>> title = "Sprint 456 review gate — three passes per D0172"; :>> createdAt = "2026-08-24"; :>> createdBy = "claudeFable5"; :>> method = VerificationMethod::inspect; :>> procedureText = "PASS 1, CLAIMS: both probe results, the exit codes and the two PASS lines on real history are quoted read-backs; the pre-fix Clean is quoted from the probe I ran BEFORE changing the baseline, not inferred. PASS 2, BOUNDARY: (i) the range still cannot check a commit that is not in it - --since HEAD~50 on a deeper push under-scans, which is pre-existing and unchanged; (ii) the ROOT-commit branch cannot detect a weakening in the root commit itself, which is correct because there is nothing before it to weaken from, and it is stated in the output rather than left implicit; (iii) merges are still excluded by --no-merges, so a weakening introduced only by a merge resolution is out of scope and remains so. PASS 3, OWN DIFF: the charter I wrote in sprint448's retro was wrong, and it was wrong in the direction of MORE enforcement - I proposed making something loud where the honest fix was to make it checkable. Had I implemented the charter without checking the CI invocation first, I would have red-lit every single-commit push, which is the same class as issue248 shipped a few hours earlier. The lesson is narrow and real: a retro-authored charter is a LEAD, and the first step in acting on it is to verify the diagnosis, not the remedy. WHAT A REVIEWER SHOULD ATTACK: whether comparing the first commit against its parent can ever pull in a baseline that legitimately predates a signed Decision, producing a false weakening on the first commit of a push whose signing commit is just outside the range - I believe not, because the keystone check reads the CHILD commit's own tree for the marker, but it is the one interaction worth a second pair of eyes."; }
    part noFalseCleanRangeReviewGateR1 : TestResult { :>> id = "044230b6-f81d-456e-bafb-5c8dfce55449"; :>> outcome = VerdictKind::pass; :>> judgedAgainst = "220b1ba5564b4f7128bddc0110634f7ae05b81d4"; :>> judgedAt = "2026-08-24"; :>> judgedBy = "claudeFable5"; }
    verification noFalseCleanRangeCloseOutGate : Test { :>> id = "b84d68e8-0cb5-4fba-8a3b-d4bb2b21ca6b"; :>> title = "Sprint 456 closeOut gate (autonomous, D0049)"; :>> createdAt = "2026-08-24"; :>> createdBy = "claudeFable5"; :>> method = VerificationMethod::inspect; :>> procedureText = "Autonomous closeOut (D0049). issue250 resolved; every chartered follow-on from the panel slate is now closed; validate + all 49 guards + check-engine + rules green, and audit-adherence itself passes on real history at two range depths."; }
    part noFalseCleanRangeCloseOutGateR1 : TestResult { :>> id = "7123d83d-fb02-4b45-ac1f-3c9eca211314"; :>> outcome = VerdictKind::pass; :>> judgedAgainst = "220b1ba5564b4f7128bddc0110634f7ae05b81d4"; :>> judgedAt = "2026-08-24"; :>> judgedBy = "claudeFable5"; }
    verification noFalseCleanRangeRetroGate : Test { :>> id = "9b0e3d5f-f34a-430a-b1ab-c739b5677353"; :>> title = "Sprint 456 retro gate (autonomous, D0049)"; :>> createdAt = "2026-08-24"; :>> createdBy = "claudeFable5"; :>> method = VerificationMethod::analyze; :>> procedureText = "Autonomous retro (D0049). AVOIDABLE-ISSUE SCAN under rcRecurrence: (1) THE finding: my own retro-authored charter was wrong, and wrong toward more enforcement - it proposed erroring where the honest fix was to make the case checkable, and implementing it as written would have failed CI on every single-commit push. That is the second time in this run that a plausible hardening would have broken the common path (issue248 was the first), so the durable rule is that a charter is a LEAD and the first act is to verify the DIAGNOSIS against the real invocation, never to implement the proposed remedy. (2) The probe used the per-command git -c override this time rather than a worktree config write, applying issue249 the very next time it mattered. WELL: chasing the symptom one layer down turned a cosmetic wording complaint into the discovery that the gate had never checked the first commit of any push - a hole present since the control shipped that morning, in the control built specifically to catch silent disarmament. Estimate 2 pts, delivered 2."; }
    part noFalseCleanRangeRetroGateR1 : TestResult { :>> id = "53f0520e-df9f-468d-9d63-179e4ab25824"; :>> outcome = VerdictKind::pass; :>> judgedAgainst = "220b1ba5564b4f7128bddc0110634f7ae05b81d4"; :>> judgedAt = "2026-08-24"; :>> judgedBy = "claudeFable5"; }
}
