// ProjectDeliveryS485 — Sprint 485: arming is proven, not assumed. EXECUTE. 3 pts.
package ProjectDeliveryS485 {
    private import EngineElement::*;
    private import EngineWork::*;
    private import EngineVerification::*;
    private import EngineRelationships::*;

    #CharteredBy dependency from armingIsProvenNotAssumedStory to d0217;

    part armingIsProvenNotAssumedStory : Story {
        :>> id = "046405b4-3cfd-4e46-aac2-3d7ef2bf1ef8";
        :>> title = "Sprint 485: the write lock is proven to serialise, and seven more controls are named as unproven (3 pts)";
        :>> createdAt = "2026-08-29"; :>> createdBy = "claudeOpus5"; :>> kind = WorkKind::code; :>> priority = WorkPriority::p0; :>> owner = "claudeOpus5"; :>> estimatedPoints = 3;
    }

    action def DeliveryRunS485 {
        action storyArmingIsProvenNotAssumed;
        verification storyArmingIsProvenNotAssumedDoD : Test { :>> id = "d36d2d6e-ef04-4beb-add7-1b08b8d48681"; :>> method = VerificationMethod::test; :>> procedureText = "RESOLVES issue303 in part. The human asked for REAL assurance. Measured first: keel controls reports 9 declared controls, 1 ARMED, 8 not-machine-checkable, and yet uncoveredHazards [] - a clean bill resting on one probe. DO: (1) prove ctlWriteLock actually SERIALISES, the control guarding every model write, whose arming reason argued there was nothing to probe; (2) record the corrected reasoning in control-arming.toml WITHOUT deleting the wrong one, since a replaced justification teaches nobody; (3) name the seven controls still unproven and what would prove each. VERIFY: six real concurrent OS processes contend for the real lock via the sanctioned write path; landed == exited-zero, and any writer exiting 0 having lost its write fails the test.: DELIVERED BACKLOG ITEMS: <items>. <what done means, verified how>."; }
        // RAN: / RAN: cargo test --release -p keel-cli --test write_lock_actually_serialises -> 1 passed (6 concurrent processes, st001-st006 landed, landed==exited_zero); cargo clippy --workspace --all-targets -D warnings clean; cargo test --workspace --release 350+ passed 0 failed; keel guard 53 guards 0 FAIL; keel gate --fast 546 clean
        part storyArmingIsProvenNotAssumedDoDR1 : TestResult { :>> id = "be13c869-c932-42bf-8c8d-4eaad24e0caf"; :>> outcome = VerdictKind::pass; :>> judgedAgainst = "50fb6e7"; :>> judgedAt = "2026-08-29"; :>> judgedBy = "claudeOpus5"; }
    }

    verification armingIsProvenNotAssumedRefineGate : Test { :>> id = "a4d353eb-610b-48a3-869f-864261f9cac5"; :>> title = "Sprint 485 refine gate (DoR)"; :>> createdAt = "2026-08-29"; :>> createdBy = "claudeOpus5"; :>> method = VerificationMethod::inspect; :>> procedureText = "READY: the finding is measured, not suspected - keel controls, keel attestation and keel enforcement-report were all read before anything was written. issue303 records it with this story as resolver. Scope is bounded to ONE control proven plus the general finding named; probes for the other seven are explicitly NOT in this sprint, because a sprint that promised eight probes would have delivered reasoning about eight and evidence about none."; }
    verification armingIsProvenNotAssumedStandupGate : Test { :>> id = "00c4dd11-ac55-422f-8f0a-f288b0e77244"; :>> title = "Sprint 485 standup gate"; :>> createdAt = "2026-08-29"; :>> createdBy = "claudeOpus5"; :>> method = VerificationMethod::inspect; :>> procedureText = "No blocker. The measurement that motivated this was already in the tree and computable - nothing had to be built to find it, which is itself the finding: the numbers were available and nobody had read them together."; }
    verification armingIsProvenNotAssumedImplementGate : Test { :>> id = "a9a3d955-0e95-4db9-b6ae-716a678a6a38"; :>> title = "Sprint 485 implement gate"; :>> createdAt = "2026-08-29"; :>> createdBy = "claudeOpus5"; :>> method = VerificationMethod::test; :>> procedureText = "RAN: cargo test --release -p keel-cli --test write_lock_actually_serialises. RESULT: 6 concurrent processes, 6 distinct statements st001-st006 landed, 6 exited 0, landed == exited_zero. The lock HOLDS - including the id-minting read-modify-write, which is the exact race issue184 lost. THE TEST DISCRIMINATES rather than passing vacuously: had two writers clobbered each other, landed would be 4 against exited_zero 6 and the assertion fails; a lock that refused everything would trip the second assertion. A missing binary PANICS rather than skipping, so an unbuilt tree cannot look like a passing probe."; }
    verification armingIsProvenNotAssumedReviewGate : Test { :>> id = "161c6981-91a0-4bc0-a99f-993ea30f389d"; :>> title = "Sprint 485 review gate — three passes per D0172"; :>> createdAt = "2026-08-29"; :>> createdBy = "claudeOpus5"; :>> method = VerificationMethod::inspect; :>> procedureText = "THREE PASSES. (1) CORRECTNESS: the count is read from the TREE, not from the writers' exit codes - the whole point is that a writer's own report is not evidence about the tree, so counting reported successes would have re-made the error under test. (2) HONESTY OF THE CORRECTION: the superseded reason is quoted in full in the contract beside the new one. A justification silently replaced teaches nobody why it was wrong, and this one was wrong in an instructive way - it ruled out DISARMING and was read as ruling out FAILING. (3) SCOPE: one control is now proven and seven are named as unproven. The sprint does not claim the assurance problem is solved, and the closeOut gate states the residual in numbers rather than adjectives."; }
    verification armingIsProvenNotAssumedCloseOutGate : Test { :>> id = "fed523e7-fd41-4f04-9e05-6f4d2d370d62"; :>> title = "Sprint 485 closeOut gate (autonomous, D0049)"; :>> createdAt = "2026-08-29"; :>> createdBy = "claudeOpus5"; :>> method = VerificationMethod::inspect; :>> procedureText = "CLOSED WITH THE RESIDUAL IN NUMBERS. Before: 9 controls, 1 machine-checkably armed, 8 unproven. After: 1 armed by view-probe, 1 proven by test, 7 unproven. That is 2 of 9, not a solved problem, and issue303 stays OPEN because its resolver covers all eight. Also unresolved and NOT touched here: the launcher has never run - .keel/runs/ does not exist, so enforcement-report reports launcherFraction as unavailable and every Need about bounded process launching has zero evidence behind it. That is the largest single assurance gap in the model and it needs its own sprint."; }
    verification armingIsProvenNotAssumedRetroGate : Test { :>> id = "185fe9bc-1b58-4e52-90f9-5d872f98cc79"; :>> title = "Sprint 485 retro gate (autonomous, D0049)"; :>> createdAt = "2026-08-29"; :>> createdBy = "claudeOpus5"; :>> method = VerificationMethod::analyze; :>> procedureText = "FINDING, and it generalises past controls: eight classifications were made by asking whether a READ-ONLY VIEW could establish the property, and were then read as statements about whether the property was verifiable AT ALL. The constraint of the asking surface silently became a property of the subject. Nothing was dishonest - every reason is individually careful - and the aggregate still produced a clean bill of health resting on one probe. BECOMES TRACKED WORK: issue303, with a third arming state (proven-by-test) and a probe per control that admits one. SECOND FINDING: the numbers that revealed this needed no new code. keel controls, keel attestation and keel enforcement-report all existed and all said it; what was missing was anyone reading them TOGETHER. That is the same shape as the Need-set inversion earlier this session - rootedness held the honest number for months and nothing ranked it."; }
}
