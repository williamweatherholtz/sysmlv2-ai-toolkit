// ProjectDeliveryS530 — Sprint 530: hook hosting spike - where the agent cannot rewrite the hooks. EXECUTE (research). 2 pts.
package ProjectDeliveryS530 {
    private import EngineElement::*;
    private import EngineWork::*;
    private import EngineVerification::*;
    private import EngineRelationships::*;

    #CharteredBy dependency from hookHostingStory to d0296;

    part hookHostingStory : Story {
        :>> id = "369b6354-d82f-4d10-a707-929ddec32b32";
        :>> title = "Sprint 530: rank the hosts for the keel hook set by who can write them and what still silences them - six live runs, one Decision, four chartered items (2 pts)";
        :>> createdAt = "2026-09-03"; :>> createdBy = "claudeOpus5"; :>> kind = WorkKind::research; :>> priority = WorkPriority::p0; :>> owner = "claudeOpus5"; :>> estimatedPoints = 2;
    }

    action def DeliveryRunS530 {
        action storyHookHosting;
        verification storyHookHostingDoD : Test { :>> id = "3656da96-4987-4845-b559-227239b61d69"; :>> method = VerificationMethod::inspect; :>> procedureText = "DELIVERED BACKLOG ITEMS: dcHooksOutsideTheAgentsWritePath (st090/us090, pulled forward by st091). DONE: the four hosts ranked on evidence - repo settings (agent-writable, live reload, drift detected not prevented), plugin (dies to an on-disk disableAllHooks at launch), plugin plus ConfigChange deny (keeps the live session, cannot revert the file), launch-scope --settings override (beats the project's key), managed settings (forced, undeclarable by a project); D0296 records the layering and charters dcKeelPluginHostsTheHooks, dcHookConfigChangeRestoresTheFile, dcLaunchPinsHooksOn, dcStatusReportsHookHosts behind dcDriftGuardRefusesDisableAllHooks (issue365). VERIFY: the six runs are recorded with their prompts and log counts in D0296's context; each documented claim names its doc section via the guide agent."; }
        // RAN: six nested `claude -p` sessions, Claude Code 2.1.260, --plugin-dir scratch plugin; log counts 2/2, 3 then 0, 3 then 0 (no deny - payload has no content), 1 then 2/2 (deny), 0/2 (key at launch), 2/2 (--settings override); claude-code-guide agent x2 for settings precedence, merge, ConfigChange input, non-revert, plugin/marketplace scope, managed path
        part storyHookHostingDoDR1 : TestResult { :>> id = "617e5afd-9187-4887-ada7-7c1bdad749eb"; :>> outcome = VerdictKind::pass; :>> judgedAgainst = "7d174a6"; :>> judgedAt = "2026-09-03"; :>> judgedBy = "claudeOpus5"; }
    }

    verification hookHostingRefineGate : Test { :>> id = "2b2ea010-1331-46e6-8914-f3e5429396e1"; :>> title = "Sprint 530 refine gate (DoR)"; :>> createdAt = "2026-09-03"; :>> createdBy = "claudeOpus5"; :>> method = VerificationMethod::inspect; :>> procedureText = "READY once the question was a ranking with a stated axis - who can write the host, what still silences it - rather than 'should keel be an extension'. The axis came from the landscape spike's Kiro finding (D0282) and from the first check, which found keel had the same hole (issue365) before any host was compared."; }
    verification hookHostingStandupGate : Test { :>> id = "38922e79-d1eb-48f1-b10f-04fe9197b669"; :>> title = "Sprint 530 standup gate"; :>> createdAt = "2026-09-03"; :>> createdBy = "claudeOpus5"; :>> method = VerificationMethod::inspect; :>> procedureText = "ONE CHOICE: run the hosts live in a scratch project with a probe plugin rather than rank them from documentation alone. The documentation could not answer the two questions that decide the design - does a ConfigChange deny reach in time, and does a launch-scope key beat a project-scope one - and its answer to the first (no ordering guarantee) turned out too pessimistic: the deny works, the payload just carries no content."; }
    verification hookHostingImplementGate : Test { :>> id = "3ba2aea7-d4e7-48d0-95e7-76922b1d8ba1"; :>> title = "Sprint 530 implement gate"; :>> createdAt = "2026-09-03"; :>> createdBy = "claudeOpus5"; :>> method = VerificationMethod::test; :>> procedureText = "RAN: six runs, each changing one variable. Run 3's silent non-deny was the finding that shaped the handler (read file_path, never stdin); run 5 showed a deny alone is not enough (the file survives to the next launch, SessionStart cannot block); run 6 showed the cheapest strong rung is one the launcher already has a place for. Nested sessions needed CLAUDECODE unset and stdin from /dev/null."; }
    verification hookHostingReviewGate : Test { :>> id = "59c9a2cd-abf3-40a0-bd57-4fa0d60c5ec7"; :>> title = "Sprint 530 review gate — three passes per D0172"; :>> createdAt = "2026-09-03"; :>> createdBy = "claudeOpus5"; :>> method = VerificationMethod::inspect; :>> procedureText = "THREE PASSES. (1) IS EACH CLAIM RE-RUNNABLE: the prompts, flags and log counts are in D0296; a reader can rebuild the probe plugin from its description. (2) IS THE LIMIT STATED: yes - every rung below managed settings sits on a filesystem the agent's shell reaches; the layering removes the repository commit as a path and leaves the fire-ledger and CI as the detective backstop, which is what exists today. (3) IS THIS A FORK: no - two alternatives fall on facts, the third is a layering; recorded as a non-fork and auto-accepted under D0207, overridable by the human's quoted word."; }
    verification hookHostingCloseOutGate : Test { :>> id = "3e2744b5-9bf9-4303-8b9a-3db4b8ed608e"; :>> title = "Sprint 530 closeOut gate (autonomous, D0049)"; :>> createdAt = "2026-09-03"; :>> createdBy = "claudeOpus5"; :>> method = VerificationMethod::inspect; :>> procedureText = "CLOSED. The spike's output is d0296 and five ordered backlog items; the scratch plugin and logs were session-local and are not evidence - the Decision's recorded counts are."; }
    verification hookHostingRetroGate : Test { :>> id = "c3b3bd78-5e23-46f7-8e91-8b8ba9b97825"; :>> title = "Sprint 530 retro gate (autonomous, D0049)"; :>> createdAt = "2026-09-03"; :>> createdBy = "claudeOpus5"; :>> method = VerificationMethod::analyze; :>> procedureText = "no new item - already tracked: the finding that a control hosted in the controlled party's own file is a convention is issue365 and d0296's consequences; the methodological finding - documentation ranked the ConfigChange rung wrongly and a two-minute live run corrected it - is the same lesson d0295 recorded about a reproduction that fails to reproduce: run it, do not reason it. The one gap this sprint leaves unowned is deliberate: a SessionStart hook cannot block, so a host that is dead at launch is detected by keel status (dcStatusReportsHookHosts), never prevented; that is stated in d0296's rationale."; }
}
