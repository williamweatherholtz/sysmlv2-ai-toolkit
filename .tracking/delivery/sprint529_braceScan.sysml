// ProjectDeliveryS529 — Sprint 529: the write path scans blocks by structure. EXECUTE. 2 pts.
package ProjectDeliveryS529 {
    private import EngineElement::*;
    private import EngineWork::*;
    private import EngineVerification::*;
    private import EngineRelationships::*;

    #CharteredBy dependency from braceScanStory to d0295;

    part braceScanStory : Story {
        :>> id = "b2eb69d6-5071-476f-8d52-ec1a681b8f86";
        :>> title = "Sprint 529: one string-aware scanner - a result lands after a multi-line DoD closes, and a brace in a DoD's text never moves the next task (2 pts)";
        :>> createdAt = "2026-09-03"; :>> createdBy = "claudeOpus5"; :>> kind = WorkKind::code; :>> priority = WorkPriority::p0; :>> owner = "claudeOpus5"; :>> estimatedPoints = 2;
    }

    action def DeliveryRunS529 {
        action storyBraceScan;
        verification storyBraceScanDoD : Test { :>> id = "504a55f1-0474-44ee-b0d0-ee5837a4d718"; :>> method = VerificationMethod::test; :>> procedureText = "DELIVERED BACKLOG ITEMS: dcAppendResultFindsTheClosingBrace (resolves issue353 and issue354). DONE: braces_in ignores braces inside string literals and after a comment marker; block_close_line finds where a block returns to depth zero, one-liners closing on their own line; find_action_def_close and find_result_insertion both use it, so add-task and append-gate-result find the def's real close and append-result places a result after a multi-line DoD block rather than inside it. VERIFY: four unit tests; the live reproduction on this repository's backlog gone; the small-fixture misplacement (a task written at package level) reproduced before and gone after; 455 tests pass."; }
        // RAN: cargo test --lib write::tests 4/4 new; add-task probe on the real backlog with the brace text restored -> inside EngineBuild at 560/562; minimal fixture: zzB at package level before the fix, inside the def after; full suite 455/0; clippy clean
        part storyBraceScanDoDR1 : TestResult { :>> id = "72167ba1-bb2a-440b-af03-963ab726f822"; :>> outcome = VerdictKind::pass; :>> judgedAgainst = "7c34bb7"; :>> judgedAt = "2026-09-03"; :>> judgedBy = "claudeOpus5"; }
    }

    verification braceScanRefineGate : Test { :>> id = "604ac710-2d2b-4d3a-803a-e4ff9f6e435c"; :>> title = "Sprint 529 refine gate (DoR)"; :>> createdAt = "2026-09-03"; :>> createdBy = "claudeOpus5"; :>> method = VerificationMethod::inspect; :>> procedureText = "READY once the mechanism was established and not before: issue354's first description named the trigger (a brace in a string) and guessed the mechanism; a minimal reproduction FAILED to reproduce, which forced the real read - find_action_def_close counts characters - and exposed the second, worse symptom (silent misplacement). The refusal seen here and the misplacement seen in a fixture are the same defect on two file shapes."; }
    verification braceScanStandupGate : Test { :>> id = "97dfd75c-553e-4d85-a64f-e20f9120fc81"; :>> title = "Sprint 529 standup gate"; :>> createdAt = "2026-09-03"; :>> createdBy = "claudeOpus5"; :>> method = VerificationMethod::inspect; :>> procedureText = "ONE CHOICE: a shared scanner used by both call sites rather than a fix at each. The alternative of forbidding braces in DoD text would have been the same mistake as forbidding the word verification in retros - a text rule protecting a scanner that should have read structure. The issue's wrong first diagnosis is corrected in place, as its owner, rather than left standing beside the fix."; }
    verification braceScanImplementGate : Test { :>> id = "cb9a0e32-8b3f-4aa0-976e-4c375cc2ee82"; :>> title = "Sprint 529 implement gate"; :>> createdAt = "2026-09-03"; :>> createdBy = "claudeOpus5"; :>> method = VerificationMethod::test; :>> procedureText = "RAN: seven probe strings against a minimal backlog (none broke it - the first surprise); the exact DoD against the minimal backlog (no refusal, but the NEXT task landed at package level - the second surprise, and the real finding); the exact text restored in the real backlog (refusal reproduced); after the fix, the real probe lands inside the def and the fixture's second task lands inside its def. The first block_close_line had a one-liner bug (depth reaching zero on the opening line) caught by reasoning before the test ran; rewritten with an opened flag."; }
    verification braceScanReviewGate : Test { :>> id = "aa017c98-1780-4043-a080-6ac9696ff6d4"; :>> title = "Sprint 529 review gate — three passes per D0172"; :>> createdAt = "2026-09-03"; :>> createdBy = "claudeOpus5"; :>> method = VerificationMethod::inspect; :>> procedureText = "THREE PASSES. (1) DOES THE SCANNER HANDLE WHAT SANITIZE PRODUCES: sanitize_field turns double quotes into apostrophes, so a string literal never contains an interior double quote and the in_str toggle is sound for API-written text; a hand-authored file with an escaped quote is out of scope and said so here. (2) IS THE ONE-LINER PATH UNCHANGED: tested - a one-line DoD's result follows it directly. (3) IS THE WORSE SYMPTOM ARMED: the misplacement test asserts the second task's line precedes the def's close brace."; }
    verification braceScanCloseOutGate : Test { :>> id = "3d777c6e-12d3-4094-b3b4-13f30131d2bd"; :>> title = "Sprint 529 closeOut gate (autonomous, D0049)"; :>> createdAt = "2026-09-03"; :>> createdBy = "claudeOpus5"; :>> method = VerificationMethod::inspect; :>> procedureText = "CLOSED. issue353 and issue354 resolved; GH#48's reporter reads the tracked id on the closed issue."; }
    verification braceScanRetroGate : Test { :>> id = "a0695d60-13f8-4068-9720-9dc0ac4d65fa"; :>> title = "Sprint 529 retro gate (autonomous, D0049)"; :>> createdAt = "2026-09-03"; :>> createdBy = "claudeOpus5"; :>> method = VerificationMethod::analyze; :>> procedureText = "no new item - already tracked: the write path has other block-locating code (record_decision's rfind of the package close, the acceptance transform's) that still reads by character; each is safe today because a package close is the last brace in the file, and each should adopt braces_in when touched - that is recorded in d0295's consequences and needs no item until one of them is wrong (the retro-backlog fourth shape, d0294, refused this retro's first draft for writing D0295 in a form no lookup resolves - the guard is reading). The methodological finding - a minimal repro that fails to reproduce is information, not a dead end - is the D0157 read-back applied to defects."; }
}
