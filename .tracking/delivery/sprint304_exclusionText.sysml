// ProjectDeliveryS304 — Sprint 304: D0149 applied — the engine stops teaching an exclusion
// mechanism its own test disproved. EXECUTE. 5 pts.
package ProjectDeliveryS304 {
    private import EngineElement::*;
    private import EngineWork::*;
    private import EngineVerification::*;
    private import EngineRelationships::*;

    #CharteredBy dependency from exclusionTextStory to d0149;

    part exclusionTextStory : Story {
        :>> id = "0d8002b0-0814-62b0-9b3e-0000003002b0";
        :>> title = "Sprint 304: correct the claim-exclusion text across process, skill, requirement and core (5 pts)";
        :>> createdAt = "2026-08-15"; :>> createdBy = "claudeOpus5"; :>> kind = WorkKind::documentation; :>> priority = WorkPriority::p0; :>> owner = "claudeOpus5"; :>> estimatedPoints = 5;
    }

    action def DeliveryRunS304 {
        action storyExclusionText;
        verification storyExclusionTextDoD : Test { :>> id = "0d8002b1-0814-62b1-9b3e-0000003002b1"; :>> method = VerificationMethod::inspect; :>> procedureText = "Applies D0149 (accepted by wweatherholtz 2026-08-15, verbatim 'confirmed') and delivers dcCorrectExclusionText, resolving issue115. CORRECTED IN FOUR LIVE PLACES, each of which taught that two contributors claiming one item are excluded because the remote accepts exactly one push: the distributed-collaboration PROCESS actionText; its SKILL.md, where the claim now stops at the trunk rather than extending to a claimed item; the srDcWorkClaim REQUIREMENT statement and rationale; and a COMMENT in frozen `schema/core/work.sysml` above `part def Claim` — comment only, no type or attribute touched, and D0149 is the sign-off for this exact claim. Also corrected the use case in `.tracking/business` whose mainSuccess asserted the disproved scenario as expected behaviour. THE CORRECTION NARROWS RATHER THAN DISCARDS: a ref update IS a compare-and-swap and DOES give first-to-land-wins over the TRUNK; what it does not give is exclusion over a claimed ITEM, because per-actor claim files remove the contention and both claims land. Every corrected passage now also carries the two corollaries that each cost a wrong implementation — that 'whoever landed first' is not recoverable from merged history, and that expiry must remove a claim from contention rather than only from the top of the ranking. DELIBERATELY NOT TOUCHED: the dcWorkClaim DoD in the backlog and the sprint 300 record. Both are historical evidence of what was asked and what was found, D0149's accepted scope named the process, skill and requirement rather than the DoD, and rewriting a passed criterion after the fact would destroy the very record that proves the mechanism was disproved. CONSEQUENCE VERIFIED: with the requirement text now true of what was built, the `#Verify` edge to srDcWorkClaim that sprint 300 deliberately withheld is honest and authored — verification-trace drops from 2 warnings to 0, and sr_verified_pct rises 89% -> 91%. validate 329 clean; check-engine clean; 33 guards green; validate_schema 16/16 kernel-side; 213 tests."; }
        part storyExclusionTextDoDR1 : TestResult { :>> id = "0d8002b2-0814-62b2-9b3e-0000003002b2"; :>> outcome = VerdictKind::pass; :>> judgedAgainst = "01fce65"; :>> judgedAt = "2026-08-15"; :>> judgedBy = "claudeOpus5"; }
    }

    verification etRefineGate : Test { :>> id = "0d8002b3-0814-62b3-9b3e-0000003002b3"; :>> title = "Sprint 304 refine gate (DoR)"; :>> createdAt = "2026-08-15"; :>> createdBy = "claudeOpus5"; :>> method = VerificationMethod::inspect; :>> procedureText = "DoR. The #DependsOn edge to d0149 cleared when the Decision was accepted, exactly as issue112's machinery intends — the item returned to the frontier by itself with no edit. The human's 'confirmed' was recorded against D0149 SPECIFICALLY, because their earlier 'approved' had been asked about D0150 and an attestation may never be inferred from an adjacent one. estimatedPoints=5."; }
    part etRefineGateR1 : TestResult { :>> id = "0d8002b4-0814-62b4-9b3e-0000003002b4"; :>> outcome = VerdictKind::pass; :>> judgedAgainst = "01fce65"; :>> judgedAt = "2026-08-15"; :>> judgedBy = "claudeOpus5"; }

    verification etStandupGate : Test { :>> id = "0d8002b5-0814-62b5-9b3e-0000003002b5"; :>> title = "Sprint 304 standup gate"; :>> createdAt = "2026-08-15"; :>> createdBy = "claudeOpus5"; :>> method = VerificationMethod::inspect; :>> procedureText = "Approach: grep the whole doc surface for the disproved claim FIRST, then classify each hit as live text to correct or historical record to preserve, and only then edit. No blockers."; }
    part etStandupGateR1 : TestResult { :>> id = "0d8002b6-0814-62b6-9b3e-0000003002b6"; :>> outcome = VerdictKind::pass; :>> judgedAgainst = "01fce65"; :>> judgedAt = "2026-08-15"; :>> judgedBy = "claudeOpus5"; }

    verification etImplementGate : Test { :>> id = "0d8002b7-0814-62b7-9b3e-0000003002b7"; :>> title = "Sprint 304 implement gate"; :>> createdAt = "2026-08-15"; :>> createdBy = "claudeOpus5"; :>> method = VerificationMethod::test; :>> procedureText = "THE SWEEP FOUND MORE THAN THE DECISION NAMED. D0149's consequences listed the process, the SKILL.md and the requirement; grepping the corpus found the claim ALSO stated as fact in a comment above `part def Claim` in frozen `schema/core/work.sysml`, and asserted as expected behaviour in a use case's mainSuccess in `.tracking/business`. Correcting only what the Decision enumerated would have left the engine teaching the disproved mechanism in the one file a reader consults to understand what a Claim IS. The frozen-core edit is a COMMENT with no type, attribute or enum touched, kernel-checked 16/16 afterwards because touching that file at all warrants it. A THIRD THING THE GUARDS CAUGHT: the commit was refused because D0149 carried no `#ProspectiveChange`/`#SafetyChange` marker, and D0070 hard-locks every process-def edit — typos included — to a marked process-change Decision. The classification is PROSPECTIVE rather than safety: work chartered under the old text stays valid, because sprint 300 described the mechanism wrongly but BUILT what D0149 now describes, so nothing downstream needs reprocessing. That is a real classification the record was missing, not a formality. CLASSIFICATION WAS THE WHOLE JOB: four live passages corrected, two historical records deliberately left alone. The dcWorkClaim DoD passed with its original wording and the sprint 300 record documents the disproof — rewriting either would have erased the evidence that the mechanism was ever tested, which is precisely the trap of correcting history to match what you now believe."; }
    part etImplementGateR1 : TestResult { :>> id = "0d8002b8-0814-62b8-9b3e-0000003002b8"; :>> outcome = VerdictKind::pass; :>> judgedAgainst = "01fce65"; :>> judgedAt = "2026-08-15"; :>> judgedBy = "claudeOpus5"; }

    verification etReviewGate : Test { :>> id = "0d8002b9-0814-62b9-9b3e-0000003002b9"; :>> title = "Sprint 304 review gate"; :>> createdAt = "2026-08-15"; :>> createdBy = "claudeOpus5"; :>> method = VerificationMethod::inspect; :>> procedureText = "Reviewed. Each corrected passage states what is STILL TRUE before what was wrong — a ref update is a compare-and-swap, a rejected push does mean someone landed first, integrate before retrying — because a correction that reads as 'this was all wrong' would push a reader to distrust the integration model too, which is sound and verified. The withheld `#Verify` edge is the sprint's best evidence that the process worked as intended: sprint 300 declined to link srDcWorkClaim BECAUSE its statement was false, said so in the file, and the link became honest the moment the statement was corrected. The requirement was never quietly marked verified in the interim."; }
    part etReviewGateR1 : TestResult { :>> id = "0d8002ba-0814-62ba-9b3e-0000003002ba"; :>> outcome = VerdictKind::pass; :>> judgedAgainst = "01fce65"; :>> judgedAt = "2026-08-15"; :>> judgedBy = "claudeOpus5"; }

    verification etCloseOutGate : Test { :>> id = "0d8002bb-0814-62bb-9b3e-0000003002bb"; :>> title = "Sprint 304 closeOut gate (autonomous, D0049)"; :>> createdAt = "2026-08-15"; :>> createdBy = "claudeOpus5"; :>> method = VerificationMethod::inspect; :>> procedureText = "Autonomous closeOut (D0049); the process-definition change it applies carries wweatherholtz's explicit sign-off as D0149. issue115 resolves through dcCorrectExclusionText. validate 329 clean; check-engine clean; 33 guards green; validate_schema 16/16; 213 tests; verification-trace residual now zero. No gate bypassed."; }
    part etCloseOutGateR1 : TestResult { :>> id = "0d8002bc-0814-62bc-9b3e-0000003002bc"; :>> outcome = VerdictKind::pass; :>> judgedAgainst = "01fce65"; :>> judgedAt = "2026-08-15"; :>> judgedBy = "claudeOpus5"; }

    verification etRetroGate : Test { :>> id = "0d8002bd-0814-62bd-9b3e-0000003002bd"; :>> title = "Sprint 304 retro gate (autonomous, D0049)"; :>> createdAt = "2026-08-15"; :>> createdBy = "claudeOpus5"; :>> method = VerificationMethod::analyze; :>> procedureText = "Autonomous retro (D0049) under D0131's retroTrack. WELL: (1) the 'confirmed' was recorded against D0149 ALONE, and the earlier 'approved' against D0150 alone, rather than one being stretched to cover both — an attestation is the human's word about a specific claim, and the cost of asking twice is one message while the cost of inferring is a fabricated record; (2) the grep-first sweep found two passages the Decision itself had not enumerated, including the comment above `part def Claim` — the single place a reader looks to learn what a Claim is; (3) the historical records were left intact deliberately and the reason is written down, so a later reader does not 'helpfully' finish the job by rewriting the passed DoD. AVOIDABLE-ISSUE: none new. The one thing worth carrying forward is that this correction only became findable because sprint 300 tested with TWO REAL CLONES instead of asserting the property — the process text had said the same false thing since D0129 and every review had read past it. A claim about DISTRIBUTED behaviour cannot be reviewed into correctness; it has to be run. Estimate 5 pts, delivered."; }
    part etRetroGateR1 : TestResult { :>> id = "0d8002be-0814-62be-9b3e-0000003002be"; :>> outcome = VerdictKind::pass; :>> judgedAgainst = "01fce65"; :>> judgedAt = "2026-08-15"; :>> judgedBy = "claudeOpus5"; }
}
