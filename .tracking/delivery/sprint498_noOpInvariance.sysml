// ProjectDeliveryS498 — Sprint 498: no-op invariance becomes the standing control for regenerate-from-model writers. EXECUTE. 3 pts.
package ProjectDeliveryS498 {
    private import EngineElement::*;
    private import EngineWork::*;
    private import EngineVerification::*;
    private import EngineRelationships::*;

    #CharteredBy dependency from noOpInvarianceStory to d0047;

    part noOpInvarianceStory : Story {
        :>> id = "8f25f92c-b36d-4ee7-bfea-83e403a0eb3a";
        :>> title = "Sprint 498: the control the human asked for - a no-op must change nothing (3 pts)";
        :>> createdAt = "2026-08-30"; :>> createdBy = "claudeOpus5"; :>> kind = WorkKind::code; :>> priority = WorkPriority::p0; :>> owner = "claudeOpus5"; :>> estimatedPoints = 3;
    }

    action def DeliveryRunS498 {
        action storyNoOpInvariance;
        verification storyNoOpInvarianceDoD : Test { :>> id = "3b4ba2d4-235b-4887-bf46-0fae4b033b80"; :>> method = VerificationMethod::test; :>> procedureText = "Resolves issue310, from the human's question (st038): what prevents this in future. THE CONTROL is no-op invariance - a command told to make a change that is already TRUE must leave the file byte-identical. It needs no inventory of 'human-editable facts' and cannot be defeated by refactoring, because regeneration is lossless only when the model can represent every byte present. It would have failed on issue293 the day it shipped. DELIVERED: no_op_writes_lose_nothing.rs 7/7 plus a source-derived COVERAGE FLOOR. The floor EARNED its place immediately: it found engine-version.toml, which keel migrate re-stamped from a template - the same class, live, unreported - now fixed by restamp_pin rewriting only the engine line. It also forced adoption-profile.toml and keel-wrapper.toml to be named scaffold-only WITH the reason in the source. VERIFY: 7/7; clippy -D warnings clean; workspace suite 0 FAILED.: DELIVERED BACKLOG ITEMS: <items>. <what done means, verified how>."; }
        // RAN: // RAN: no_op_writes_lose_nothing 7/7; the coverage floor RED first and its finding was real (migrate's pin re-stamp); clippy -D warnings clean; workspace 0 FAILED
        part storyNoOpInvarianceDoDR1 : TestResult { :>> id = "66f4d2b3-8abb-4ca0-b443-c7ba879d681b"; :>> outcome = VerdictKind::pass; :>> judgedAgainst = "6b43586"; :>> judgedAt = "2026-08-30"; :>> judgedBy = "claudeOpus5"; }
    }

    verification noOpInvarianceRefineGate : Test { :>> id = "39a41880-cc3d-492c-89fd-41de59c97804"; :>> title = "Sprint 498 refine gate (DoR)"; :>> createdAt = "2026-08-30"; :>> createdBy = "claudeOpus5"; :>> method = VerificationMethod::inspect; :>> procedureText = "READY: the class was already characterised and tracked as issue310 from sprint497's retro, so this sprint chose a CONTROL for a stated class rather than inventing scope. The alternatives were weighed before building - see the review gate."; }
    verification noOpInvarianceStandupGate : Test { :>> id = "7e6a7cb9-6ceb-465d-8a54-a680c28f8aae"; :>> title = "Sprint 498 standup gate"; :>> createdAt = "2026-08-30"; :>> createdBy = "claudeOpus5"; :>> method = VerificationMethod::inspect; :>> procedureText = "No blocker. The design question was which invariant to hold. IDEMPOTENCE (run twice, same result) was rejected: a lossy regenerator is perfectly idempotent - it produces the same lossy output every time - so it would have passed issue293 cleanly. What catches the class is comparing against a HUMAN-AUTHORED baseline, which is exactly what a no-op invocation gives for free."; }
    verification noOpInvarianceImplementGate : Test { :>> id = "1a3b764d-16d5-4882-92ab-ae2258adf112"; :>> title = "Sprint 498 implement gate"; :>> createdAt = "2026-08-30"; :>> createdBy = "claudeOpus5"; :>> method = VerificationMethod::test; :>> procedureText = "RAN: cargo test --test no_op_writes_lose_nothing -> 7/7. The floor was RED first and its failure was a real finding, not a fixture problem: it named engine-version.toml, adoption-profile.toml and keel-wrapper.toml, of which the first is a genuine live instance of the class (migrate.rs rewrote the pin file from a template). Fixed via restamp_pin; the case that holds it (a hand-added comment surviving the re-stamp) fails against the old code. clippy -D warnings clean - two lints fixed by EXTRACTING the helper and repositioning it, never by suppression, and the second lint was itself caused by my insertion landing between #[must_use] and its function, which the linter caught. cargo test --workspace --release -> 0 FAILED."; }
    verification noOpInvarianceReviewGate : Test { :>> id = "2071ae4e-4657-48a8-bc1e-8563c5211ddb"; :>> title = "Sprint 498 review gate — three passes per D0172"; :>> createdAt = "2026-08-30"; :>> createdBy = "claudeOpus5"; :>> method = VerificationMethod::inspect; :>> procedureText = "THREE PASSES, using the control-propriety lenses (D0257). (1) OVERFIT: the invariant is a property of the WRITE, not a pattern from the issue293 instance - it holds any command against its own no-op, so it generalises to writers not yet written. (2) CLASS COVERAGE, honestly bounded: the case table is ENUMERATED, not derived, so a new writer is covered only when a case is added; the floor narrows that by failing when the source grows a whole-file write to a tracked surface no case exercises, which is a mechanical floor and NOT a complete fence - a write through a computed path evades it, and that residual is stated in the file header rather than implied. (3) CIRCUMVENTABILITY: the invariant cannot be satisfied by a lossy writer, which is the property idempotence lacked; the floor, being source-text based, can be evaded by refactoring, so the two are deliberately layered rather than presented as one guarantee."; }
    verification noOpInvarianceCloseOutGate : Test { :>> id = "b0a23bb7-ddfe-4f87-a5c3-6b22527a0019"; :>> title = "Sprint 498 closeOut gate (autonomous, D0049)"; :>> createdAt = "2026-08-30"; :>> createdBy = "claudeOpus5"; :>> method = VerificationMethod::inspect; :>> procedureText = "CLOSED. The backlog task dcNoOpInvarianceControl is delivered by this sprint and issue310 resolves. Two live instances of the class existed at the start of this sprint (activation, already fixed in 497; migrate's pin re-stamp, found and fixed here) and the control now holds both, plus the .claude preservation claim that had been asserted in a doc comment for months without a test."; }
    verification noOpInvarianceRetroGate : Test { :>> id = "740dd1b7-e91c-4aea-8493-10684b3082c3"; :>> title = "Sprint 498 retro gate (autonomous, D0049)"; :>> createdAt = "2026-08-30"; :>> createdBy = "claudeOpus5"; :>> method = VerificationMethod::analyze; :>> procedureText = "FINDING: the control found a second live instance WITHIN MINUTES of existing, which is the strongest available evidence that the class was real and that I had not enumerated it correctly by inspection - I had named sync-claude as the likely next candidate and it turned out to be fine, while migrate, which I never considered, was defective. A control that only confirms what its author already suspected is a formality; this one contradicted me. SECOND FINDING, about the residual: the coverage floor is source-text based and a computed path evades it. That is written in the file header as a stated residual rather than filed as new work, because the honest next step is not a cleverer parser but fewer whole-file writers - and that is a refactor with no defect behind it yet, which D0047 does not license."; }
}
