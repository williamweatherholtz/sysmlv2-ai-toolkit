// ProjectDeliveryS315 — Sprint 315: the console's navigation is COMPUTED. The twelve hardcoded tabs
// are gone. EXECUTE. 8 pts.
package ProjectDeliveryS315 {
    private import EngineElement::*;
    private import EngineWork::*;
    private import EngineVerification::*;
    private import EngineRelationships::*;

    #CharteredBy dependency from derivedNavStory to d0154;

    part derivedNavStory : Story {
        :>> id = "0d800360-0814-6360-9b3e-000000300360";
        :>> title = "Sprint 315: derived console navigation — surfaces from the declared registry (8 pts)";
        :>> createdAt = "2026-08-16"; :>> createdBy = "claudeOpus5"; :>> kind = WorkKind::code; :>> priority = WorkPriority::p0; :>> owner = "claudeOpus5"; :>> estimatedPoints = 8;
    }

    action def DeliveryRunS315 {
        action storyDerivedNav;
        verification storyDerivedNavDoD : Test { :>> id = "0d800361-0814-6361-9b3e-000000300361"; :>> method = VerificationMethod::demo; :>> procedureText = "THIS IS THE FIRST CONSOLE CODE THE REDESIGN HAS CHANGED — the previous sprint landed D0152 and six requirements and built nothing, which the human named directly: 'is this delivered? seems not really'. It was not. DELIVERED NOW: `const TABS=[...]` is DELETED from console.html; navigation is fetched from a new `/api/surfaces`, which computes it from the declared Viewpoint registry (view.rs `surfaces_json`). Applies D0154, whose `surface` attribute made this possible. VERIFIED LIVE against a running server, both halves of the requirement: (1) the served console contains ZERO occurrences of a literal tab list and three references to /api/surfaces; (2) THE THRESHOLD THAT MATTERS — declaring a 33rd viewpoint on an existing surface left the top-level count at 6 while that surface's contents grew 4 to 5, which is srConsoleArrivalBounded's exact delta test, and it is a delta rather than a cap precisely so nesting cannot game it; (3) a viewpoint declaring NO surface appears under `unsurfaced` and is never filed under a default (N-C2 — an absent grouping is a gap the reader must see). ALSO POPULATED: `surface` on all 28 pre-existing viewpoints, grouped into 6 surfaces — act, work, assurance, architecture, record, explore — chosen so each answers a different question a supervisor has. clippy clean; 221 tests; validate 342 clean; check-engine clean; 33 guards green."; }
        part storyDerivedNavDoDR1 : TestResult { :>> id = "0d800362-0814-6362-9b3e-000000300362"; :>> outcome = VerdictKind::pass; :>> judgedAgainst = "3cc5f8c"; :>> judgedAt = "2026-08-16"; :>> judgedBy = "claudeOpus5"; }
    }

    verification dnRefineGate : Test { :>> id = "0d800363-0814-6363-9b3e-000000300363"; :>> title = "Sprint 315 refine gate (DoR)"; :>> createdAt = "2026-08-16"; :>> createdBy = "claudeOpus5"; :>> method = VerificationMethod::inspect; :>> procedureText = "DoR. THE BUILD WAS STOPPED ONCE BEFORE IT STARTED, and that is the reason this sprint exists at all: the consumer check (dorConsumer, D0144) measured what generating navigation from the registry would actually produce — 28 viewpoints, therefore 28 top-level entries, worse than the 12 being replaced — and the fallback of grouping by `audience` produced 20 groups because that field is free prose ordered inconsistently. The requirement could not be built as written, D0154 was proposed and accepted, and only then did the build begin. srConsoleNavigationDerived was chosen first among the six because every other surface renders through it; building any of them first would have hardcoded what must be derived, which is precisely how twelve tabs happened. estimatedPoints=8."; }
    part dnRefineGateR1 : TestResult { :>> id = "0d800364-0814-6364-9b3e-000000300364"; :>> outcome = VerdictKind::pass; :>> judgedAgainst = "3cc5f8c"; :>> judgedAt = "2026-08-16"; :>> judgedBy = "claudeOpus5"; }

    verification dnStandupGate : Test { :>> id = "0d800365-0814-6365-9b3e-000000300365"; :>> title = "Sprint 315 standup gate"; :>> createdAt = "2026-08-16"; :>> createdBy = "claudeOpus5"; :>> method = VerificationMethod::inspect; :>> procedureText = "Approach: compute the navigation server-side so the console asks the MODEL what its surfaces are; dispatch each viewpoint on its DECLARED renderer rather than on a title map, so the binding also comes from the model; verify against a running server rather than by reading the diff. No blockers."; }
    part dnStandupGateR1 : TestResult { :>> id = "0d800366-0814-6366-9b3e-000000300366"; :>> outcome = VerdictKind::pass; :>> judgedAgainst = "3cc5f8c"; :>> judgedAt = "2026-08-16"; :>> judgedBy = "claudeOpus5"; }

    verification dnImplementGate : Test { :>> id = "0d800367-0814-6367-9b3e-000000300367"; :>> title = "Sprint 315 implement gate"; :>> createdAt = "2026-08-16"; :>> createdBy = "claudeOpus5"; :>> method = VerificationMethod::test; :>> procedureText = "A SECOND GAP APPEARED WHILE POPULATING: the registry had NO viewpoint for any obligation class, so the `act` surface — the whole point of N-C1 — would have been empty. Four were declared (acceptances-pending, findings-awaiting-disposition, authority-queue, sitting-review-due), which is UC-C6 working as designed: a surface is added by DECLARING a viewpoint, not by editing the console. Declaring them immediately failed the viewpoint-renderer guard, because `authority-queue` is a real command that had never been added to the guard's known-command list — a genuine defect found only because a declaration finally named it. THE OWNERSHIP GUARD BLOCKED THE FIRST COMMIT, correctly: adding `surface` to 28 viewpoints owned by wweatherholtz is a non-owner editing their fields (D0108). Superseding 28 items to add one attribute would have doubled the registry, and asking the owner to hand-edit 28 items is not a process. D0067's migration path is the third and right one — a committed transform under `.engine/tools/migrations/` that a reviewer can read, which is the ONLY way the ownership exemption can be obtained (it cannot be claimed). The transform is idempotent (a re-run adds 0), reconciles control totals (32 viewpoints before and after, refusing outright if the count changes, since it may only ADD attributes), and REPORTS any unmapped viewpoint rather than guessing a surface for it. VERIFIED AGAINST A RUNNING SERVER, not by reading the diff, and the distinction mattered: the first check reported the literal tab list still present, because the binary embeds console.html and the rebuild had failed silently — `keel.exe` was locked by a serve process left running from the previous test, and cargo reported 'Access is denied' where a reader skimming for errors would see none. The stale binary served the old console and the check would have PASSED a change that had not shipped. Killed the process, rebuilt, re-verified. That is the session's recurring shape once more: a confident wrong answer, caught only by comparing against a number already known."; }
    part dnImplementGateR1 : TestResult { :>> id = "0d800368-0814-6368-9b3e-000000300368"; :>> outcome = VerdictKind::pass; :>> judgedAgainst = "3cc5f8c"; :>> judgedAt = "2026-08-16"; :>> judgedBy = "claudeOpus5"; }

    verification dnReviewGate : Test { :>> id = "0d800369-0814-6369-9b3e-000000300369"; :>> title = "Sprint 315 review gate"; :>> createdAt = "2026-08-16"; :>> createdBy = "claudeOpus5"; :>> method = VerificationMethod::inspect; :>> procedureText = "Reviewed. THE DISPATCH BINDING COMES FROM THE MODEL TOO, which is the part most likely to be quietly re-hardcoded later: a viewpoint's panel is chosen from the command named in its DECLARED `renderer`, not from a title-to-panel map, so a viewpoint pointing at an existing panel gets it and one that does not shows the exact command to run instead of a blank area. Settings is deliberately NOT a surface and sits outside the derived nav as a single affordance — it is app configuration rather than a lens on the model, and calling it a surface would have been the first crack in the same wall. WHAT IS NOT YET DONE, stated plainly: this satisfies srConsoleNavigationDerived and srConsoleArrivalBounded. The other four requirements — explicit view status, resolved model scope, project rebind, obligations present on arrival — are untouched. The `act` surface now EXISTS and lists its four viewpoints, but arriving at the console does not yet put them in front of you, so N-C1 is declared and not delivered."; }
    part dnReviewGateR1 : TestResult { :>> id = "0d80036a-0814-636a-9b3e-00000030036a"; :>> outcome = VerdictKind::pass; :>> judgedAgainst = "3cc5f8c"; :>> judgedAt = "2026-08-16"; :>> judgedBy = "claudeOpus5"; }

    verification dnCloseOutGate : Test { :>> id = "0d80036b-0814-636b-9b3e-00000030036b"; :>> title = "Sprint 315 closeOut gate (autonomous, D0049)"; :>> createdAt = "2026-08-16"; :>> createdBy = "claudeOpus5"; :>> method = VerificationMethod::inspect; :>> procedureText = "Autonomous closeOut (D0049); the frozen-core attribute it applies carries wweatherholtz's explicit sign-off as D0154, kernel-checked 16/16 after a stale-JVM sweep. Two of six console requirements are now built; four remain. clippy clean; 221 tests; validate 342 clean; check-engine clean; 33 guards green. Serve processes stopped after testing."; }
    part dnCloseOutGateR1 : TestResult { :>> id = "0d80036c-0814-636c-9b3e-00000030036c"; :>> outcome = VerdictKind::pass; :>> judgedAgainst = "3cc5f8c"; :>> judgedAt = "2026-08-16"; :>> judgedBy = "claudeOpus5"; }

    verification dnRetroGate : Test { :>> id = "0d80036d-0814-636d-9b3e-00000030036d"; :>> title = "Sprint 315 retro gate (autonomous, D0049)"; :>> createdAt = "2026-08-16"; :>> createdBy = "claudeOpus5"; :>> method = VerificationMethod::analyze; :>> procedureText = "Autonomous retro (D0049) under D0131's retroTrack. WELL: (1) the human's 'is this delivered? seems not really' was correct and checking it took one command — no code had been touched by the console work at all, and saying so plainly was better than defending the sprint records that had called it delivered; (2) the build STOPPED when the consumer check showed the requirement was unbuildable as written, rather than shipping the half that worked and leaving a worse console; (3) both halves of the threshold were verified against a running server with a real probe viewpoint, including the unsurfaced path. AVOIDABLE-ISSUE: I verified the served console BEFORE noticing the rebuild had failed. cargo printed 'Access is denied' because a serve process from an earlier test still held keel.exe, and the running server then served the OLD embedded console — so the check found the literal tab list still present and, had the result gone the other way, would have passed a change that never shipped. The tell to keep, and it is the same one this session keeps producing: a verification that reads a SERVED artifact must first confirm the artifact was rebuilt, because a stale binary answers confidently. NO NEW ITEM: the concrete control already exists in the form of checking the build's exit rather than skimming its output, which the D0151 clause covers. Estimate 8 pts, delivered."; }
    part dnRetroGateR1 : TestResult { :>> id = "0d80036e-0814-636e-9b3e-00000030036e"; :>> outcome = VerdictKind::pass; :>> judgedAgainst = "3cc5f8c"; :>> judgedAt = "2026-08-16"; :>> judgedBy = "claudeOpus5"; }
}
