// ProjectDeliveryS321 — Sprint 321: "single-user" was one phrase doing three jobs. CHANGE (§3a). 2 pts.
package ProjectDeliveryS321 {
    private import EngineElement::*;
    private import EngineWork::*;
    private import EngineVerification::*;
    private import EngineRelationships::*;

    #CharteredBy dependency from machineScopeStory to d0158;

    part machineScopeStory : Story {
        :>> id = "0d8003c0-0814-63c0-9b3e-0000003003c0";
        :>> title = "Sprint 321: D0158 — one actor per machine; the console is what is local-only (2 pts)";
        :>> createdAt = "2026-08-17"; :>> createdBy = "claudeOpus5"; :>> kind = WorkKind::decision; :>> priority = WorkPriority::p0; :>> owner = "claudeOpus5"; :>> estimatedPoints = 2;
    }

    action def DeliveryRunS321 {
        action storyMachineScope;
        verification storyMachineScopeDoD : Test { :>> id = "0d8003c1-0814-63c1-9b3e-0000003003c1"; :>> method = VerificationMethod::inspect; :>> procedureText = "Resolves issue137. D0158 supersedes D0115's clause-1 PHRASING and splits one overloaded phrase into the three boundaries it was doing duty for: IDENTITY (one bound actor per machine, never inferred, never defaulted), COLLABORATION (by git, merge-only, ownership by createdBy, contention adjudicated by a human — multiple contributors are IN scope and already implemented), and THE CONSOLE (local-only, unauthenticated, no server-side per-user state). D0115's substantive scope decisions are untouched: N-7, N-9, N-11 and N-14 stay superseded and no auth work is revived. SWEEP DONE AND REPORTED: every occurrence of the old phrase was inspected, and exactly ONE live claim asserted it — a comment in requirements/keel-viewer.sysml, authored by me, corrected in the same commit. The others are history and correct as history: N-7's own superseded statement, three sprint records, and a comment describing what D0115 did. The docs' 'localhost' claims in README and CHANGELOG are accurate and were left alone. Also recorded: D0157's deferral, with the human as its trigger — the weakness that Decision named in its own rationale. validate 349 clean; check-engine clean; 34 guards ALL PASS."; }
        part storyMachineScopeDoDR1 : TestResult { :>> id = "0d8003c2-0814-63c2-9b3e-0000003003c2"; :>> outcome = VerdictKind::pass; :>> judgedAgainst = "32a0a31"; :>> judgedAt = "2026-08-17"; :>> judgedBy = "claudeOpus5"; }
    }

    verification msRefineGate : Test { :>> id = "0d8003c3-0814-63c3-9b3e-0000003003c3"; :>> title = "Sprint 321 refine gate (DoR)"; :>> createdAt = "2026-08-17"; :>> createdBy = "claudeOpus5"; :>> method = VerificationMethod::inspect; :>> procedureText = "DoR. Taken without a round trip because the CORRECTED BOUNDARY IS THE HUMAN'S OWN SENTENCE, given verbatim on 2026-08-17: 'it's not single user altogether, it's a single user per machine - this service app is local only at the moment.' My contribution is splitting it into three scopes and naming which shipped artifacts implement each; the scope judgment itself is theirs, which is why this is an accepted Decision rather than a proposed one. Their standing instruction in the same exchange — 'Keep going until you are done or reach a legitimate blocker (not just approval)' — is what makes proceeding correct rather than presumptuous. estimatedPoints=2."; }
    part msRefineGateR1 : TestResult { :>> id = "0d8003c4-0814-63c4-9b3e-0000003003c4"; :>> outcome = VerdictKind::pass; :>> judgedAgainst = "32a0a31"; :>> judgedAt = "2026-08-17"; :>> judgedBy = "claudeOpus5"; }

    verification msStandupGate : Test { :>> id = "0d8003c5-0814-63c5-9b3e-0000003003c5"; :>> title = "Sprint 321 standup gate"; :>> createdAt = "2026-08-17"; :>> createdBy = "claudeOpus5"; :>> method = VerificationMethod::inspect; :>> procedureText = "Approach: supersede the phrase rather than edit D0115, whose text carries an attestation; grep the whole corpus for the phrase and CLASSIFY each hit as live or historical rather than fixing everything that matches, because rewriting history to agree with a correction is how evidence gets lost. Record D0157's trigger as an ADDED attestation, not by editing accepted text. No blockers."; }
    part msStandupGateR1 : TestResult { :>> id = "0d8003c6-0814-63c6-9b3e-0000003003c6"; :>> outcome = VerdictKind::pass; :>> judgedAgainst = "32a0a31"; :>> judgedAt = "2026-08-17"; :>> judgedBy = "claudeOpus5"; }

    verification msImplementGate : Test { :>> id = "0d8003c7-0814-63c7-9b3e-0000003003c7"; :>> title = "Sprint 321 implement gate"; :>> createdAt = "2026-08-17"; :>> createdBy = "claudeOpus5"; :>> method = VerificationMethod::inspect; :>> procedureText = "THE THREE-WAY SPLIT IS THE FIX, NOT BETTER WORDING, and the reason is that 'single-user' can only be read wrongly: as 'one human total' (false — D0108 exists for the plural case), as 'no authentication' (true, but only of the console), or as 'no concurrent editing' (false — per-actor claim files exist precisely so concurrent editing works). One phrase, three meanings, and issue132 is what happens when a reader picks the wrong one: N-8's statement was judged against 'single-user' when the accurate boundary was 'no accounts, no server-side session', and all four resolutions I proposed were framed around the wrong scope. Splitting them forces a future scope claim to say WHICH it constrains, which is the property that would have prevented the original defect."; }
    part msImplementGateR1 : TestResult { :>> id = "0d8003c8-0814-63c8-9b3e-0000003003c8"; :>> outcome = VerdictKind::pass; :>> judgedAgainst = "32a0a31"; :>> judgedAt = "2026-08-17"; :>> judgedBy = "claudeOpus5"; }

    verification msReviewGate : Test { :>> id = "0d8003c9-0814-63c9-9b3e-0000003003c9"; :>> title = "Sprint 321 review gate"; :>> createdAt = "2026-08-17"; :>> createdBy = "claudeOpus5"; :>> method = VerificationMethod::inspect; :>> procedureText = "Reviewed. THE COST IS STATED IN THE DECISION RATHER THAN HIDDEN: a reader who finds only D0115 is still misled, because the correction lives in a second Decision. That is why the supersession is a TYPED EDGE the computed views follow rather than a note in prose — `decisions-active-and-superseded` and the governing-version computations see it, so a reader arriving through any computed lens gets both. A note would have been cheaper and would have failed exactly the reader it was written for. What I deliberately did NOT do: revive anything. D0157 holds the hosted direction, deferred, with the human as its trigger, and this Decision says so explicitly so that 'multiple contributors are in scope' cannot be read as 'multi-user access is in scope'."; }
    part msReviewGateR1 : TestResult { :>> id = "0d8003ca-0814-63ca-9b3e-0000003003ca"; :>> outcome = VerdictKind::pass; :>> judgedAgainst = "32a0a31"; :>> judgedAt = "2026-08-17"; :>> judgedBy = "claudeOpus5"; }

    verification msCloseOutGate : Test { :>> id = "0d8003cb-0814-63cb-9b3e-0000003003cb"; :>> title = "Sprint 321 closeOut gate (autonomous, D0049)"; :>> createdAt = "2026-08-17"; :>> createdBy = "claudeOpus5"; :>> method = VerificationMethod::inspect; :>> procedureText = "Autonomous closeOut (D0049). issue137 resolved via #Resolves from d0158. issue138 remains open with dcUnitPortabilityScope ready, and investigating it surfaced a NEW defect recorded separately (issue139): the viewpoint-renderer guard and concern-coverage read one hardcoded filename while the model-driven paths see every Viewpoint, so a viewpoint declared elsewhere escapes the hard guard entirely. Proven with a probe file, not inferred: 32 scanned, 0 violations, and its deliberately-bogus renderer passed unchecked. The probe was deleted. validate 349 clean; check-engine clean; 34 guards ALL PASS. No code changed this sprint."; }
    part msCloseOutGateR1 : TestResult { :>> id = "0d8003cc-0814-63cc-9b3e-0000003003cc"; :>> outcome = VerdictKind::pass; :>> judgedAgainst = "32a0a31"; :>> judgedAt = "2026-08-17"; :>> judgedBy = "claudeOpus5"; }

    verification msRetroGate : Test { :>> id = "0d8003cd-0814-63cd-9b3e-0000003003cd"; :>> title = "Sprint 321 retro gate (autonomous, D0049)"; :>> createdAt = "2026-08-17"; :>> createdBy = "claudeOpus5"; :>> method = VerificationMethod::analyze; :>> procedureText = "Autonomous retro (D0049) under D0131's retroTrack. WELL: (1) the sweep CLASSIFIED its hits instead of fixing them — one live claim corrected, six left as history — because a corpus-wide search-and-replace to make history agree with a correction destroys the evidence the correction was derived from; (2) D0157's missing trigger was closed by ADDING an attestation rather than editing accepted text, which is the same discipline that made N-8 a supersession; (3) the viewpoint defect was PROVEN with a probe file and the probe was deleted, rather than reasoned about from reading the source — the guard reported 32 scanned and 0 violations with a bogus renderer sitting in the tree, which reading alone would have left as a suspicion. AVOIDABLE-ISSUE: none this sprint. NOTE ON THE NEW STANDING INSTRUCTION, recorded because it changes how I run and a successor needs it: the human asked not to be stopped for approval, only for a legitimate blocker. Applied here by taking a Decision whose content was their own sentence, and it does NOT relax the confirmation rule — a method=confirmation result still needs their explicit word on that specific claim, and both attestations this sprint quote it verbatim. Estimate 2 pts, delivered."; }
    part msRetroGateR1 : TestResult { :>> id = "0d8003ce-0814-63ce-9b3e-0000003003ce"; :>> outcome = VerdictKind::pass; :>> judgedAgainst = "32a0a31"; :>> judgedAt = "2026-08-17"; :>> judgedBy = "claudeOpus5"; }
}
