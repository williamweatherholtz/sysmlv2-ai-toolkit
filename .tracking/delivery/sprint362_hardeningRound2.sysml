// ProjectDeliveryS362 — Sprint 362: hardening round 2. The CLI stops answering for names that do not
// exist; the HTTP surface declares itself. Both findings cleared. EXECUTE. 5 pts.
package ProjectDeliveryS362 {
    private import EngineElement::*;
    private import EngineWork::*;
    private import EngineVerification::*;
    private import EngineRelationships::*;

    #CharteredBy dependency from hardening2Story to d0169;

    part hardening2Story : Story {
        :>> id = "0d800650-0814-6650-9b3e-000000300650";
        :>> title = "Sprint 362: hardening round 2 — an unknown name is a failure, and the HTTP surface declares itself (5 pts)";
        :>> createdAt = "2026-08-20"; :>> createdBy = "claudeOpus5"; :>> kind = WorkKind::code; :>> priority = WorkPriority::p0; :>> owner = "claudeOpus5"; :>> estimatedPoints = 5;
    }

    action def DeliveryRunS362 {
        action storyHardening2;
        verification storyHardening2DoD : Test { :>> id = "0d800651-0814-6651-9b3e-000000300651"; :>> method = VerificationMethod::test; :>> procedureText = "DELIVERED BACKLOG ITEMS: dcUnknownNameFails, dcAdvertiseApiSurface. Clears issue177 and issue178 under D0169. ISSUE177: six name-taking read commands returned EXIT 0 for a name that does not exist - `keel trace .` answered `{upstream: [], downstream: []}`, and `keel governing-version .` reported a process AND a process_def for it, the most confidently wrong of the six. D0093 makes the CLI the automation substrate, so a script reads an empty relation set as `no relations` rather than `no such item` - the reassuring wrong answer. Now all six exit 1 naming the item; verified BOTH ways, six failures and three real names still resolving. ISSUE178: 46 registered routes, 3 declared by nothing - /api/projects, /api/scope, and /api/project which is a POST, so an undeclared WRITE path existed outside the contract a consumer uses to discover what it may change. All three advertised; unaccounted is now 0. A FOURTH LENS was added (`apiSurface`) rather than just fixing the three, because this question was the FIFTH hand probe of the session to produce a wrong number - one pass after the instrument was built to stop exactly that. validate 394 clean; check-engine clean; 38 guards ALL PASS; 193 tests; clippy clean."; }
        part storyHardening2DoDR1 : TestResult { :>> id = "0d800652-0814-6652-9b3e-000000300652"; :>> outcome = VerdictKind::pass; :>> judgedAgainst = "376fde6"; :>> judgedAt = "2026-08-20"; :>> judgedBy = "claudeOpus5"; }
    }

    verification h2RefineGate : Test { :>> id = "0d800653-0814-6653-9b3e-000000300653"; :>> title = "Sprint 362 refine gate (DoR)"; :>> createdAt = "2026-08-20"; :>> createdBy = "claudeOpus5"; :>> method = VerificationMethod::inspect; :>> procedureText = "DoR. Pass 2 attacked a surface pass 1 never touched: argument handling and self-declaration across all 75 subcommands and all 46 routes. TWO FINDINGS, and they turned out to be THE SAME DEFECT at two layers - a surface that under-declares itself, which is also what issue172 was. One measurement was deliberately NOT turned into a finding: `keel assured` at 9.8s is the slowest read command, and the human has already said CLI slowness is acceptable, so recording it would have been manufacturing work against a standing instruction. estimatedPoints=5."; }
    part h2RefineGateR1 : TestResult { :>> id = "0d800654-0814-6654-9b3e-000000300654"; :>> outcome = VerdictKind::pass; :>> judgedAgainst = "376fde6"; :>> judgedAt = "2026-08-20"; :>> judgedBy = "claudeOpus5"; }

    verification h2StandupGate : Test { :>> id = "0d800655-0814-6655-9b3e-000000300655"; :>> title = "Sprint 362 standup gate"; :>> createdAt = "2026-08-20"; :>> createdBy = "claudeOpus5"; :>> method = VerificationMethod::inspect; :>> procedureText = "Approach: fix each finding in the ONE place it lives, and add the lens that makes it un-re-derivable. issue177 has one home - `cmd_query1`, the shared wrapper six commands route through - which is why it was a small fix and why `governing-version` escaped it: that command has its own wrapper, and having its own wrapper is precisely how it drifted. No blockers."; }
    part h2StandupGateR1 : TestResult { :>> id = "0d800656-0814-6656-9b3e-000000300656"; :>> outcome = VerdictKind::pass; :>> judgedAgainst = "376fde6"; :>> judgedAt = "2026-08-20"; :>> judgedBy = "claudeOpus5"; }

    verification h2ImplementGate : Test { :>> id = "0d800657-0814-6657-9b3e-000000300657"; :>> title = "Sprint 362 implement gate"; :>> createdAt = "2026-08-20"; :>> createdBy = "claudeOpus5"; :>> method = VerificationMethod::test; :>> procedureText = "I RECORDED A WRONG NUMBER AND HAD TO CORRECT MY OWN FINDING, which is the result of this sprint I would most want a successor to read. issue178 first said 13 of 46 routes were unaccounted. The probe read `fn api_version`'s BODY - which names KEEL_API_READ_ENDPOINTS and KEEL_API_WRITE_ENDPOINTS rather than containing any endpoint string - so it saw almost nothing advertised. Measured against the actual constants the answer is THREE. THE FIFTH WRONG HAND PROBE OF THE SESSION, in the pass immediately after issue171 was recorded and cleared for exactly this. issue178's description was rewritten to state the correction rather than quietly replacing the number, because a finding that overstates directs a successor as surely as one that understates. THREE OTHER OWN-GOALS, all caught by testing rather than by reading: my `is_declared` scanner stopped at `:` and so kept the `;` from a bare `action foo;`, making every backlog action look undeclared - it broke `keel item` for the most common item type in this model; my first rc measurement piped to `head` and reported the pipe's status, so six fixed commands looked unfixed; and the new unit test used `Path::new(dot)` when a test's cwd is the CRATE dir, so it read a tree with no `.tracking` and would have passed vacuously in one direction. BOTH CONTROLS VERIFIED BY BREAKING THEM: a route registered and declared by nothing fails the build naming `/api/undeclared-thing`; a dispatch arm with no catalogue line fails naming itself."; }
    part h2ImplementGateR1 : TestResult { :>> id = "0d800658-0814-6658-9b3e-000000300658"; :>> outcome = VerdictKind::pass; :>> judgedAgainst = "376fde6"; :>> judgedAt = "2026-08-20"; :>> judgedBy = "claudeOpus5"; }

    verification h2ReviewGate : Test { :>> id = "0d800659-0814-6659-9b3e-000000300659"; :>> title = "Sprint 362 review gate"; :>> createdAt = "2026-08-20"; :>> createdBy = "claudeOpus5"; :>> method = VerificationMethod::inspect; :>> procedureText = "Reviewed. THE PATTERN ACROSS THREE FINDINGS NOW - issue172, issue177, issue178 - is one defect wearing three costumes: a surface that under-declares itself, always in the same direction, because adding a thing is easy and declaring it is a separate act nobody is forced to perform. Help omitted 35 commands; the router omitted 3 routes; and the name-resolution path omitted the failure case entirely, which is the same shape - the command declared success for a question it had not actually answered. All three are now pinned by a test that fails the build, which is the only version of this that survives me. WHAT I ADDED BEYOND THE FINDING: `advertisedButNotRegistered`, the reverse direction, which nothing had ever checked. It is empty today. An advertised route that does not exist would 404 a real consumer that trusted the contract, and it cost four lines to check once the two sets were in hand."; }
    part h2ReviewGateR1 : TestResult { :>> id = "0d80065a-0814-665a-9b3e-00000030065a"; :>> outcome = VerdictKind::pass; :>> judgedAgainst = "376fde6"; :>> judgedAt = "2026-08-20"; :>> judgedBy = "claudeOpus5"; }

    verification h2CloseOutGate : Test { :>> id = "0d80065b-0814-665b-9b3e-00000030065b"; :>> title = "Sprint 362 closeOut gate (autonomous, D0049)"; :>> createdAt = "2026-08-20"; :>> createdBy = "claudeOpus5"; :>> method = VerificationMethod::inspect; :>> procedureText = "Autonomous closeOut (D0049). issue177 and issue178 both cleared, both under D0169, which is still PROPOSED and unsigned. `keel hardening` now carries four lenses; two new controls, both verified by deliberate regression. issue178's own description was CORRECTED in place rather than superseded, since I own it and the correction is to my own reading rather than to their words (D0108). validate 394 clean; check-engine clean; 38 guards ALL PASS; 193 tests; clippy clean."; }
    part h2CloseOutGateR1 : TestResult { :>> id = "0d80065c-0814-665c-9b3e-00000030065c"; :>> outcome = VerdictKind::pass; :>> judgedAgainst = "376fde6"; :>> judgedAt = "2026-08-20"; :>> judgedBy = "claudeOpus5"; }

    verification h2RetroGate : Test { :>> id = "0d80065d-0814-665d-9b3e-00000030065d"; :>> title = "Sprint 362 retro gate (autonomous, D0049)"; :>> createdAt = "2026-08-20"; :>> createdBy = "claudeOpus5"; :>> method = VerificationMethod::analyze; :>> procedureText = "Autonomous retro (D0049) under D0131's retroTrack. WELL: (1) the wrong number was corrected IN THE FINDING rather than quietly fixed, so the record shows a 13 that was really a 3; (2) both fixes went into the one place the behaviour lives, and the one command that had its own wrapper is called out as the reason it drifted; (3) both controls were verified by producing the regression; (4) the reverse direction of issue178 - advertised-but-not-registered - was checked though nobody asked, because the two sets were already in hand; (5) `keel assured` at 9.8s was NOT recorded as a finding, since the human had already ruled CLI slowness acceptable and recording it would have manufactured work against a standing instruction. AVOIDABLE-ISSUE, AND IT IS THE SAME ONE AS LAST SPRINT: the fifth wrong hand probe, one pass after building the instrument that exists to prevent it. The lesson is not `be careful with regex` - it is that I reach for a probe when a question feels like a one-off, and this question felt like a one-off for the fifth time. THE RULE: if the answer would be worth recording as a finding, it is worth a lens, and the lens comes first. SECOND AVOIDABLE-ISSUE: three self-inflicted bugs in the fix itself (the `;` in a bare declaration, measuring rc through a pipe, a unit test rooted at the crate dir). All three were caught by testing both directions rather than by reading the code, which is the only reason the sprint is green. Estimate 5 pts, delivered."; }
    part h2RetroGateR1 : TestResult { :>> id = "0d80065e-0814-665e-9b3e-00000030065e"; :>> outcome = VerdictKind::pass; :>> judgedAgainst = "376fde6"; :>> judgedAt = "2026-08-20"; :>> judgedBy = "claudeOpus5"; }
}
