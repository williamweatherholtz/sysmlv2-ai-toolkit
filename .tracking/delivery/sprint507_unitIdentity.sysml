// ProjectDeliveryS507 — Sprint 507: publishing an improvement defeated yesterday's drift report. EXECUTE. 2 pts.
package ProjectDeliveryS507 {
    private import EngineElement::*;
    private import EngineWork::*;
    private import EngineVerification::*;
    private import EngineRelationships::*;

    #CharteredBy dependency from unitIdentityStory to d0272;

    part unitIdentityStory : Story {
        :>> id = "3f7a1c04-6b2e-4d51-9c83-5a1e0f2b7d64";
        :>> title = "Sprint 507: a unit's identity survives being republished by whoever improved it (2 pts)";
        :>> createdAt = "2026-09-01"; :>> createdBy = "claudeOpus5"; :>> kind = WorkKind::code; :>> priority = WorkPriority::p0; :>> owner = "claudeOpus5"; :>> estimatedPoints = 2;
    }

    action def DeliveryRunS507 {
        action storyUnitIdentity;
        verification storyUnitIdentityDoD : Test { :>> id = "8c5d3e91-42f7-4a08-b6d2-19e4c8f05a73"; :>> method = VerificationMethod::test; :>> procedureText = "DELIVERED BACKLOG ITEMS: dcUnitIdentityIsCarriedNotMinted (resolves issue323). FOUND BY DOING, not by looking: publishing the exec-summary improvement defeated srDriftIsReportedPerUnit, which had shipped one day earlier. Export read the unit id from unit-ids.toml alone - the ids this project MINTED - but this project had IMPORTED exec-summary, so the import filed it under the LIBRARY's id in installed-units.toml and wrote nothing to the minted registry. The lookup missed, minted a fresh id, and shipped the improved content under an identity no consumer had ever installed; next_unit_version then missed on THAT id and took its None arm, restarting the version at 1. Content changed, identity changed, version did not - so a consumer's drift check does not MISS the update, it AFFIRMS there is none. DONE: the install record outranks the minted registry; a disagreement REPAIRS the minted one in place, because it is what the next export reads and a fix that only prefers the right id reopens on the following publish; one process name under two ids REFUSES and names both; and next_unit_version refuses rather than restarting when the id misses on a process the project demonstrably has installed. Live damage repaired - this repo's record carried exec-summary under two ids, both v1; the library now holds unitId a2428932 at v2 with the 151-line skill. ALSO recorded, not built: issue324, a peer session's circular lock, verified here at file:line before recording. VERIFY: unit_identity_survives_republish 3/3, all three ARMED against the pre-fix binary where all three fail; workspace suite 449 passed 0 failed; keel guard 0 violations."; }
        // RAN: unit_identity_survives_republish 3/3; cargo test --release workspace-wide 449 passed / 0 failed; the round trip shows the re-mint directly against the stashed binary - 9287c762 published over 969856ab; library exec-summary read back as unitId a2428932 v2
        part storyUnitIdentityDoDR1 : TestResult { :>> id = "e2b90f47-1d63-4c85-a97e-3b60d1f8c452"; :>> outcome = VerdictKind::pass; :>> judgedAgainst = "93eb6dc"; :>> judgedAt = "2026-09-01"; :>> judgedBy = "claudeOpus5"; }
    }

    verification unitIdentityRefineGate : Test { :>> id = "a41c7b28-905e-4f36-8d19-6c2b3e07f5a1"; :>> title = "Sprint 507 refine gate (DoR)"; :>> createdAt = "2026-09-01"; :>> createdBy = "claudeOpus5"; :>> method = VerificationMethod::inspect; :>> procedureText = "READY because the defect was OBSERVED, not suspected: the library's unit.toml said version 1 under an id that did not match the install record's key, both read off disk before any fix was written. issue323 also named its own test - import, change one file, publish, assert the identity is unchanged and the version incremented - so the acceptance criterion existed before the implementation."; }
    verification unitIdentityStandupGate : Test { :>> id = "b7e03d5a-2c48-41f9-a05b-8e17d4c96203"; :>> title = "Sprint 507 standup gate"; :>> createdAt = "2026-09-01"; :>> createdBy = "claudeOpus5"; :>> method = VerificationMethod::inspect; :>> procedureText = "SCOPE HELD DELIBERATELY NARROW. The forked-identity state is caught at the WRITE PATH and by no guard, so it can sit in a committed contract until the next publish refuses. A guard was considered and NOT built: it would widen the keystone-locked enforcement surface for a state only one command can create and that command now refuses to propagate. Stated as a residual in D0272 rather than left unsaid, so the trade is revisitable if a second way to fork an identity appears."; }
    verification unitIdentityImplementGate : Test { :>> id = "c9f16a80-73d5-4e21-9b47-0a582c3ed6f9"; :>> title = "Sprint 507 implement gate"; :>> createdAt = "2026-09-01"; :>> createdBy = "claudeOpus5"; :>> method = VerificationMethod::test; :>> procedureText = "RAN: cargo test --release --test unit_identity_survives_republish -> 3 passed. ARMED per D0253 by `git stash push keel-cli/src/process_cmd.rs`, rebuilding, and re-running: 0 passed / 3 FAILED, the round trip printing the re-mint directly as left 9287c762 vs right 969856ab. cargo test --release workspace-wide -> 449 passed, 0 failed across 33 binaries. keel validate -> 577 clean. keel guard -> 0 violations. Live repair read back from the library rather than from the command's own report: unit.toml unitId a2428932-77c0-4714-9d61-c41d2857811f, version 2, SKILL.md 151 lines, and `keel library list` shows exec-summary v2."; }
    verification unitIdentityReviewGate : Test { :>> id = "d0847e13-5f92-4c6a-8137-2be95a0d41c8"; :>> title = "Sprint 507 review gate — three passes per D0172"; :>> createdAt = "2026-09-01"; :>> createdBy = "claudeOpus5"; :>> method = VerificationMethod::inspect; :>> procedureText = "THREE PASSES. (1) IS THE REPAIR SAFE TO RUN SILENTLY: unit_id_for rewrites unit-ids.toml when it disagrees with the install record. That is a write on a read-shaped path, so it prints what it did and it only ever moves the minted registry TOWARD the install record - it can never invent an id, because the value written was read from a committed contract. (2) DOES THE REFUSAL HAVE AN ESCAPE: yes, and it is the right one - the human deletes the wrong section. No flag was added to force past it, because every heuristic for picking between two ids silently chooses an identity on the human's behalf and picking wrong orphans installs. (3) DID THE FIX'S OWN TEST GET TESTED: yes - that is what the stash run is for. Two of the three cases would have passed against a fix that only changed unit_id_for's preference order; the round trip is the one that could not, and it was run against the pre-fix binary specifically to see it fail."; }
    verification unitIdentityCloseOutGate : Test { :>> id = "e5230c9b-84a1-4d76-b0f3-97c14e628d05"; :>> title = "Sprint 507 closeOut gate (autonomous, D0049)"; :>> createdAt = "2026-09-01"; :>> createdBy = "claudeOpus5"; :>> method = VerificationMethod::inspect; :>> procedureText = "CLOSED. issue323 resolved and its resolver corrected - it had been mis-triaged to dcCliSurfaceConsolidation, the previous call's resolver carried over. issue324 recorded with a real resolver and NOT started; it is downstream-only, since check_preconditions refuses this repo as a self-build. Doc-sync rode the change: library-stewardship rule 5 now governs publishing an adaptation back."; }
    verification unitIdentityRetroGate : Test { :>> id = "f8461d02-3e57-49b8-a625-1c0d7b53fa96"; :>> title = "Sprint 507 retro gate (autonomous, D0049)"; :>> createdAt = "2026-09-01"; :>> createdBy = "claudeOpus5"; :>> method = VerificationMethod::analyze; :>> procedureText = "TWO FINDINGS, and the second is the one worth keeping. (1) THE CONTROL THAT SHIPPED YESTERDAY WAS DEFEATED BY USING IT TODAY. srDriftIsReportedPerUnit was verified against fixtures where the version numbers were correct; nothing exercised the publish path that PRODUCES those numbers. A report is only as sound as the field it reads, and its test never asked where that field comes from. The general lesson: when a lens reads a value another command writes, the lens's test must include a round trip through the writer, or it is testing its own fixture. (2) A MIS-TRIAGE PASSED THE ISSUES GUARD. issue323's #Resolves pointed at a task that cannot resolve it, carried over from the previous record issue call. The guard checks that an edge EXISTS (guards.rs:970-986) and never that the resolver can resolve it - so a false triage reads as triaged, and the frontier ranks work against issues it will not close. NOT FIXED HERE and deliberately so: issue322 points at that same task DELIBERATELY and says so in its own text, so the distinguishing signal is prose, and a guard that fired on prose would be wrong about half the time. What would work is requiring the RESOLVER to name the issue, which is a convention change and belongs in a proposal, not in a retro fix."; }
}
