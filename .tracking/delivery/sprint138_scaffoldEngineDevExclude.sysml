// ProjectDeliveryS138 — Sprint 138: scaffoldEngineDevExclude (D0093 boundary) — exclude the engine-DEV
// kernel/Python toolchain (.engine/tools/, __pycache__, *.pyc) from the `keel init` scaffold. Downstream
// gets only the reusable engine (Rust path, D0048). Fresh scaffold 212->176 files, 0 python, no tools/.
// First deployment-readiness task. 2 pts. AUTONOMOUS (D0049).
package ProjectDeliveryS138 {
    private import EngineElement::*;
    private import EngineWork::*;
    private import EngineVerification::*;
    private import EngineRelationships::*;

    #CharteredBy dependency from scaffoldEngineDevExcludeStory to d0093;

    part scaffoldEngineDevExcludeStory : Story {
        :>> id = "63940516-2c7d-4e8f-c138-51627384c001";
        :>> title = "Sprint 138: scaffoldEngineDevExclude (2 pts) — keel init ships only the reusable engine, not the kernel/python toolchain (D0093)";
        :>> createdAt = "2026-06-23"; :>> createdBy = "wweatherholtz"; :>> kind = WorkKind::code; :>> priority = WorkPriority::p2; :>> owner = "claudeOpus"; :>> estimatedPoints = 2;
    }

    action def DeliveryRunS138 {
        action storyScaffoldEngineDevExclude;
        verification storyScaffoldEngineDevExcludeDoD : Test { :>> id = "63940516-2c7d-4e8f-c138-51627384c002"; :>> method = VerificationMethod::test; :>> procedureText = "D0093 engine/instance boundary: `keel init` embedded ALL of .engine (include_dir!), shipping ~30 engine-DEV-only python files (tools/validate kernel validators, _kernel.py, spikes, probes, __pycache__, migrations/) downstream can't run (no conda/JVM; D0048 Rust path is authority). FIX: main.rs adds is_engine_dev_only(rel) — true for any component named `tools`/`__pycache__` or a .pyc — and write_engine_file SKIPS those; the reusable engine (schema/workflows/processes/skills/decisions->reference/docs/views/contracts) still scaffolds. init_smoke.rs asserts no .engine/tools + 0 .py/.pyc in a fresh scaffold (walk_count helper). VERIFY (measured): fresh `keel init` = 176 engine files (was 212), no tools/, 0 python; keel validate + guard all PASS on the fresh scaffold; clippy --workspace --all-targets -D warnings green (fixed: Path import in the test); cargo test 48 lib + init_smoke + BDD pass; repo keel validate 151 + guard all (13) green."; }
        part storyScaffoldEngineDevExcludeDoDR1 : TestResult { :>> id = "63940516-2c7d-4e8f-c138-51627384c003"; :>> outcome = VerdictKind::pass; :>> judgedAgainst = "888a5df"; :>> judgedAt = "2026-06-23"; :>> judgedBy = "claudeOpus"; }
    }

    verification scaffoldEngineDevExcludeRefineGate : Test { :>> id = "63940516-2c7d-4e8f-c138-51627384c004"; :>> title = "Sprint 138 refine gate (DoR)"; :>> createdAt = "2026-06-23"; :>> createdBy = "claudeOpus"; :>> method = VerificationMethod::inspect; :>> procedureText = "DoR: deployment-readiness #1. Research found `keel init` ships ~30 engine-dev python files downstream can't use. Resolver: scaffoldEngineDevExclude. estimatedPoints=2. #CharteredBy d0093. DoD accepted."; }
    part scaffoldEngineDevExcludeRefineGateR1 : TestResult { :>> id = "63940516-2c7d-4e8f-c138-51627384c005"; :>> outcome = VerdictKind::pass; :>> judgedAgainst = "888a5df"; :>> judgedAt = "2026-06-23"; :>> judgedBy = "claudeOpus"; }
    verification scaffoldEngineDevExcludeStandupGate : Test { :>> id = "63940516-2c7d-4e8f-c138-51627384c006"; :>> title = "Sprint 138 standup gate"; :>> createdAt = "2026-06-23"; :>> createdBy = "claudeOpus"; :>> method = VerificationMethod::inspect; :>> procedureText = "Approach: filter at scaffold-write time (is_engine_dev_only on the include_dir rel path) rather than the embed (include_dir has no easy glob-exclude); skip tools/+__pycache__+.pyc. Assert in init_smoke. Verify a fresh init has none + still validates/guards. No .engine/schema/process-def change. No blockers."; }
    part scaffoldEngineDevExcludeStandupGateR1 : TestResult { :>> id = "63940516-2c7d-4e8f-c138-51627384c007"; :>> outcome = VerdictKind::pass; :>> judgedAgainst = "888a5df"; :>> judgedAt = "2026-06-23"; :>> judgedBy = "claudeOpus"; }
    verification scaffoldEngineDevExcludeImplementGate : Test { :>> id = "63940516-2c7d-4e8f-c138-51627384c008"; :>> title = "Sprint 138 implement gate"; :>> createdAt = "2026-06-23"; :>> createdBy = "claudeOpus"; :>> method = VerificationMethod::test; :>> procedureText = "Implemented is_engine_dev_only + the write_engine_file skip + init_smoke assertion. VERIFY (live): fresh init = 176 files, no tools/, 0 .py; validate + guard all PASS on it; clippy green; cargo test 48 lib + init_smoke pass; repo validate 151 + guard all (13) PASS."; }
    part scaffoldEngineDevExcludeImplementGateR1 : TestResult { :>> id = "63940516-2c7d-4e8f-c138-51627384c009"; :>> outcome = VerdictKind::pass; :>> judgedAgainst = "888a5df"; :>> judgedAt = "2026-06-23"; :>> judgedBy = "claudeOpus"; }
    verification scaffoldEngineDevExcludeReviewGate : Test { :>> id = "63940516-2c7d-4e8f-c138-51627384c00a"; :>> title = "Sprint 138 review gate"; :>> createdAt = "2026-06-23"; :>> createdBy = "claudeOpus"; :>> method = VerificationMethod::inspect; :>> procedureText = "Diff reviewed. Filtering at write-time (not embed) is the pragmatic choice (include_dir embeds the whole tree; the ~30 small files in the binary are negligible, but they no longer LAND in a consumer's project). The exclusion is conservative + tested (init_smoke asserts no tools + 0 python). The fresh scaffold still validates + guards green, so nothing reusable was dropped. D0093 boundary tightened: downstream gets the engine, not the engine's dev toolchain. Clean."; }
    part scaffoldEngineDevExcludeReviewGateR1 : TestResult { :>> id = "63940516-2c7d-4e8f-c138-51627384c00b"; :>> outcome = VerdictKind::pass; :>> judgedAgainst = "888a5df"; :>> judgedAt = "2026-06-23"; :>> judgedBy = "claudeOpus"; }
    verification scaffoldEngineDevExcludeCloseOutGate : Test { :>> id = "63940516-2c7d-4e8f-c138-51627384c00c"; :>> title = "Sprint 138 closeOut gate (autonomous, D0049)"; :>> createdAt = "2026-06-23"; :>> createdBy = "claudeOpus"; :>> method = VerificationMethod::inspect; :>> procedureText = "Autonomous closeOut (D0049): DoD pass; fresh scaffold is clean (176 files, no tools/python) + green; init_smoke guards it. clippy + cargo test + keel validate 151 + guard all (13) green. Self-evidencing (D0051). Deployment-readiness 1/8 done; scaffoldCommitGate next."; }
    part scaffoldEngineDevExcludeCloseOutGateR1 : TestResult { :>> id = "63940516-2c7d-4e8f-c138-51627384c00d"; :>> outcome = VerdictKind::pass; :>> judgedAgainst = "888a5df"; :>> judgedAt = "2026-06-23"; :>> judgedBy = "claudeOpus"; }
    verification scaffoldEngineDevExcludeRetroGate : Test { :>> id = "63940516-2c7d-4e8f-c138-51627384c00e"; :>> title = "Sprint 138 retro gate (autonomous, D0049)"; :>> createdAt = "2026-06-23"; :>> createdBy = "claudeOpus"; :>> method = VerificationMethod::analyze; :>> procedureText = "Autonomous retro (D0049). WELL: extending the existing init_smoke test with the exclusion assertion (walk_count) means the D0093 boundary is now a REGRESSION-GUARDED property, not a one-time cleanup — a future engine-dev file under tools/ can't silently leak downstream. AVOIDABLE-ISSUE SCAN: one avoidable nit caught + fixed (the test needed `Path` in its import; clippy --all-targets surfaced it before commit — the CI gate's value again). NON-blocking forward note (NOT debt): the ~30 dev files are still EMBEDDED in the binary (include_dir has no easy glob-exclude); negligible size, and they simply aren't written to a consumer project — a future embed-time exclusion is optional. Estimate 2 pts held. 7 deployment tasks remain."; }
    part scaffoldEngineDevExcludeRetroGateR1 : TestResult { :>> id = "63940516-2c7d-4e8f-c138-51627384c00f"; :>> outcome = VerdictKind::pass; :>> judgedAgainst = "888a5df"; :>> judgedAt = "2026-06-23"; :>> judgedBy = "claudeOpus"; }
}
