// ProjectDeliveryS459 — Sprint 459: the channel's deterministic logic moves into the binary where it is tested; gh effects stay a thin step; policy stays in the process (D0221). EXECUTE. 2 pts.
package ProjectDeliveryS459 {
    private import EngineElement::*;
    private import EngineWork::*;
    private import EngineVerification::*;
    private import EngineRelationships::*;

    #CharteredBy dependency from channelLogicInBinaryStory to d0221;

    part channelLogicInBinaryStory : Story {
        :>> id = "24cdb60a-9f3f-4e7c-89c1-683f82e6d118";
        :>> title = "Sprint 459: no decision logic left in a bespoke script (2 pts)";
        :>> createdAt = "2026-08-24"; :>> createdBy = "claudeFable5"; :>> kind = WorkKind::code; :>> priority = WorkPriority::p0; :>> owner = "claudeFable5"; :>> estimatedPoints = 2;
    }

    action def DeliveryRunS459 {
        action storyChannelLogicInBinary;
        verification storyChannelLogicInBinaryDoD : Test { :>> id = "1ef2b403-d595-45d0-a9df-d0fba5e04dc0"; :>> method = VerificationMethod::test; :>> procedureText = "DELIVERED: dcChannelLogicInBinary, delivering D0221 IN PART. The human, on seeing the channel adopted: 'I don't want all these bespoke scripts - if we need something consistently, let us build it into keel or into a process if we need it flexible.' The evidence was already in this session: the channel shipped 272 lines of bespoke shell and python, and every recurring defect came from that - record_decision.sh RE-GREPPED the login table the binary already owns, which is two implementations of one rule and exactly how the workflow gate and the recorder drifted apart (D0219); the gesture vocabulary was a shell `case` with a locale-dependent `tr` doing text parsing that nothing unit-tested; and a bespoke script is invisible to every keel surface, so no guard reads it and its behaviour cannot be re-derived from the tree. THE SPLIT, by KIND rather than convenience: DETERMINISTIC TEXT LOGIC into the binary as `keel github-gesture`, which reads COMMENT_BODY / ISSUE_BODY / COMMENT_ID / COMMENT_BODIES from ENV - never argv, because a comment body is attacker-influenced text - and prints JSON carrying verdict, option, reason, decision and alreadyReceipted, exiting 1 when nothing parsed; GITHUB I/O stays in the script, because the binary makes no network calls, the same reasoning that keeps orient from fetching; POLICY stays in the process definition. The vocabulary now lives in ONE place. I considered declaring it as configurable data so the parser reads it, and REJECTED that under D0088: nobody has needed a different vocabulary, and a config file plus reader plus doc surface is the speculative generality this engine keeps paying for - so D0221's own consequence text was AMENDED to say so rather than let the decision and the build silently diverge. VERIFIED: five unit tests pin the documented vocabulary (single letter, accept, accept X, reject <why>, first-line-only) and, the one that matters most, that nothing unrecognised is ever read as an accept - lgtm, yes, acceptable, accept BB and a bare number all resolve to unparsed, because a misread gesture becomes a fabricated human attestation (D0106), the one failure this path must never have. Live: B and accept and reject <why> return the right JSON and lgtm exits 1; idempotency reports alreadyReceipted from the fetched comment bodies. HONEST ACCOUNTING, and it is not the win the request implies: record_decision.sh went 130 -> 129 lines, because the gh fetches the binary cannot do were ADDED as the logic was removed. What changed is that NO decision logic remains in it - it is I/O and orchestration. open_decision_issues.py still composes the issue body in python, and `.github/scripts/` still exists; the target state of that directory disappearing is chartered, not reached."; }
        part storyChannelLogicInBinaryDoDR1 : TestResult { :>> id = "f65d6547-3044-4e26-8d30-f333636d9844"; :>> outcome = VerdictKind::pass; :>> judgedAgainst = "9253f3c907438e52e00817b954b5e410661922da"; :>> judgedAt = "2026-08-24"; :>> judgedBy = "claudeFable5"; }
    }

    verification channelLogicInBinaryRefineGate : Test { :>> id = "04af359f-f634-4b44-a7df-c56930967b5f"; :>> title = "Sprint 459 refine gate (DoR)"; :>> createdAt = "2026-08-24"; :>> createdBy = "claudeFable5"; :>> method = VerificationMethod::inspect; :>> procedureText = "DoR. Delivers part of D0221, recorded from the human's direction. Scope: move the deterministic text logic of the RECORDING path into the binary with tests, and leave the effects as effects. Explicitly NOT in scope this sprint: the issue-body composer, and deleting the scripts. 2 points."; }
    part channelLogicInBinaryRefineGateR1 : TestResult { :>> id = "9dd4b13f-7bb9-42ee-9a5e-27943973b947"; :>> outcome = VerdictKind::pass; :>> judgedAgainst = "9253f3c907438e52e00817b954b5e410661922da"; :>> judgedAt = "2026-08-24"; :>> judgedBy = "claudeFable5"; }
    verification channelLogicInBinaryStandupGate : Test { :>> id = "f4585cc7-458a-42a9-9056-35b890f15231"; :>> title = "Sprint 459 standup gate"; :>> createdAt = "2026-08-24"; :>> createdBy = "claudeFable5"; :>> method = VerificationMethod::inspect; :>> procedureText = "Approach: classify by whether a thing is DETERMINISTIC and therefore testable - text parsing is, network effects are not, and what a gesture MEANS is a judgment a project should be able to change. Keep the comment body arriving by env so nothing attacker-influenced is ever interpolated into a shell command. Resist adding a vocabulary config file: build the flexible thing when a justified need appears, not before. No blockers."; }
    part channelLogicInBinaryStandupGateR1 : TestResult { :>> id = "0bf1cb97-58b0-4039-bf0d-49e4c8e7a7b1"; :>> outcome = VerdictKind::pass; :>> judgedAgainst = "9253f3c907438e52e00817b954b5e410661922da"; :>> judgedAt = "2026-08-24"; :>> judgedBy = "claudeFable5"; }
    verification channelLogicInBinaryImplementGate : Test { :>> id = "9cda2314-81b7-427f-8cac-4c8cc70f114a"; :>> title = "Sprint 459 implement gate"; :>> createdAt = "2026-08-24"; :>> createdBy = "claudeFable5"; :>> method = VerificationMethod::test; :>> procedureText = "Verified by running the built binary directly: B yields accept/option B, accept yields accept/no option, `reject too wide` yields reject with the reason carried, lgtm exits 1 as unparsed, and a receipted comment id reports alreadyReceipted true. cargo test --lib -> 260 passed including five new gesture tests; cargo clippy --workspace --all-targets -D warnings clean after fixing a heredoc-mangled char literal by extracting a json_escape helper; bash -n clean on the rewritten script; validate 510 + all 49 guards + check-engine + rules green."; }
    part channelLogicInBinaryImplementGateR1 : TestResult { :>> id = "c6fbdc77-c0e4-4ab0-bf95-a9f9456de1be"; :>> outcome = VerdictKind::pass; :>> judgedAgainst = "9253f3c907438e52e00817b954b5e410661922da"; :>> judgedAt = "2026-08-24"; :>> judgedBy = "claudeFable5"; }
    verification channelLogicInBinaryReviewGate : Test { :>> id = "344a3d68-800f-40c5-bf4f-f5687feb9542"; :>> title = "Sprint 459 review gate — three passes per D0172"; :>> createdAt = "2026-08-24"; :>> createdBy = "claudeFable5"; :>> method = VerificationMethod::inspect; :>> procedureText = "PASS 1, CLAIMS: the JSON outputs, the exit codes and the test count are quoted read-backs; the line-count claim is stated as a NON-improvement rather than dressed up. PASS 2, BOUNDARY: (i) the recording path is exercised end-to-end only in production - I cannot run `gh` against a real issue from here, so the parts are unit-tested and the composition is not; that is the honest risk of this change and the sweeper plus the receipt idempotency are what limit it; (ii) open_decision_issues.py still composes the issue body, so half the python remains; (iii) the vocabulary is now a binary fact, so a project wanting a different one needs a binary upgrade - deliberate, argued in D0221, and revisitable on the first real need. PASS 3, OWN DIFF: I wrote D0221 saying the parser would READ the vocabulary from the process, then on building it judged that speculative and amended the Decision rather than quietly building something different from what I had recorded. That is the behaviour I want from myself, and it is worth noting because the alternative - letting the record and the build diverge - is the exact class this whole session has been fixing. WHAT A REVIEWER SHOULD ATTACK: that the script did not actually shrink, so if the objection was to the EXISTENCE of bespoke scripts rather than to logic living in them, this sprint answers the wrong half; the chartered remainder answers the other half."; }
    part channelLogicInBinaryReviewGateR1 : TestResult { :>> id = "81b1ca0a-f51f-40aa-8760-b5cbb753ff02"; :>> outcome = VerdictKind::pass; :>> judgedAgainst = "9253f3c907438e52e00817b954b5e410661922da"; :>> judgedAt = "2026-08-24"; :>> judgedBy = "claudeFable5"; }
    verification channelLogicInBinaryCloseOutGate : Test { :>> id = "ad7a5ff3-039a-455a-970e-8e8ddc71bb0c"; :>> title = "Sprint 459 closeOut gate (autonomous, D0049)"; :>> createdAt = "2026-08-24"; :>> createdBy = "claudeFable5"; :>> method = VerificationMethod::inspect; :>> procedureText = "Autonomous closeOut (D0049). D0221 partially delivered: no decision logic remains in the recording script, and the vocabulary is tested and single-sourced. The remainder - the body composer, and removing `.github/scripts/` - stays chartered on dcChannelLogicInBinary's successor work rather than being claimed. validate + all 49 guards + check-engine + rules green."; }
    part channelLogicInBinaryCloseOutGateR1 : TestResult { :>> id = "ff9a49fa-7877-4dd7-bf3f-a61e2ddb9663"; :>> outcome = VerdictKind::pass; :>> judgedAgainst = "9253f3c907438e52e00817b954b5e410661922da"; :>> judgedAt = "2026-08-24"; :>> judgedBy = "claudeFable5"; }
    verification channelLogicInBinaryRetroGate : Test { :>> id = "3d081e96-9d4c-4ba1-a458-188b78976aec"; :>> title = "Sprint 459 retro gate (autonomous, D0049)"; :>> createdAt = "2026-08-24"; :>> createdBy = "claudeFable5"; :>> method = VerificationMethod::analyze; :>> procedureText = "Autonomous retro (D0049). AVOIDABLE-ISSUE SCAN under rcRecurrence: (1) the heredoc-escaping class recurred a SIXTH time this session, mangling a Rust char literal, and I again switched to literal edits only after it broke. The rule has been recorded twice and violated four times since, which is now strong evidence that a recorded lesson is not a control - the only real fix is to stop generating Rust through shell heredocs at all. (2) I nearly shipped a build that differed from the Decision I had just recorded (a vocabulary config file the Decision promised); catching it and AMENDING the Decision is the right move and the cheap one, because the record was still proposed. WELL: the request was a direction rather than a defect, and following it produced a tested parser with a refusal property that matters more than the refactor - nothing unrecognised can ever be recorded as a human's acceptance. Estimate 2 pts, delivered 2."; }
    part channelLogicInBinaryRetroGateR1 : TestResult { :>> id = "abe3a9d2-7513-46a9-8a00-d46b6bd2d51e"; :>> outcome = VerdictKind::pass; :>> judgedAgainst = "9253f3c907438e52e00817b954b5e410661922da"; :>> judgedAt = "2026-08-24"; :>> judgedBy = "claudeFable5"; }
}
