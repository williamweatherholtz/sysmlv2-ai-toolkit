// ProjectDeliveryS388 — Sprint 388: P4a + P3a + P4b - process units are versioned, updateable, and travel with their teeth. EXECUTE. 13 pts.
package ProjectDeliveryS388 {
    private import EngineElement::*;
    private import EngineWork::*;
    private import EngineVerification::*;
    private import EngineRelationships::*;

    #CharteredBy dependency from p4ModularUnitsStory to d0183;

    part p4ModularUnitsStory : Story {
        :>> id = "39780fe8-cce5-424c-9eee-89917a753352";
        :>> title = "Sprint 388: P4 - versioned units, three-way updates, rule attribution, rules travel (13 pts)";
        :>> createdAt = "2026-08-21"; :>> createdBy = "claudeFable5"; :>> kind = WorkKind::code; :>> priority = WorkPriority::p0; :>> owner = "claudeFable5"; :>> estimatedPoints = 13;
    }

    action def DeliveryRunS388 {
        action storyP4ModularUnits;
        verification storyP4ModularUnitsDoD : Test { :>> id = "58279bdb-59f8-4c52-980c-42aa890b7f28"; :>> method = VerificationMethod::test; :>> procedureText = "DELIVERED BACKLOG ITEMS: p4aUnitIdentity, p4aInstallRecord, p4aImportUpdate, p4aHandshake, p4aGoverningVersion, p3aRuleAttribution, p3aKeystoneExtension, p4bRulesTravel. IDENTITY (d0183): a unit's id is minted once and recorded in .engine/contracts/unit-ids.toml - stable across exports (proven live: v1 then v2 from consecutive exports after the origin-versioning defect this sprint FOUND was fixed: the origin never recorded its own exports, so downstream could never see a version advance). INSTALL RECORD: import writes the versioned unit id + per-file content hashes to installed-units.toml - the three-way base. UPDATE (K9/K10): import --update runs the three-way per file, ALL BRANCHES PROVEN LIVE - divergence REFUSED with a per-file report, local-at-base takes upstream, upstream-at-base KEEPS local additions (1 kept local additions in the transcript - the assert-constraint case the panel named), --assume-local-base bootstraps pre-D0183 installs by explicit human flag, never inference; the supersession record is the D0070 keystone commit, and reprocess-candidates reads definition history per item. HANDSHAKE (K8): required guards diffed against GUARD_NAMES - refuse, or --degrade lands the prose LOUDLY with a recorded obligation; the P4b slice extends it to RULES: a bundle that cannot land its declared rules refuses (proven live on a stripped bundle) or degrades with the obligation. GOVERNING-VERSION GENERALIZED (K10): resolved PER ITEM from its charter edges (the chartering Decision's intro commit's touched process/workflow defs), falling back to the D0069 Story->Delivery convention; the hardcoded delivery.sysml path is dead. RULE ATTRIBUTION (d0184): unit.rules populates from .engine/contracts/rule-owners.toml (data, not Rust; the hardcoded rules: Vec::new() is dead), and guard_state treats a guard as active if ANY active unit asserts it - first-match-wins is dead. KEYSTONE EXTENSION (d0184): the D0070 lock now covers .engine/skills and .engine/contracts (machine-state registries exempted by name: unit-ids, installed-units, deck-inbox, adoption-profile) - and it GOVERNED ITS OWN SPRINT: the demo rule-owners.toml was withdrawn from this commit because landing it requires the marked-Decision commit the extension itself demands. RULES TRAVEL (P4b): export EXTRACTS the owned rule declarations into a unit-local rules file (shared rules files are never copied, so an import can never clobber the destination's other rules), proven live end to end: attribution -> export carries the rule -> import lands prose + teeth -> handshake refuses the stripped bundle. 223 tests; clippy 0."; }
        part storyP4ModularUnitsDoDR1 : TestResult { :>> id = "88f6454c-c9fb-4cf3-b3e3-162a9160fafb"; :>> outcome = VerdictKind::pass; :>> judgedAgainst = "e2571f8"; :>> judgedAt = "2026-08-21"; :>> judgedBy = "claudeFable5"; }
    }

    verification p4ModularUnitsRefineGate : Test { :>> id = "d7360c31-0cc3-41ff-a279-47ff547c2d0f"; :>> title = "Sprint 388 refine gate (DoR)"; :>> createdAt = "2026-08-21"; :>> createdBy = "claudeFable5"; :>> method = VerificationMethod::inspect; :>> procedureText = "DoR. P4a's five items plus P3a's two plus P4b's one - P4b executes under d0183 jointly with d0184 per the accepted decisions, so one sprint carries the three WPs the sequencing diagram joins. estimatedPoints=13."; }
    part p4ModularUnitsRefineGateR1 : TestResult { :>> id = "08f41875-c978-42d2-8ab8-ed1bc2a1380a"; :>> outcome = VerdictKind::pass; :>> judgedAgainst = "e2571f8"; :>> judgedAt = "2026-08-21"; :>> judgedBy = "claudeFable5"; }
    verification p4ModularUnitsStandupGate : Test { :>> id = "d9668669-220c-4d3c-9d56-61d367d879c1"; :>> title = "Sprint 388 standup gate"; :>> createdAt = "2026-08-21"; :>> createdBy = "claudeFable5"; :>> method = VerificationMethod::inspect; :>> procedureText = "Approach: identity and bases are DATA in committed contracts (unit-ids, installed-units), hashes ride the existing stable_hash, and the three-way is per-file by content hash - no new formats, no new dependencies. Rule attribution is a contract file rather than a schema change (invariant 5: schema/core stays frozen; the association is project data). The extraction-not-copy design for traveling rules exists because shared rules files would clobber on import - the panel's stem-keying warning applied one level down."; }
    part p4ModularUnitsStandupGateR1 : TestResult { :>> id = "50285f62-18fd-4afa-aea1-9bd0c2b50521"; :>> outcome = VerdictKind::pass; :>> judgedAgainst = "e2571f8"; :>> judgedAt = "2026-08-21"; :>> judgedBy = "claudeFable5"; }
    verification p4ModularUnitsImplementGate : Test { :>> id = "deaf2aa1-bf08-4889-bb04-574473dee2e1"; :>> title = "Sprint 388 implement gate"; :>> createdAt = "2026-08-21"; :>> createdBy = "claudeFable5"; :>> method = VerificationMethod::test; :>> procedureText = "Every branch run live: export v1/v2 identity stability; fresh import with record; divergence refusal; local-at-base update; upstream-at-base keeping local additions; --assume-local-base bootstrap demand and acceptance; guard handshake refusal wording; rules handshake refusing a stripped bundle and degrading with an obligation; attribution populating unit.rules read back from process list --verbose. TWO DEFECTS FOUND BY RUNNING: the origin never versioned its own exports (v1 forever - fixed by recording exports at the origin), and the first keep-local test actually created a THREE-WAY divergence (my test setup reverted upstream underneath the base) - the refusal that fired was correct and the test was wrong, which is exactly the discrimination the three-way exists to make."; }
    part p4ModularUnitsImplementGateR1 : TestResult { :>> id = "0cfad469-c18f-48b8-9540-8cc36855f452"; :>> outcome = VerdictKind::pass; :>> judgedAgainst = "e2571f8"; :>> judgedAt = "2026-08-21"; :>> judgedBy = "claudeFable5"; }
    verification p4ModularUnitsReviewGate : Test { :>> id = "0d813ea2-1ecb-45cc-97ca-1abe95136d6b"; :>> title = "Sprint 388 review gate — three passes per D0172"; :>> createdAt = "2026-08-21"; :>> createdBy = "claudeFable5"; :>> method = VerificationMethod::inspect; :>> procedureText = "PASS 1, CLAIMS vs computed/emitted: every verdict from a live transcript line or a test; 223 tests, clippy 0. PASS 2, BOUNDARY: pre-D0183 bundles (no unitId) refuse --update with the bootstrap path named; unreadable files hash as unreadable rather than panicking; the extraction brace-walker returns None on unbalanced input. PASS 3, OWN DIFF: a raw backslash in a replace literal broke the build once (the authoring-mangling family; caught by rustc in seconds); the demo attribution entry nearly landed without its marked Decision until the sprint's own keystone extension refused the thought. WHAT A REVIEWER SHOULD ATTACK: governing_def_for takes the FIRST touched def of the chartering Decision's intro commit - a Decision landing two defs picks arbitrarily; acceptable while charters touch one def, recorded here as the tightening point."; }
    part p4ModularUnitsReviewGateR1 : TestResult { :>> id = "1d70b66a-183f-4c9e-ba21-3348b55cc27a"; :>> outcome = VerdictKind::pass; :>> judgedAgainst = "e2571f8"; :>> judgedAt = "2026-08-21"; :>> judgedBy = "claudeFable5"; }
    verification p4ModularUnitsCloseOutGate : Test { :>> id = "2e34be2d-ee78-44fe-a7fd-b0fb08ad0298"; :>> title = "Sprint 388 closeOut gate (autonomous, D0049)"; :>> createdAt = "2026-08-21"; :>> createdBy = "claudeFable5"; :>> method = VerificationMethod::inspect; :>> procedureText = "Autonomous closeOut (D0049). Eight DoDs flipped at the judging HEAD; test residue withdrawn from the real tree (unit registries, demo attribution); the keystone extension active from this commit forward. validate clean; 41 guards ALL PASS; 223 tests; clippy 0."; }
    part p4ModularUnitsCloseOutGateR1 : TestResult { :>> id = "c99d39f3-ad9d-4149-a609-30b6a81fdbfe"; :>> outcome = VerdictKind::pass; :>> judgedAgainst = "e2571f8"; :>> judgedAt = "2026-08-21"; :>> judgedBy = "claudeFable5"; }
    verification p4ModularUnitsRetroGate : Test { :>> id = "f88cd8eb-62cf-412d-a6cc-2cd135ac09d6"; :>> title = "Sprint 388 retro gate (autonomous, D0049)"; :>> createdAt = "2026-08-21"; :>> createdBy = "claudeFable5"; :>> method = VerificationMethod::analyze; :>> procedureText = "Autonomous retro (D0049). AVOIDABLE-ISSUE SCAN under rcRecurrence: (1) the run-helpers-before-their-definer script-ordering slip (import rewritten before its helpers script ran) is the first occurrence of run-order-between-authored-scripts - practice recorded: a multi-script change runs scripts in dependency order and builds between them; (2) authoring-mangling appeared once more in a replace literal - the Write-tool-file rule held everywhere else and the single lapse was compiler-caught. WELL: (1) the three-way refused my own mis-constructed test - a control disagreeing with its author and being RIGHT; (2) the keystone extension governed the sprint that shipped it, refusing its own demo residue; (3) all eight DoDs were implementable exactly as the panel wrote them - second WP in a row where the decomposition survived contact. Estimate 13 pts, delivered."; }
    part p4ModularUnitsRetroGateR1 : TestResult { :>> id = "e70c35fa-dc2d-4f4a-b6cd-e25053ccc35b"; :>> outcome = VerdictKind::pass; :>> judgedAgainst = "e2571f8"; :>> judgedAt = "2026-08-21"; :>> judgedBy = "claudeFable5"; }
}
