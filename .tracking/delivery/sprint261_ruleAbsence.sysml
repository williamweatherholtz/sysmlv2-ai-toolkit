// ProjectDeliveryS261 — Sprint 261: an absent declared rule is not a violation; six more guards
// unblocked (issue090, D0136). v0.2.2. Found by hunting for more instances, not by another field
// report. EXECUTE. 2 pts.
package ProjectDeliveryS261 {
    private import EngineElement::*;
    private import EngineWork::*;
    private import EngineVerification::*;
    private import EngineRelationships::*;

    #CharteredBy dependency from ruleAbsenceStory to d0136;

    part ruleAbsenceStory : Story {
        :>> id = "0d7d0001-0814-5d01-9b3e-0000002d0001";
        :>> title = "Sprint 261: rule_violations_opt — absence is not violation; v0.2.2 patch (2 pts)";
        :>> createdAt = "2026-08-14"; :>> createdBy = "claudeOpus5"; :>> kind = WorkKind::code; :>> priority = WorkPriority::p0; :>> owner = "claudeOpus5"; :>> estimatedPoints = 2;
    }

    action def DeliveryRunS261 {
        action storyRuleAbsence;
        verification storyRuleAbsenceDoD : Test { :>> id = "0d7d0002-0814-5d02-9b3e-0000002d0002"; :>> method = VerificationMethod::test; :>> procedureText = "Delivers dcRuleAbsenceNotViolation (issue090/D0136). Found by deliberately hunting for MORE instances of D0136's class after issue089 rather than assuming it was isolated — and it had the same blast radius. Six HARD guards are rule-sourced; each called `rule_violations`, which returns Err when the named rule is not declared, and each mapped Err to a VIOLATION. REPRODUCED on a fresh `keel init` project with `.engine/rules/` removed: SIX hard failures, exit 1, every commit blocked, with messages naming internal rule names (acceptanceEventRule, charterRule, capabilityRootednessRule...) that mean nothing to a downstream reader and suggest no action. SEMANTIC ERROR AT THE ROOT: a project that never ADOPTED a control has not VIOLATED it — absence and violation were conflated. FIX: `rule_violations_opt` returns Ok(None) on absence; each guard maps that to a WARNING naming the control as NOT ADOPTED plus a pass — never silent, so deleting a rule to escape a gate stays visible on every run — while a MALFORMED rule still hard-fails. VERIFY, four states all measured: fresh project minus .engine/rules goes from 6 hard failures to ALL PASS exit 0 with 6 visible NOT-ADOPTED warnings; fresh project WITH rules still passes; this repo unaffected; NEGATIVE TEST — an injected untriaged Issue with issuesTriagedRule PRESENT still hard-fails with exit 1, so the protection is intact. ALSO CONFIRMED this sprint, the real test of 'can other projects proceed': a fresh `keel init` project passes its OWN full gate (validate + all 23 guards + check-engine, exit 0). clippy clean; 156 tests; shipped v0.2.2 with three platform binaries verified attached at b98f526."; }
        part storyRuleAbsenceDoDR1 : TestResult { :>> id = "0d7d0003-0814-5d03-9b3e-0000002d0003"; :>> outcome = VerdictKind::pass; :>> judgedAgainst = "b98f526"; :>> judgedAt = "2026-08-14"; :>> judgedBy = "claudeOpus5"; }
    }

    verification raRefineGate : Test { :>> id = "0d7d0004-0814-5d04-9b3e-0000002d0004"; :>> title = "Sprint 261 refine gate (DoR)"; :>> createdAt = "2026-08-14"; :>> createdBy = "claudeOpus5"; :>> method = VerificationMethod::inspect; :>> procedureText = "DoR: the human asked 'anything else to button this up so other projects can proceed?'. Rather than inspect and reassure, the plan was to TEST it — `keel init` a fresh project with the shipped binary and run its own gate — and then hunt the remaining hard guards for the same coupling class as issue089. The fresh init passed; the rule-sourced guards did not. estimatedPoints=2. DoR met."; }
    part raRefineGateR1 : TestResult { :>> id = "0d7d0005-0814-5d05-9b3e-0000002d0005"; :>> outcome = VerdictKind::pass; :>> judgedAgainst = "b98f526"; :>> judgedAt = "2026-08-14"; :>> judgedBy = "claudeOpus5"; }

    verification raStandupGate : Test { :>> id = "0d7d0006-0814-5d06-9b3e-0000002d0006"; :>> title = "Sprint 261 standup gate"; :>> createdAt = "2026-08-14"; :>> createdBy = "claudeOpus5"; :>> method = VerificationMethod::inspect; :>> procedureText = "Approach: answer 'can other projects proceed' EMPIRICALLY — actually init a project and run its gate — because the question is about a state I do not inhabit. Then enumerate the remaining hard guards and ask of each whether it depends on project-side content the binary cannot guarantee. Make absence produce a WARNING rather than silence, so the fix cannot be abused to dodge a gate. No blockers."; }
    part raStandupGateR1 : TestResult { :>> id = "0d7d0007-0814-5d07-9b3e-0000002d0007"; :>> outcome = VerdictKind::pass; :>> judgedAgainst = "b98f526"; :>> judgedAt = "2026-08-14"; :>> judgedBy = "claudeOpus5"; }

    verification raImplementGate : Test { :>> id = "0d7d0008-0814-5d08-9b3e-0000002d0008"; :>> title = "Sprint 261 implement gate"; :>> createdAt = "2026-08-14"; :>> createdBy = "claudeOpus5"; :>> method = VerificationMethod::test; :>> procedureText = "Implemented at b98f526, released v0.2.2. The negative test was run in the SAME configuration as the fix (rule present, model violating) to prove the unblock did not cost the protection. The remaining hard guards were checked and found either correct-by-design when the project owns the content (process-skill, viewpoint-renderer, engine-lint) or vacuous when it is absent (manifest-coverage), so markers and rules were the only two real instances."; }
    part raImplementGateR1 : TestResult { :>> id = "0d7d0009-0814-5d09-9b3e-0000002d0009"; :>> outcome = VerdictKind::pass; :>> judgedAgainst = "b98f526"; :>> judgedAt = "2026-08-14"; :>> judgedBy = "claudeOpus5"; }

    verification raReviewGate : Test { :>> id = "0d7d000a-0814-5d0a-9b3e-0000002d000a"; :>> title = "Sprint 261 review gate"; :>> createdAt = "2026-08-14"; :>> createdBy = "claudeOpus5"; :>> method = VerificationMethod::inspect; :>> procedureText = "Reviewed. The right instinct was distrusting my own 'fixed' claim from the previous sprint and hunting for siblings — issue089 was reported from the field, and had I not looked, issue090 would have been the next field report instead. But the deeper point is the human's: BOTH fixes answer 'what has this project adopted?' by INFERENCE from file presence, which is implicit and cannot express intent — a project cannot state what it adopted, cannot adopt a process as a unit, and enforcement shifts when a file moves. The principled mechanism is the ACTIVATION MANIFEST (srPortActivationManifest), now declared as dcActivationManifest at frontier top, which subsumes both patches by making adoption a DECLARED fact. These two fixes are correct and shippable, but they are the degenerate case of that design, not its replacement."; }
    part raReviewGateR1 : TestResult { :>> id = "0d7d000b-0814-5d0b-9b3e-0000002d000b"; :>> outcome = VerdictKind::pass; :>> judgedAgainst = "b98f526"; :>> judgedAt = "2026-08-14"; :>> judgedBy = "claudeOpus5"; }

    verification raCloseOutGate : Test { :>> id = "0d7d000c-0814-5d0c-9b3e-0000002d000c"; :>> title = "Sprint 261 closeOut gate (autonomous, D0049)"; :>> createdAt = "2026-08-14"; :>> createdBy = "claudeOpus5"; :>> method = VerificationMethod::inspect; :>> procedureText = "Autonomous closeOut (D0049). dcRuleAbsenceNotViolation carries a passing DoD TestResult at b98f526; issue090 RESOLVES. v0.2.2 published with three platform binaries; a fresh `keel init` project passes its own gate; an existing project on any .engine vintage is unblocked with no action required. validate + all 23 guards + check-engine green; clippy clean. Frontier reordered: dcActivationManifest is now top, as the declared answer to project adoption."; }
    part raCloseOutGateR1 : TestResult { :>> id = "0d7d000d-0814-5d0d-9b3e-0000002d000d"; :>> outcome = VerdictKind::pass; :>> judgedAgainst = "b98f526"; :>> judgedAt = "2026-08-14"; :>> judgedBy = "claudeOpus5"; }

    verification raRetroGate : Test { :>> id = "0d7d000e-0814-5d0e-9b3e-0000002d000e"; :>> title = "Sprint 261 retro gate (autonomous, D0049)"; :>> createdAt = "2026-08-14"; :>> createdBy = "claudeOpus5"; :>> method = VerificationMethod::analyze; :>> procedureText = "Autonomous retro (D0049) under D0131's retroTrack. WELL: (1) 'can other projects proceed' was answered by ACTUALLY DOING IT — init a project, run its gate — rather than by inspection, which is the only honest way to answer a question about a state I do not inhabit; (2) hunting for siblings of issue089 found issue090 BEFORE it became a second field report, and the count of instances (now four) is what turned a one-off fix into a stated rule in D0136; (3) absence produces a visible warning rather than silence, so the unblock cannot be abused to dodge a gate. AVOIDABLE-ISSUE 1: my `until` polling loop for the release workflow read the PREVIOUS run's status and exited before the v0.2.2 run existed, so I briefly reported 'release not found' as if the publish had failed. Fixed by selecting the run for the specific tag. NO NEW ITEM — this is the read-back-the-computed-answer principle again (now its sixth recorded instance this sitting), already carried by the accepted response contract; the count is the signal, and it is consistently about trusting an intermediate rather than the thing actually asked. AVOIDABLE-ISSUE 2 (architectural, the human's point): both this fix and issue089's infer ADOPTION from file presence. TRACKED as dcActivationManifest (srPortActivationManifest), promoted to frontier top — adoption should be a DECLARED fact, and the manifest subsumes both patches. Estimate 2 pts, delivered."; }
    part raRetroGateR1 : TestResult { :>> id = "0d7d000f-0814-5d0f-9b3e-0000002d000f"; :>> outcome = VerdictKind::pass; :>> judgedAgainst = "b98f526"; :>> judgedAt = "2026-08-14"; :>> judgedBy = "claudeOpus5"; }
}
