// ProjectDeliveryS165 — Sprint 165: D0103 (CHANGE) — decision-rationale hard guard. Guarantees the human's
// "strong why" requirement: every Decision must carry a SUBSTANTIVE context + rationale (>=20 chars each),
// not just the schema-present fields. NEW hard guard (GUARD_NAMES 13->14). The same review REJECTED retiring
// #Supersede (it is the required Decision->Need scope-cut edge, sr02). EXECUTE (CHANGE). 2 pts. AUTONOMOUS (D0049).
package ProjectDeliveryS165 {
    private import EngineElement::*;
    private import EngineWork::*;
    private import EngineVerification::*;
    private import EngineRelationships::*;

    #CharteredBy dependency from decisionRationaleStory to d0103;

    part decisionRationaleStory : Story {
        :>> id = "63940516-2c7d-4e8f-c165-51627384c001";
        :>> title = "Sprint 165: D0103 decision-rationale hard guard — guarantee a substantive why on every Decision";
        :>> createdAt = "2026-06-25"; :>> createdBy = "wweatherholtz"; :>> kind = WorkKind::code; :>> priority = WorkPriority::p2; :>> owner = "claudeOpus"; :>> estimatedPoints = 2;
    }

    action def DeliveryRunS165 {
        action storyDecisionRationale;
        verification storyDecisionRationaleDoD : Test { :>> id = "63940516-2c7d-4e8f-c165-51627384c002"; :>> method = VerificationMethod::test; :>> procedureText = "CHANGE per D0103 (accepted by wweatherholtz: 'Add non-empty-rationale guard'; kernel-validated). The human's requirement: decisions must carry a strong WHY for future improvement + reevaluation. DELIVERED: view::decisions_weak_rationale (decisions with context OR rationale trimmed <20 chars) + guards::decision_rationale (HARD; GUARD_NAMES 13->14) — a Decision without a substantive why is a violation. CORRECTION recorded: the same selection's 'retire #Supersede' was WITHDRAWN — #Supersede is the required Decision->Need scope-cut edge (sr02DecisionRecord statement + §2.4 + tracking-template); only Decision->Decision supersession uses the status field (D0070). #Supersede unchanged. doc-sync: CLAUDE.md §5 (14 forward guards: 13 hard + decision-requirement-link warning; the decision-rationale guard). VERIFIED LIVE: `keel guard decision-rationale` = 103 decisions scanned, 0 violations (all pass — pre-scan confirmed all >=20 chars); guard all (14) ALL PASS; clippy -D warnings + cargo test (68 lib) + keel validate (178) green; D0103 kernel-validated."; }
        part storyDecisionRationaleDoDR1 : TestResult { :>> id = "63940516-2c7d-4e8f-c165-51627384c003"; :>> outcome = VerdictKind::pass; :>> judgedAgainst = "c2f3b82"; :>> judgedAt = "2026-06-25"; :>> judgedBy = "claudeOpus"; }
    }

    verification decisionRationaleRefineGate : Test { :>> id = "63940516-2c7d-4e8f-c165-51627384c004"; :>> title = "Sprint 165 refine gate (DoR)"; :>> createdAt = "2026-06-25"; :>> createdBy = "claudeOpus"; :>> method = VerificationMethod::inspect; :>> procedureText = "DoR: human requirement (strong why, guaranteed) -> D0047 automated control. Pre-scan: all 102 decisions already >=20 chars context+rationale, so a hard guard binds with zero flood. Design accepted as D0103. estimatedPoints=2. #CharteredBy d0103. DoR met."; }
    part decisionRationaleRefineGateR1 : TestResult { :>> id = "63940516-2c7d-4e8f-c165-51627384c005"; :>> outcome = VerdictKind::pass; :>> judgedAgainst = "c2f3b82"; :>> judgedAt = "2026-06-25"; :>> judgedBy = "claudeOpus"; }
    verification decisionRationaleStandupGate : Test { :>> id = "63940516-2c7d-4e8f-c165-51627384c006"; :>> title = "Sprint 165 standup gate"; :>> createdAt = "2026-06-25"; :>> createdBy = "claudeOpus"; :>> method = VerificationMethod::inspect; :>> procedureText = "Approach: view::decisions_weak_rationale + guards::decision_rationale (hard, GUARD_NAMES+1) + run_one; doc-sync CLAUDE.md; D0103 + kernel-validate. The supersede-retire was dropped on evidence (sr02). No blockers."; }
    part decisionRationaleStandupGateR1 : TestResult { :>> id = "63940516-2c7d-4e8f-c165-51627384c007"; :>> outcome = VerdictKind::pass; :>> judgedAgainst = "c2f3b82"; :>> judgedAt = "2026-06-25"; :>> judgedBy = "claudeOpus"; }
    verification decisionRationaleImplementGate : Test { :>> id = "63940516-2c7d-4e8f-c165-51627384c008"; :>> title = "Sprint 165 implement gate"; :>> createdAt = "2026-06-25"; :>> createdBy = "claudeOpus"; :>> method = VerificationMethod::test; :>> procedureText = "Implemented the hard guard. LIVE: decision-rationale = 103 scanned, 0 violations; guard all (14) ALL PASS. clippy -D warnings clean (fixed 2 first-pass lints: indexing-may-panic, doc-paragraph); cargo test (68 lib) + keel validate (178) green; D0103 kernel-validated."; }
    part decisionRationaleImplementGateR1 : TestResult { :>> id = "63940516-2c7d-4e8f-c165-51627384c009"; :>> outcome = VerdictKind::pass; :>> judgedAgainst = "c2f3b82"; :>> judgedAt = "2026-06-25"; :>> judgedBy = "claudeOpus"; }
    verification decisionRationaleReviewGate : Test { :>> id = "63940516-2c7d-4e8f-c165-51627384c00a"; :>> title = "Sprint 165 review gate"; :>> createdAt = "2026-06-25"; :>> createdBy = "claudeOpus"; :>> method = VerificationMethod::inspect; :>> procedureText = "Reviewed. The guard is precise (blank-check, no false positives — unlike a prose heuristic), hard (the human wants the why guaranteed), and floods nothing (all existing pass). It makes the decision-record's basis a CHECKED fact, not an assumed one — fitting for a system whose decisions must be reevaluable. The #Supersede correction was the right call: retiring it would have broken sr02's contract + the downstream template; caught before acting on the mistaken 'vestigial' read. Clean."; }
    part decisionRationaleReviewGateR1 : TestResult { :>> id = "63940516-2c7d-4e8f-c165-51627384c00b"; :>> outcome = VerdictKind::pass; :>> judgedAgainst = "c2f3b82"; :>> judgedAt = "2026-06-25"; :>> judgedBy = "claudeOpus"; }
    verification decisionRationaleCloseOutGate : Test { :>> id = "63940516-2c7d-4e8f-c165-51627384c00c"; :>> title = "Sprint 165 closeOut gate (autonomous, D0049)"; :>> createdAt = "2026-06-25"; :>> createdBy = "claudeOpus"; :>> method = VerificationMethod::inspect; :>> procedureText = "Autonomous closeOut (D0049): DoD pass; the 'strong why' is now a hard, guaranteed honest-state gate (14th forward guard). clippy + cargo test (68 lib) + keel validate (178) + guard all (14) green; D0103 kernel-validated. Self-evidencing (D0051). #Supersede correctly retained (sr02). assured READY; suspect clean."; }
    part decisionRationaleCloseOutGateR1 : TestResult { :>> id = "63940516-2c7d-4e8f-c165-51627384c00d"; :>> outcome = VerdictKind::pass; :>> judgedAgainst = "c2f3b82"; :>> judgedAt = "2026-06-25"; :>> judgedBy = "claudeOpus"; }
    verification decisionRationaleRetroGate : Test { :>> id = "63940516-2c7d-4e8f-c165-51627384c00e"; :>> title = "Sprint 165 retro gate (autonomous, D0049)"; :>> createdAt = "2026-06-25"; :>> createdBy = "claudeOpus"; :>> method = VerificationMethod::analyze; :>> procedureText = "Autonomous retro (D0049). WELL: the human's value ('strong why for reevaluation') became a precise hard guard with zero flood (the pre-scan de-risked enforcement level — confirm-all-pass-then-hard, the same move as the requirement-rootedness data-check). AVOIDABLE-ISSUE SCAN: the BIG catch — I had called #Supersede 'vestigial' + offered to retire it; scoping the retirement surfaced that sr02DecisionRecord REQUIRES #Supersede (Decision->Need cuts), so retiring would have broken a requirement's contract + the shipped template. LESSON (reusable): before retiring any 'unused' construct, grep its references across REQUIREMENTS + templates + tests, not just authored instances — a specified-but-unexercised mechanism looks unused but isn't. Caught before acting; correction recorded in D0103. Estimate 2 pts held. NEXT: B1 (the 2 FastStart re-verifies) + B2 (orphan-story charter backfill), then releaseTag010."; }
    part decisionRationaleRetroGateR1 : TestResult { :>> id = "63940516-2c7d-4e8f-c165-51627384c00f"; :>> outcome = VerdictKind::pass; :>> judgedAgainst = "c2f3b82"; :>> judgedAt = "2026-06-25"; :>> judgedBy = "claudeOpus"; }
}
