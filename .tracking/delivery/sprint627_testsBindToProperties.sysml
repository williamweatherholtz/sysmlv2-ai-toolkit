// ProjectDeliveryS627 — Sprint 627: A test that asserts program source contains a code-shaped literal is refused by the suite, and the refusal names the property to bind to (dcTestsBindToPropertiesNotSource, issue388, D0401). EXECUTE. 3 pts.
package ProjectDeliveryS627 {
    private import EngineElement::*;
    private import EngineWork::*;
    private import EngineVerification::*;
    private import EngineRelationships::*;

    #CharteredBy dependency from testsBindToPropertiesStory to d0401;

    part testsBindToPropertiesStory : Story {
        :>> id = "dbc7f1e9-9d34-4609-a6a9-ebaca377c0d7";
        :>> title = "Sprint 627: A test that asserts program source contains a code-shaped literal is refused by the suite, and the refusal names the property to bind to (dcTestsBindToPropertiesNotSource, issue388, D0401) (3 pts)";
        :>> createdAt = "2026-09-09"; :>> createdBy = "claudeOpus5"; :>> kind = WorkKind::code; :>> priority = WorkPriority::p0; :>> owner = "claudeOpus5"; :>> estimatedPoints = 3;
    }

    action def DeliveryRunS627 {
        action storyTestsBindToProperties;
        verification storyTestsBindToPropertiesDoD : Test { :>> id = "d5e4e625-7a5e-430a-845b-dfff6d6239de"; :>> method = VerificationMethod::test; :>> procedureText = "DELIVERED: `keel-cli/tests/tests_bind_to_properties.rs` walks every test region in keel-cli (src from its first `#[cfg(test)]`, tests/ whole) and REFUSES a positive `contains`/`matches` of a code-shaped literal on an identifier bound - directly or through let/for derivation - to `include_str!`/`read_to_string` of a `.rs` file; per finding it names file:line, the test, the literal, the property (its doc's first sentence) and any behavioural equivalent the doc names that exists. Tier: REFUSAL, decided first on the census (14 source-reading tests, 3 offenders, 0 overlap with the 11 legitimate shapes) and recorded in D0401 with its reason. The three offenders are rebound: main.rs the_turn_boundary test deleted (held by tests/remaining_controls_actually_fire.rs turn_boundary_gate_allows_a_clean_tree_and_blocks_a_dishonest_one and tests/stop_says_nothing_about_decisions.rs); guards.rs gains the pure `GuardReport::self_contradiction()` that print() calls and the runner test asserts its value on four report shapes; fingerprint.rs loses its serve.rs-reading test and serve.rs gains the_epoch_is_advanced_by_writes_and_not_by_reads, driving the real log_request middleware with tower oneshot (fifty GETs move the epoch by fewer than fifty, fifty POSTs by at least a hundred). VERIFIED: the control's six probes ran first (D0388) - the three known-positive fixtures are refused with the expected literals, property sentences and equivalents, the five known-negative shapes (format!-built arm, prose needle, emptiness scan, negated contains, unbound rendered output) are not, and a src-file region starts at cfg(test); the real-tree run then named exactly the three offenders (5 asserts) and none of the eleven legitimate tests before the fixes, and is green after. Full suite: 59 suites, 0 failed; clippy --all-targets -D warnings clean."; }
        // RAN: cargo test --release --test tests_bind_to_properties: 6 probes + real-tree test ok; before the fixes the real-tree run named main.rs:5165/5171, guards.rs:6048, fingerprint.rs:144/148 and nothing else; cargo test --release 59 suites 0 failed; cargo clippy --workspace --all-targets -- -D warnings exit 0
        part storyTestsBindToPropertiesDoDR1 : TestResult { :>> id = "9b4fe637-8ee2-44ac-a52c-84a5c44cd233"; :>> outcome = VerdictKind::pass; :>> judgedAgainst = "b9294ef"; :>> judgedAt = "2026-09-09"; :>> judgedBy = "claudeOpus5"; }
    }

    verification testsBindToPropertiesRefineGate : Test { :>> id = "91ad52c1-a38d-4482-8253-2f81a71aa155"; :>> title = "Sprint 627 refine gate (DoR)"; :>> createdAt = "2026-09-09"; :>> createdBy = "claudeOpus5"; :>> method = VerificationMethod::inspect; :>> procedureText = "READY. Head of keel whats-next at b9294ef. The DoD asks for the tier to be decided first on the evidence in the tree, so the census ran before any code: 14 source-reading tests, 3 of them the offending shape, and a discriminator with zero overlap. That evidence chose REFUSAL and D0401 records it with the process-change marker (a rule over the test surface), proposed for the human per D0337; the control rides the D0070 lock co-committed, as D0363/D0398/D0400 did. 3 points: a text-level scanner with probes, three test rewrites, one dev-dependency."; }
    // RAN: keel whats-next . at b9294ef: dcTestsBindToPropertiesNotSource at the head; census 14 source-reading tests / 3 offenders / 0 overlap; D0401 recorded proposed with the process-change marker; 3 points
    part testsBindToPropertiesRefineGateR1 : TestResult { :>> id = "2c9617e8-45f1-4da9-b900-f9f1be970e6b"; :>> outcome = VerdictKind::pass; :>> judgedAgainst = "b9294ef"; :>> judgedAt = "2026-09-09"; :>> judgedBy = "claudeOpus5"; }
    verification testsBindToPropertiesStandupGate : Test { :>> id = "2219e0a6-be23-448f-8c46-097cdf324bf0"; :>> title = "Sprint 627 standup gate"; :>> createdAt = "2026-09-09"; :>> createdBy = "claudeOpus5"; :>> method = VerificationMethod::inspect; :>> procedureText = "Blockers: none within the sprint. D0401 waits on the human through the brief; the control is in force under cargo test regardless of the Decision's standing, which is the precedent shape."; }
    // RAN: blockers none; D0401 waits on the human via the brief
    part testsBindToPropertiesStandupGateR1 : TestResult { :>> id = "771600b5-be37-44f3-a9d5-5a2532d6eedc"; :>> outcome = VerdictKind::pass; :>> judgedAgainst = "b9294ef"; :>> judgedAt = "2026-09-09"; :>> judgedBy = "claudeOpus5"; }
    verification testsBindToPropertiesImplementGate : Test { :>> id = "1e6776ba-6420-4402-8d46-36a1a0b888a9"; :>> title = "Sprint 627 implement gate"; :>> createdAt = "2026-09-09"; :>> createdBy = "claudeOpus5"; :>> method = VerificationMethod::test; :>> procedureText = "The scanner is text-level, not a Rust parser: string-literal-aware paren matching and top-level splitting, bindings by `let`/`const`/`static` statement, derivation to a fixpoint over `let X = ...bound...` and `for X in ...bound...` at any block depth. Two first-run defects, both fixed before the answer was stated: statement splitting at depth 0 saw no statement inside a fn body (the probes caught it - the turn-boundary and epoch fixtures came back empty), and a separator check sliced inside an em dash in a real doc comment (the real-tree run panicked; is_char_boundary guards it now). The self-contradiction line in GuardReport::print is unchanged in wording; the runner test now constructs four reports and asserts Some/None. The epoch test needed a getter (fingerprint::epoch) and tower's util feature as a dev-dependency; Cargo.lock gains one dependency line and no new crate."; }
    // RAN: cargo test --release --test tests_bind_to_properties: probes 6 passed after two fixes; real-tree run before fixes 5 findings in 3 tests (main.rs:5165/5171, guards.rs:6048, fingerprint.rs:144/148), 0 on the 11 legitimate; cargo clippy --workspace --all-targets -- -D warnings exit 0
    part testsBindToPropertiesImplementGateR1 : TestResult { :>> id = "bf935068-f9b5-4a44-b727-53ddbe6f5a2a"; :>> outcome = VerdictKind::pass; :>> judgedAgainst = "b9294ef"; :>> judgedAt = "2026-09-09"; :>> judgedBy = "claudeOpus5"; }
    verification testsBindToPropertiesReviewGate : Test { :>> id = "4c3d3b56-a2e6-4bc9-867a-39f70c9c367c"; :>> title = "Sprint 627 review gate — three passes per D0172"; :>> createdAt = "2026-09-09"; :>> createdBy = "claudeOpus5"; :>> method = VerificationMethod::inspect; :>> procedureText = "Pass 1 (intent): each VERIFY clause of the DoD is a named probe or the real-tree test - fires on the_turn_boundary shape (probe_positive_the_turn_boundary_shape...), does not fire on the doc-claim, guard-catalogue or CLI-surface shapes (probe_negative_the_legitimate_source_reading_shapes...), suite green, tier recorded with reason in D0401. Pass 2 (defects): the real-tree report before the fixes was read against the census - 5 findings in 3 tests, exactly the 3 offenders, the 11 legitimate tests silent - so the discriminator's stated overlap of zero was observed, not assumed. The control excludes its own file because its fixtures ARE the shape; a second copy of a fixture elsewhere in tests/ would be refused, which is correct. Pass 3 (docs): the DoD, the test's module doc and D0401 all state the same rule and the same tokens; the guards.rs release_tag_tests comment that misquoted release040's current title is corrected in the same commit."; }
    // RAN: real-tree report read against the census: 3 offenders named, 11 legitimate silent; cargo test --release: 59 suites ok, 0 failed
    part testsBindToPropertiesReviewGateR1 : TestResult { :>> id = "31b3aa8f-7752-4335-af7b-322c8a948991"; :>> outcome = VerdictKind::pass; :>> judgedAgainst = "b9294ef"; :>> judgedAt = "2026-09-09"; :>> judgedBy = "claudeOpus5"; }
    verification testsBindToPropertiesCloseOutGate : Test { :>> id = "f82ca3d5-2dbc-4f58-a933-d64cc4f1a992"; :>> title = "Sprint 627 closeOut gate (autonomous, D0049)"; :>> createdAt = "2026-09-09"; :>> createdBy = "claudeOpus5"; :>> method = VerificationMethod::inspect; :>> procedureText = "A test now has to say what property it holds, or the suite says it for it. The three that spelled out a mechanism are rebound to behaviour, and the next one cannot land."; }
    // RAN: keel-serve.exe validate . 712 clean; check-engine . clean; guard . --no-receipt ALL PASS
    part testsBindToPropertiesCloseOutGateR1 : TestResult { :>> id = "48314645-b551-4090-89e5-0d54166bf1a2"; :>> outcome = VerdictKind::pass; :>> judgedAgainst = "b9294ef"; :>> judgedAt = "2026-09-09"; :>> judgedBy = "claudeOpus5"; }
    verification testsBindToPropertiesRetroGate : Test { :>> id = "2f21aea6-b092-4b30-9507-bdb200f45de7"; :>> title = "Sprint 627 retro gate (autonomous, D0049)"; :>> createdAt = "2026-09-09"; :>> createdBy = "claudeOpus5"; :>> method = VerificationMethod::analyze; :>> procedureText = "Retro held; avoidable-issue scan: the check's first run was wrong twice (a depth rule that saw no statements; a slice inside a multibyte character) and both were found by the probes and the first real-tree run before any answer was stated - the D0388 discipline working as designed, so already tracked by d0388 and its probe rule; no new item. That the guard read the uppercase form as naming nothing is issue424, resolved by dcRetroNamesDecisionsAsWritten. One residual is stated rather than tracked: the scanner is textual, so a source-bound identifier passed through a helper function (not a let) is not followed - the census found no such case and the probes would show it if one appears."; }
    // RAN: retro held; two first-run defects caught by probes and first real-tree run (D0388); no new item
    part testsBindToPropertiesRetroGateR1 : TestResult { :>> id = "49725c38-9e0a-40ae-aeec-bc87356710ee"; :>> outcome = VerdictKind::pass; :>> judgedAgainst = "b9294ef"; :>> judgedAt = "2026-09-09"; :>> judgedBy = "claudeOpus5"; }
}
