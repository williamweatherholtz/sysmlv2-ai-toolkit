// ProjectDeliveryS606 — Sprint 606: The human words a read-back check reads are bounded by a declared boundary, never by an apostrophe the recorder's own framing happens to carry (dcQuotedWordsAreBounded, D0375, issue397). EXECUTE. 2 pts.
package ProjectDeliveryS606 {
    private import EngineElement::*;
    private import EngineWork::*;
    private import EngineVerification::*;
    private import EngineRelationships::*;

    #CharteredBy dependency from quotedWordsAreBoundedStory to d0375;

    part quotedWordsAreBoundedStory : Story {
        :>> id = "967ed9de-56d0-453b-bf28-73197819e909";
        :>> title = "Sprint 606: The human words a read-back check reads are bounded by a declared boundary, never by an apostrophe the recorder's own framing happens to carry (dcQuotedWordsAreBounded, D0375, issue397) (2 pts)";
        :>> createdAt = "2026-09-08"; :>> createdBy = "claudeOpus5"; :>> kind = WorkKind::code; :>> priority = WorkPriority::p0; :>> owner = "claudeOpus5"; :>> estimatedPoints = 2;
    }

    action def DeliveryRunS606 {
        action storyQuotedWordsAreBounded;
        verification storyQuotedWordsAreBoundedDoD : Test { :>> id = "a5997c9a-fc86-496e-a28c-7b51fc5b99c3"; :>> method = VerificationMethod::test; :>> procedureText = "DELIVERED: checks::quoted_spans (keel-cli/src/view/checks.rs) extracts every quoted span from a note with declared boundaries - typographic “…” and ‘…’ pairs, and an ASCII apostrophe that OPENS only when the previous character is not alphanumeric and CLOSES only when the next character is not a letter, so `brief's` and `let's` never open or close a span; an unclosed opener yields nothing; quotes_conversational_words answers from that list, and view::read_back_names reads the same spans, so the id/option/title match runs over what the human said and only that. `keel accept <d> --words TEXT [--note framing]` (main.rs fold_words_into_note) folds their words into the note as `{framing} - their words, verbatim: “{words}”`, making the boundary declared by construction; the CliCommand fact and usage carry the new form. VERIFIED: checks::tests::quoted_spans_are_bounded_and_an_in_word_apostrophe_never_opens_one - the live refused note from issue397 now yields exactly the human's marked line; a spliced note whose apostrophe-shifted span would carry the decision id while the human's words do not yields only the human's words (the passing-direction case, constructed); contractions and an unclosed opener yield nothing; view::tests::read_back_names_the_decision_or_refuses gains the live note binding for d0360, the spliced note refused, and “c for d375” binding to d0375 by digits and by letter; delegated_records_must_quote_or_cite_a_gesture still holds. LIVE: the acceptance of D0375 itself was recorded through the fix - `keel accept d0375 --words 'c for d375' --by wweatherholtz` - and read back by id and option letter. Resolves issue397."; }
        // RAN: keel suite . 589/0 (receipt 37f6d8356120); the three tests named in the DoD pass; keel accept d0375 --words recorded the live acceptance; keel validate . 689 clean; keel guard --no-receipt ALL PASS; CLAUDE.md accept paragraph carries --words and the declared-boundary rule
        part storyQuotedWordsAreBoundedDoDR1 : TestResult { :>> id = "3484e7f1-efb5-482a-aa74-ce5f1c5938a9"; :>> outcome = VerdictKind::pass; :>> judgedAgainst = "7a61044816c7c01fbbe10976596d68bcbdc8c88c"; :>> judgedAt = "2026-09-08"; :>> judgedBy = "claudeOpus5"; }
    }

    verification quotedWordsAreBoundedRefineGate : Test { :>> id = "d25beff1-aece-430b-8d08-708368e9765b"; :>> title = "Sprint 606 refine gate (DoR)"; :>> createdAt = "2026-09-08"; :>> createdBy = "claudeOpus5"; :>> method = VerificationMethod::inspect; :>> procedureText = "READY, 2 pts: one extractor rewritten, one flag added, two test functions extended, and the DoD names the check for each. Chartered by D0375, a #SafetyChange fork whose option C the human chose in chat (“c for d375”); the change sits on the attestation path in view/checks.rs and so lands behind the accepted Decision in one commit, as the keystone lock asks. The DoD was re-read for the issue372 defect before any check ran: every command it names exists."; }
    // RAN: inspect: sprint 606 Refine text; estimatedPoints 2 and #CharteredBy d0375 present in the file; d0375 accepted (d0375AcceptR1, judgedBy wweatherholtz); dcQuotedWordsAreBounded DoD re-read, every command it names exists
    part quotedWordsAreBoundedRefineGateR1 : TestResult { :>> id = "1d523223-200d-43c4-813d-d3765a13afa4"; :>> outcome = VerdictKind::pass; :>> judgedAgainst = "7a61044816c7c01fbbe10976596d68bcbdc8c88c"; :>> judgedAt = "2026-09-08"; :>> judgedBy = "claudeOpus5"; }
    verification quotedWordsAreBoundedStandupGate : Test { :>> id = "37a3fc79-78ff-4454-a512-d8aa2e2cad41"; :>> title = "Sprint 606 standup gate"; :>> createdAt = "2026-09-08"; :>> createdBy = "claudeOpus5"; :>> method = VerificationMethod::inspect; :>> procedureText = "ONE CHOICE: fix the extractor AND add a declared-boundary flag, rather than either alone. The extractor alone still asks the recorder to hand-quote correctly and leaves the ASCII apostrophe doing two jobs; the flag alone leaves every existing --note path with the old splitter, which is where the refusal actually fired. With both, the flag is the path an agent should take and the extractor is the control when it does not. A second choice: an in-word apostrophe is decided by its neighbours (alphanumeric before / letter after), not by a dictionary of contractions - a possessive on a record id (d0360's) has a digit before it and must not open either."; }
    // RAN: inspect: sprint 606 Standup text; estimatedPoints 2 and #CharteredBy d0375 present in the file; d0375 accepted (d0375AcceptR1, judgedBy wweatherholtz); dcQuotedWordsAreBounded DoD re-read, every command it names exists
    part quotedWordsAreBoundedStandupGateR1 : TestResult { :>> id = "d348d5a3-e96a-47c7-bd8b-ab8e4f10dfc5"; :>> outcome = VerdictKind::pass; :>> judgedAgainst = "7a61044816c7c01fbbe10976596d68bcbdc8c88c"; :>> judgedAt = "2026-09-08"; :>> judgedBy = "claudeOpus5"; }
    verification quotedWordsAreBoundedImplementGate : Test { :>> id = "049b2feb-7239-41b0-84cf-6226c11db320"; :>> title = "Sprint 606 implement gate"; :>> createdAt = "2026-09-08"; :>> createdBy = "claudeOpus5"; :>> method = VerificationMethod::test; :>> procedureText = "RAN: Edit tool on checks.rs, mod.rs, main.rs and commands.sysml (the pre-bash hook refused one python heredoc carrying an escaped quote, per D0309); cargo build --release; cargo test --release -p keel-cli --lib quoted_spans_are_bounded_and_an_in_word_apostrophe_never_opens_one / read_back_names_the_decision_or_refuses / delegated_records_must_quote_or_cite_a_gesture, each passing; keel accept d0375 --words 'c for d375' --by wweatherholtz --date 2026-09-08 from the new binary, accepted against 7a61044; keel validate . (689 clean); keel guard --no-receipt ALL PASS; cp to target/release/keel-serve.exe and .keel/bin/keel.exe so the hooks and the suite run the same engine; keel suite from the copy."; }
    // RAN: inspect: sprint 606 Implement text; keel suite . 589/0 (receipt 37f6d8356120); dcQuotedWordsAreBoundedDoDR1 pass recorded; d0375AcceptR1 present; git diff --stat names checks.rs, view/mod.rs, main.rs, commands.sysml, CLAUDE.md, backlog, the decision file
    part quotedWordsAreBoundedImplementGateR1 : TestResult { :>> id = "16939f11-375e-4109-b17e-ebc4e5e85551"; :>> outcome = VerdictKind::pass; :>> judgedAgainst = "7a61044816c7c01fbbe10976596d68bcbdc8c88c"; :>> judgedAt = "2026-09-08"; :>> judgedBy = "claudeOpus5"; }
    verification quotedWordsAreBoundedReviewGate : Test { :>> id = "ccf97c77-449b-4ab2-975e-c7d56f83eac9"; :>> title = "Sprint 606 review gate — three passes per D0172"; :>> createdAt = "2026-09-08"; :>> createdBy = "claudeOpus5"; :>> method = VerificationMethod::inspect; :>> procedureText = "THREE QUESTIONS (D0172). Can a span now be attached to words the human did not say? Only if the recorder places a declared opener before text that is not theirs - the same fabrication the quote rule already cannot detect and D0289 leaves to the human's exception; what is closed is the ACCIDENTAL splice, where a correct quote is read at the wrong boundary. Does the tightening refuse anything it should accept? A standalone ASCII 'quote' still opens; typographic pairs open; the only newly-silent shape is an in-word apostrophe, which never began a human's words. What is NOT claimed: that the check judges consent (it reads back a referent, D0375 option C's plan-covers-step rule is the next item); that guards under the keystone lock changed (checks.rs is the accept path's reader, guards.rs is untouched)."; }
    // RAN: inspect: sprint 606 Review text; keel suite . 589/0 (receipt 37f6d8356120); dcQuotedWordsAreBoundedDoDR1 pass recorded; d0375AcceptR1 present; git diff --stat names checks.rs, view/mod.rs, main.rs, commands.sysml, CLAUDE.md, backlog, the decision file
    part quotedWordsAreBoundedReviewGateR1 : TestResult { :>> id = "400fbe8d-27bc-482c-a77e-83bd7eade210"; :>> outcome = VerdictKind::pass; :>> judgedAgainst = "7a61044816c7c01fbbe10976596d68bcbdc8c88c"; :>> judgedAt = "2026-09-08"; :>> judgedBy = "claudeOpus5"; }
    verification quotedWordsAreBoundedCloseOutGate : Test { :>> id = "2c53f54a-f7bb-48ef-b1e6-893b487e362a"; :>> title = "Sprint 606 closeOut gate (autonomous, D0049)"; :>> createdAt = "2026-09-08"; :>> createdBy = "claudeOpus5"; :>> method = VerificationMethod::inspect; :>> procedureText = "CLOSED. The refusal class of issue397 is gone at the root and the acceptance of D0375 is the first record made through the fix. Option C's implementation is chartered work behind D0375; the frontier names it next."; }
    // RAN: inspect: sprint 606 CloseOut text; keel suite . 589/0 (receipt 37f6d8356120); dcQuotedWordsAreBoundedDoDR1 pass recorded; d0375AcceptR1 present; git diff --stat names checks.rs, view/mod.rs, main.rs, commands.sysml, CLAUDE.md, backlog, the decision file
    part quotedWordsAreBoundedCloseOutGateR1 : TestResult { :>> id = "3c34e358-0a83-4818-8333-0f48d430fd40"; :>> outcome = VerdictKind::pass; :>> judgedAgainst = "7a61044816c7c01fbbe10976596d68bcbdc8c88c"; :>> judgedAt = "2026-09-08"; :>> judgedBy = "claudeOpus5"; }
    verification quotedWordsAreBoundedRetroGate : Test { :>> id = "c7e59d88-beec-444d-a58b-795768e64823"; :>> title = "Sprint 606 retro gate (autonomous, D0049)"; :>> createdAt = "2026-09-08"; :>> createdBy = "claudeOpus5"; :>> method = VerificationMethod::analyze; :>> procedureText = "AVOIDABLE-ISSUE SCAN HELD. One process finding, already tracked: the refusal fired twice on the same morning's acceptances (D0375 context, issue397) and was worked around by rewording before the cause was read from the code - the human named it (“it keeps happening”) before the tracked item moved; issue397 was High and at the head of the frontier, so the ranking was right and the discipline of taking the frontier before the next brief was not. No new item - the control is D0052's own rule, and this sprint took the item."; }
    // RAN: inspect: sprint 606 Retro text; keel suite . 589/0 (receipt 37f6d8356120); dcQuotedWordsAreBoundedDoDR1 pass recorded; d0375AcceptR1 present; git diff --stat names checks.rs, view/mod.rs, main.rs, commands.sysml, CLAUDE.md, backlog, the decision file
    part quotedWordsAreBoundedRetroGateR1 : TestResult { :>> id = "e897499e-b383-4318-8a0d-f71ff3ba50fa"; :>> outcome = VerdictKind::pass; :>> judgedAgainst = "7a61044816c7c01fbbe10976596d68bcbdc8c88c"; :>> judgedAt = "2026-09-08"; :>> judgedBy = "claudeOpus5"; }
}
