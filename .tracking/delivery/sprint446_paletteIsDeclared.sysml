// ProjectDeliveryS446 — Sprint 446: the process catalogue reports every DECLARED process, so a guard-less process is listable, showable and exportable WHOLE (issue241, D0212). EXECUTE. 2 pts.
package ProjectDeliveryS446 {
    private import EngineElement::*;
    private import EngineWork::*;
    private import EngineVerification::*;
    private import EngineRelationships::*;

    #CharteredBy dependency from paletteIsDeclaredStory to d0212;

    part paletteIsDeclaredStory : Story {
        :>> id = "c9f4f04a-ecf0-4fa5-8740-851af7199135";
        :>> title = "Sprint 446: carrying enforcement is not a precondition of travelling (2 pts)";
        :>> createdAt = "2026-08-24"; :>> createdBy = "claudeFable5"; :>> kind = WorkKind::code; :>> priority = WorkPriority::p0; :>> owner = "claudeFable5"; :>> estimatedPoints = 2;
    }

    action def DeliveryRunS446 {
        action storyPaletteIsDeclared;
        verification storyPaletteIsDeclaredDoD : Test { :>> id = "1682c9e1-c3a2-47e6-80f1-45c89f57917d"; :>> method = VerificationMethod::test; :>> procedureText = "DELIVERED: dcPaletteIsDeclared (resolves issue241, the nine-lens panel's unanimous single-ship fix). THE DEFECT: process_cmd::rows() iterated activation::unit_names(), and a unit forms only when a process asserts a guard, so `keel process show intake` exited 2 with 'no process intake' while .engine/processes/intake.sysml sat on disk - list, search, show and export all DENIED the 12 guard-less processes (intake, definition-of-done, definition-of-ready, adversarial-panel-review, architectural-critique, review-critique, migration, report, indicator, diagram, introduction, obligation-review). That breaks srPortModularProcessUnit, an accepted MUST that a unit travel whole between projects - carrying enforcement is not a precondition of travelling - and it is the un-swept half of issue149, whose remedy reached activation/activate/deactivate and never this catalogue (a D0047 correct-at-the-root failure). THE FIX: rows() iterates the already-existing, already-tested activation::declared_processes(); THREE states are reported rather than two, so a guard-bearing process reads active|INACTIVE and a guard-less one reads `always` with the reason printed - reporting a guard-less process as INACTIVE would assert this project had switched it off, which is the issue149 defect inverted; is_process_active semantics are UNCHANGED and a zero-guard process stays non-switchable, so keel deactivate keeps its accurate refusal rather than succeeding and changing nothing; the list header states its population and split instead of a bare total; guard-less processes now resolve their deploying skill from the registry so they EXPORT WHOLE; and activation-manifest's scan count reads the declared population. VERIFIED end-to-end on the real repo with a freshness-checked binary: list prints 23 rows headed '23 declared; 11 assert guards and are switchable, 12 assert none'; show/search/export intake all exit 0 where they exited 2; export intake went from 1 file (definition only) to 2 files + unit.toml (definition + SKILL.md). Two new regression tests pin the population, the never-INACTIVE property and the carries-its-skill property; the vacuous issue149 assertion was re-pointed from knowledge-graph-memory (which since gained an assert constraint, so it passed without exercising the guard-less case) to intake, with a companion assertion so the next capture cannot re-hollow it. Full lib suite 246 passed; workspace clippy --all-targets clean; validate + all 48 guards + check-engine + rules --enforce green. NOT CHANGED (bounded): activation still governs guards and the unit set stays observably narrower than the declared set - the panel rejected merging the two catalogues because it would have broken the existing declared_processes_is_every_file_not_only_the_guard_bearing_units test and regressed issue149's recorded conclusion."; }
        part storyPaletteIsDeclaredDoDR1 : TestResult { :>> id = "e357da08-ac79-407c-b190-6b46326a64c7"; :>> outcome = VerdictKind::pass; :>> judgedAgainst = "bca4265a4f02db2dcddf566db43035103e0a76f3"; :>> judgedAt = "2026-08-24"; :>> judgedBy = "claudeFable5"; }
    }

    verification paletteIsDeclaredRefineGate : Test { :>> id = "e44870f4-2684-4688-b3f7-15d239f505dc"; :>> title = "Sprint 446 refine gate (DoR)"; :>> createdAt = "2026-08-24"; :>> createdBy = "claudeFable5"; :>> method = VerificationMethod::inspect; :>> procedureText = "DoR. Resolves issue241 (HIGH), raised by the 2026-08-24 nine-lens adoption/portability panel and named by the reducer as the single-ship answer: one call site into an already-tested helper, closing the portability and discoverability findings at once, and SUBTRACTIVE - it removes a surface's ability to disagree rather than adding a control to notice that it did. Scope: the catalogue surfaces + the deploying-skill resolution + the scan count + regression tests. 2 points."; }
    part paletteIsDeclaredRefineGateR1 : TestResult { :>> id = "3d0a89c6-5814-4fc7-a04e-f81b44cf2451"; :>> outcome = VerdictKind::pass; :>> judgedAgainst = "bca4265a4f02db2dcddf566db43035103e0a76f3"; :>> judgedAt = "2026-08-24"; :>> judgedBy = "claudeFable5"; }
    verification paletteIsDeclaredStandupGate : Test { :>> id = "abc95ec6-dd9a-4738-ac04-615e9b47e27f"; :>> title = "Sprint 446 standup gate"; :>> createdAt = "2026-08-24"; :>> createdBy = "claudeFable5"; :>> method = VerificationMethod::inspect; :>> procedureText = "Approach: point rows() at activation::declared_processes() rather than unit_names(); add a `switchable` flag to Row so the guard-less case is a THIRD state instead of being folded into INACTIVE; leave is_process_active and guard_state untouched so no enforcement changes and no adopted process flips state; resolve deploying skills from the registry when no unit exists so export carries definition + skill. Touching guards.rs (the scan count) puts this commit under the enforcement-surface lock frozen earlier today, so D0212 is co-committed as the marked Decision. No blockers."; }
    part paletteIsDeclaredStandupGateR1 : TestResult { :>> id = "1fcddd47-e38a-454a-be2d-e16302609aa5"; :>> outcome = VerdictKind::pass; :>> judgedAgainst = "bca4265a4f02db2dcddf566db43035103e0a76f3"; :>> judgedAt = "2026-08-24"; :>> judgedBy = "claudeFable5"; }
    verification paletteIsDeclaredImplementGate : Test { :>> id = "1bcc3035-dda8-4fe4-a10e-f2d646a1e75b"; :>> title = "Sprint 446 implement gate"; :>> createdAt = "2026-08-24"; :>> createdBy = "claudeFable5"; :>> method = VerificationMethod::test; :>> procedureText = "Verified by running the freshly-built binary (binary freshness checked by grepping the exe for a new string first, per the sprint445 lesson): `keel process list` prints 23 rows with the split header; `keel process show intake`, `search intake` and `export intake --out DIR` all exit 0 where they previously exited 2; the export bundle contains processes/intake.sysml + skills/intake/SKILL.md + unit.toml (2 files, was 1). cargo test --lib -> 246 passed including the two new tests; cargo clippy --workspace --all-targets -D warnings clean; validate 497 + all 48 guards + check-engine + rules --enforce green; activation-manifest now reports 23 scanned (was 11). Test side-effects (a minted unit-id, an installed-units file) were reverted before commit rather than committed silently."; }
    part paletteIsDeclaredImplementGateR1 : TestResult { :>> id = "dc9c0948-fd21-4756-a56f-3b7900b16df3"; :>> outcome = VerdictKind::pass; :>> judgedAgainst = "bca4265a4f02db2dcddf566db43035103e0a76f3"; :>> judgedAt = "2026-08-24"; :>> judgedBy = "claudeFable5"; }
    verification paletteIsDeclaredReviewGate : Test { :>> id = "bfd479c5-161e-4e76-9962-0127ecfa0eb6"; :>> title = "Sprint 446 review gate — three passes per D0172"; :>> createdAt = "2026-08-24"; :>> createdBy = "claudeFable5"; :>> method = VerificationMethod::inspect; :>> procedureText = "PASS 1, CLAIMS: every exit code and the before/after export file counts are quoted read-backs from the built binary, and the binary was freshness-checked before the run. PASS 2, BOUNDARY: (i) activation semantics are deliberately untouched - the unit set stays narrower and the pinning test still passes, because the panel showed that merging the catalogues would break that test and regress issue149; (ii) the export carries definition + skill but rules are still carried BY NAME in the manifest rather than as files, which is pre-existing and stated in unit_files' own comment, not introduced here; (iii) a guard-less unit exports with '0 guard(s) the receiving project must activate', which is honest for a process whose enforcement is declared unenforceable in process-enforcement.toml. PASS 3, OWN DIFF: my first pass fixed the DENIAL but left the export incomplete - `export intake` succeeded while writing only the process file, because skills still came from the absent unit; I caught it by reading the export's own output ('1 file(s)') rather than trusting exit 0, which is the same lesson as the stale-binary miss: a zero exit code is not the claim. Added a test pinning that the guard-less unit carries its SKILL.md. WHAT A REVIEWER SHOULD ATTACK: the `.max(act.unit_names().len())` in the scan count is defensive belt-and-braces; if declared_processes ever under-counts relative to units that would mask it rather than fail."; }
    part paletteIsDeclaredReviewGateR1 : TestResult { :>> id = "7a2b2b7b-e35c-4205-844e-416b63db85a6"; :>> outcome = VerdictKind::pass; :>> judgedAgainst = "bca4265a4f02db2dcddf566db43035103e0a76f3"; :>> judgedAt = "2026-08-24"; :>> judgedBy = "claudeFable5"; }
    verification paletteIsDeclaredCloseOutGate : Test { :>> id = "374f31c3-4f2b-4ed6-a6f6-eeb32f1cbb50"; :>> title = "Sprint 446 closeOut gate (autonomous, D0049)"; :>> createdAt = "2026-08-24"; :>> createdBy = "claudeFable5"; :>> method = VerificationMethod::inspect; :>> procedureText = "Autonomous closeOut (D0049). issue241 resolved; D0212 co-committed as the marked Decision satisfying the enforcement-surface lock; validate + all 48 guards + check-engine + rules green; the remaining seven panel findings (issue239, issue240, issue242-issue246) are on the frontier in the panel's ranked order."; }
    part paletteIsDeclaredCloseOutGateR1 : TestResult { :>> id = "f8dde7e3-7bca-4c43-bf47-d0e5c632b16d"; :>> outcome = VerdictKind::pass; :>> judgedAgainst = "bca4265a4f02db2dcddf566db43035103e0a76f3"; :>> judgedAt = "2026-08-24"; :>> judgedBy = "claudeFable5"; }
    verification paletteIsDeclaredRetroGate : Test { :>> id = "42be32e3-0bcb-4c2a-8aae-73851fc0dc2c"; :>> title = "Sprint 446 retro gate (autonomous, D0049)"; :>> createdAt = "2026-08-24"; :>> createdBy = "claudeFable5"; :>> method = VerificationMethod::analyze; :>> procedureText = "Autonomous retro (D0049). AVOIDABLE-ISSUE SCAN under rcRecurrence: (1) the exit-code-is-not-the-claim class recurred - `export intake` exited 0 while writing an incomplete bundle, and I only caught it by reading the command's own '1 file(s)' output; same shape as the stale-binary false-silent in sprint445. The durable rule: read what the command SAYS it did, never only what it returned. (2) A new instance of test-side-effects-in-the-real-tree: verifying export minted a unit-id into .engine/contracts/unit-ids.toml; caught by git status before commit and reverted, but a verification that writes to the tree under test should run against a copy. WELL: the panel's single-ship recommendation was exactly right - one call site, and it closed a MUST-requirement violation, the discoverability complaint and the two-catalogue confusion together, while a reusable sprint-filler script was built along the way to cut the ceremony friction for the seven remaining findings. Estimate 2 pts, delivered 2."; }
    part paletteIsDeclaredRetroGateR1 : TestResult { :>> id = "fbe14ea1-0eed-443d-ad79-b0210dff1a55"; :>> outcome = VerdictKind::pass; :>> judgedAgainst = "bca4265a4f02db2dcddf566db43035103e0a76f3"; :>> judgedAt = "2026-08-24"; :>> judgedBy = "claudeFable5"; }
}
