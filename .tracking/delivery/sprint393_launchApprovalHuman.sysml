// ProjectDeliveryS393 — Sprint 393: the launch approval names its human and binds to the reviewed plan; the five serve-discipline SRs verified honestly - two recorded FAIL. EXECUTE. 3 pts.
package ProjectDeliveryS393 {
    private import EngineElement::*;
    private import EngineWork::*;
    private import EngineVerification::*;
    private import EngineRelationships::*;

    #CharteredBy dependency from launchApprovalHumanStory to d0182;

    part launchApprovalHumanStory : Story {
        :>> id = "c5855e8b-6ea7-4996-b02e-203a70bbc6c3";
        :>> title = "Sprint 393: approval is a named human's attestation (3 pts)";
        :>> createdAt = "2026-08-21"; :>> createdBy = "claudeFable5"; :>> kind = WorkKind::code; :>> priority = WorkPriority::p0; :>> owner = "claudeFable5"; :>> estimatedPoints = 3;
    }

    action def DeliveryRunS393 {
        action storyLaunchApprovalHuman;
        verification storyLaunchApprovalHumanDoD : Test { :>> id = "a386ba58-0f4f-4fbd-ad6e-59c05d88e09e"; :>> method = VerificationMethod::test; :>> procedureText = "DELIVERED: srServeApproveGateHuman implemented and the five serve-discipline SRs verified against the LIVE system. (1) The agent stream's approve gate was a bare approved flag ANY caller could set - an AI could approve its own routing, nothing was recorded, and an edited route kept a stale approval. Now: approved_by is required and must be a registered Person (kind refused before role), the approval binds to planHash - the identity of the exact plan the human reviewed, computed by the plan endpoint and rechecked at execution - and every launched run's records (machine-local JSON + tracked summary) carry approvedBy, so the authorization is an authored fact naming actor, time and target. (2) FOUND LIVE while probing: the console has ALWAYS sent approved=1 against a strict-bool deserializer, so every approved execution died as a wire parse error before any gate ran (issue202) - the approve gate looked structural while its only sanctioned client could not get through it; fixed to approved=true, and the page's approve flow now names its approver via judgedBy(). (3) srServeSingleSpawnPoint's required automated check exists: unit test single_agent_spawn_point counts the agent invocation marker across five source files and fails the gate on a second spawn path. (4) srServeBoundedReachableContext's escape clause satisfied: every tracked run summary now STATES the reachability residual - what is bounded, what is not, and what the enforced control actually is. (5) Five verification records authored in serve-discipline-verification.sysml with #Verify edges: three PASS on live-probe/test/inspect evidence, TWO RECORDED FAIL (srServeLaunchContract, srServeOutputValidation - the output-schema contract machinery waits on the accepted D0185 trigger, and an honest fail beats an absent edge per D0098). Read back from the computed lens: never-touched SRs 19 -> 14, examined 45% -> 48%, exercised 73% -> 75%."; }
        part storyLaunchApprovalHumanDoDR1 : TestResult { :>> id = "f07b2116-76fa-41ce-aed5-ed01d144cf49"; :>> outcome = VerdictKind::pass; :>> judgedAgainst = "174eeab"; :>> judgedAt = "2026-08-21"; :>> judgedBy = "claudeFable5"; }
    }

    verification launchApprovalHumanRefineGate : Test { :>> id = "5a30cb1d-e6b6-46e3-aa2a-199e8e6979ee"; :>> title = "Sprint 393 refine gate (DoR)"; :>> createdAt = "2026-08-21"; :>> createdBy = "claudeFable5"; :>> method = VerificationMethod::inspect; :>> procedureText = "DoR. Chartered by d0182 (run records + the launch lifecycle this hardens). Scope: exercise the five serve-discipline SRs, fix what srServeApproveGateHuman finds wanting in the gate it supersedes, record honest pass/fail for the rest. 3 points."; }
    part launchApprovalHumanRefineGateR1 : TestResult { :>> id = "d514c5a2-e83f-48bc-b539-422ecbe83fe1"; :>> outcome = VerdictKind::pass; :>> judgedAgainst = "174eeab"; :>> judgedAt = "2026-08-21"; :>> judgedBy = "claudeFable5"; }
    verification launchApprovalHumanStandupGate : Test { :>> id = "6b931d57-2a6e-4461-98fb-4e3694920de9"; :>> title = "Sprint 393 standup gate"; :>> createdAt = "2026-08-21"; :>> createdBy = "claudeFable5"; :>> method = VerificationMethod::inspect; :>> procedureText = "Approach: read each SR's statement against the shipped code FIRST, implement only what the statements demand (approver identity, plan binding, recorded fact, single-spawn check, stated residual), refuse to stamp what does not hold - the two D0185-gated clauses record FAIL rather than waiting unverified. No blockers."; }
    part launchApprovalHumanStandupGateR1 : TestResult { :>> id = "076ecf27-10a4-4ffd-8fd1-5bd784e4be0d"; :>> outcome = VerdictKind::pass; :>> judgedAgainst = "174eeab"; :>> judgedAt = "2026-08-21"; :>> judgedBy = "claudeFable5"; }
    verification launchApprovalHumanImplementGate : Test { :>> id = "fcc283ce-b9a7-4b7c-8ecc-124acac7c50b"; :>> title = "Sprint 393 implement gate"; :>> createdAt = "2026-08-21"; :>> createdBy = "claudeFable5"; :>> method = VerificationMethod::test; :>> procedureText = "All four refusal paths observed as live HTTP responses on a scratch instance (no approver / AI approver / stale plan_hash / missing plan_hash - each names srServeApproveGateHuman and the reason); planHash served by the plan endpoint and verified at execution; RUN_RECORD_FIELDS 12 -> 13 (approvedBy) with both record writers updated; single_agent_spawn_point green; cargo test 278 passed 0 failed; clippy pedantic+nursery clean; validate 429 clean."; }
    part launchApprovalHumanImplementGateR1 : TestResult { :>> id = "e409a5c4-4c63-48f3-9905-7b297c26d854"; :>> outcome = VerdictKind::pass; :>> judgedAgainst = "174eeab"; :>> judgedAt = "2026-08-21"; :>> judgedBy = "claudeFable5"; }
    verification launchApprovalHumanReviewGate : Test { :>> id = "ee1ef6f3-22d9-4965-9787-8a2dcdb18b9b"; :>> title = "Sprint 393 review gate — three passes per D0172"; :>> createdAt = "2026-08-21"; :>> createdBy = "claudeFable5"; :>> method = VerificationMethod::inspect; :>> procedureText = "PASS 1, CLAIMS: every verification claim in serve-discipline-verification.sysml cites live probe output or a named unit test, and the two FAILs cite the accepted decision (D0185) that gates their machinery - none read the SR's own rationale as evidence. PASS 2, BOUNDARY: probed the settings boundary - the agent-bridge-off refusal fires BEFORE the approver check, so the bridge toggle cannot be used to skip approval (the order is refuse-earliest); also probed that plan/read endpoints still parse with no approval fields present. PASS 3, OWN DIFF: the plan-hash computation was first inserted where q.action had already been moved (compile error, machine-caught) and the heredoc ate the separator escape in plan_identity, silently changing the hash input to plain concatenation - caught by grep-after-write, fixed via chr(92) line surgery; the authoring-mangling family again, and the standing rule (Write tool for fix scripts) was violated before being re-honoured. WHAT A REVIEWER SHOULD ATTACK: issue202 means NO console approval ever executed, so the approve path had zero field exercise before today - the live probes are its first evidence; and the Person check binds to the registry rather than attestation-policy.toml (stated as a residual in the verification record)."; }
    part launchApprovalHumanReviewGateR1 : TestResult { :>> id = "c1da74f8-403f-4341-9eae-9e15520ad9aa"; :>> outcome = VerdictKind::pass; :>> judgedAgainst = "174eeab"; :>> judgedAt = "2026-08-21"; :>> judgedBy = "claudeFable5"; }
    verification launchApprovalHumanCloseOutGate : Test { :>> id = "22ebc866-b8d4-4e18-80ca-7c01db8b3b8e"; :>> title = "Sprint 393 closeOut gate (autonomous, D0049)"; :>> createdAt = "2026-08-21"; :>> createdBy = "claudeFable5"; :>> method = VerificationMethod::inspect; :>> procedureText = "Autonomous closeOut (D0049). issue202 recorded with this story as resolver; five #Verify edges landed; verification lens read back (neither: 19 -> 14); console restarted on the new binary; validate + guards green."; }
    part launchApprovalHumanCloseOutGateR1 : TestResult { :>> id = "7a607ee5-2cd5-4565-ac81-8dd7eeca82c0"; :>> outcome = VerdictKind::pass; :>> judgedAgainst = "174eeab"; :>> judgedAt = "2026-08-21"; :>> judgedBy = "claudeFable5"; }
    verification launchApprovalHumanRetroGate : Test { :>> id = "d6bd3068-bc66-45c7-8104-8234f195a9bf"; :>> title = "Sprint 393 retro gate (autonomous, D0049)"; :>> createdAt = "2026-08-21"; :>> createdBy = "claudeFable5"; :>> method = VerificationMethod::analyze; :>> procedureText = "Autonomous retro (D0049). AVOIDABLE-ISSUE SCAN under rcRecurrence: issue202 is the verify-the-wrong-surface family - the approve gate was verified by reading the server code while the CLIENT could not reach it; the preventing practice this sprint applied and the records now carry: a gate's evidence is a live round-trip THROUGH its sanctioned client path, never the handler alone. Second family instance: the heredoc escape-mangling recurred because a fix script went through a shell heredoc instead of the Write tool - the standing rule exists, the violation was mine, and the review gate says so plainly. WELL: exercising SRs against the live system found a High defect (issue202) that three sprints of code-reading had sat on top of - the verification campaign pays for itself in its first increment. Estimate 3 pts, delivered 3."; }
    part launchApprovalHumanRetroGateR1 : TestResult { :>> id = "d22a26c1-9529-47ce-80c3-69c4e370b925"; :>> outcome = VerdictKind::pass; :>> judgedAgainst = "174eeab"; :>> judgedAt = "2026-08-21"; :>> judgedBy = "claudeFable5"; }
}
