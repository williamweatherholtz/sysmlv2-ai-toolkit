// ProjectDeliveryS226 — Sprint 226: reviewQueueSurface — the human REVIEW QUEUE + accept/reject loop in
// keel serve (D0121; schema CR D0122 for reject). A computed review-queue view (proposed Decisions +
// unjudged confirmation gates, ceremony-filtered from the DECLARED workflow phases), a "Review" console
// tab, and write-backs that record the human's accept/reject + rationale as fact (D0106). Delivered in
// one increment (D0121 planned it as 226-228). EXECUTE. 5 pts.
package ProjectDeliveryS226 {
    private import EngineElement::*;
    private import EngineWork::*;
    private import EngineVerification::*;
    private import EngineRelationships::*;

    #CharteredBy dependency from reviewQueueStory to d0121;

    part reviewQueueStory : Story {
        :>> id = "63940516-2c7d-4e8f-c226-51627384c001";
        :>> title = "Sprint 226: reviewQueueSurface (5 pts) - review queue + accept/reject loop in keel serve (D0121/D0122)";
        :>> createdAt = "2026-07-15"; :>> createdBy = "wweatherholtz"; :>> kind = WorkKind::code; :>> priority = WorkPriority::p1; :>> owner = "claudeOpus"; :>> estimatedPoints = 5;
    }

    action def DeliveryRunS226 {
        action storyReviewQueue;
        verification storyReviewQueueDoD : Test { :>> id = "63940516-2c7d-4e8f-c226-51627384c002"; :>> method = VerificationMethod::demo; :>> procedureText = "Implements the D0121 human review loop (reject path needs the D0122 schema CR). BUILT: (1) view::review_queue_json — user-gated items = proposed Decisions + UNJUDGED confirmation gates; each gate tagged ceremony via is_ceremony_gate, whose phase vocabulary is DERIVED from the project's DECLARED workflow (declared_workflow_phases scans .engine/workflows action defs) — NOT a hardcoded keel list (the fix for 'dynamically adjust to existing processes'); GET /api/review-queue. (2) A 'Review' console tab: cards + a show-ceremony/all toggle + per-item context, with Accept ▶ and Reject ✕ controls. (3) Write-backs recording the human's judgment as fact (D0106 — the click + note/rationale IS the attestation, judgedBy a Person, never AI-fabricated, never auto-commit): accept a Decision (write::accept_decision -> status=accepted + {d}Accept event) POST /api/decision/accept; reject a Decision (write::reject_decision -> status=rejected + {d}Reject event) POST /api/decision/reject; accept/reject a gate (append_gate_result pass|fail + note) POST /api/gate-result. KEEL_API 1.8.0. VERIFY (demo): unit tests (schema_scan, ceremony_gate_derives_from_declared_phases); live browser Review tab rendered the 4 proposed Decisions + N-18 gate with Accept/Reject; write-backs exercised against a THROWAWAY repo copy (accept -> accepted + AcceptR1; reject -> rejected + RejectR1; gate fail) with the copy validating clean — no pollution of this repo. clippy/build green; keel validate + guard + check-engine green."; }
        part storyReviewQueueDoDR1 : TestResult { :>> id = "63940516-2c7d-4e8f-c226-51627384c003"; :>> outcome = VerdictKind::pass; :>> judgedAgainst = "16b106c"; :>> judgedAt = "2026-07-15"; :>> judgedBy = "claudeOpus"; :>> notes = "reject path (DecisionStatus::rejected) gated on D0122 human acceptance before commit (frozen schema/core)."; }
    }

    verification rqRefineGate : Test { :>> id = "63940516-2c7d-4e8f-c226-51627384c004"; :>> title = "Sprint 226 refine gate (DoR)"; :>> createdAt = "2026-07-15"; :>> createdBy = "claudeOpus"; :>> method = VerificationMethod::inspect; :>> procedureText = "DoR: the human wants an oversight loop — launch serve, review user-gated items at a URL, accept/reject with rationale recorded as fact, then resume (D0121). Scope: review-queue view + Review tab + accept/reject write-backs; reject needs DecisionStatus::rejected (D0122 CR). #CharteredBy d0121. DoR met."; }
    part rqRefineGateR1 : TestResult { :>> id = "63940516-2c7d-4e8f-c226-51627384c005"; :>> outcome = VerdictKind::pass; :>> judgedAgainst = "16b106c"; :>> judgedAt = "2026-07-15"; :>> judgedBy = "claudeOpus"; }
    verification rqStandupGate : Test { :>> id = "63940516-2c7d-4e8f-c226-51627384c006"; :>> title = "Sprint 226 standup gate"; :>> createdAt = "2026-07-15"; :>> createdBy = "claudeOpus"; :>> method = VerificationMethod::inspect; :>> procedureText = "Approach: reuse append_gate_result (extended with optional notes + verdict) for gates; add accept_decision/reject_decision for the status flip + event; derive ceremony phases from declared workflows (not hardcoded); Review tab mirrors the disposition UX. Test write-backs against a copy to avoid polluting the repo. No blockers."; }
    part rqStandupGateR1 : TestResult { :>> id = "63940516-2c7d-4e8f-c226-51627384c007"; :>> outcome = VerdictKind::pass; :>> judgedAgainst = "16b106c"; :>> judgedAt = "2026-07-15"; :>> judgedBy = "claudeOpus"; }
    verification rqImplementGate : Test { :>> id = "63940516-2c7d-4e8f-c226-51627384c008"; :>> title = "Sprint 226 implement gate"; :>> createdAt = "2026-07-15"; :>> createdBy = "claudeOpus"; :>> method = VerificationMethod::demo; :>> procedureText = "review_queue_json + declared_workflow_phases + is_ceremony_gate + accept_decision + reject_decision + 5 serve endpoints + Review tab + DecisionStatus::rejected implemented. clippy -D warnings clean; unit tests pass; live browser + copy-based write tests pass; validate/check-engine green."; }
    part rqImplementGateR1 : TestResult { :>> id = "63940516-2c7d-4e8f-c226-51627384c009"; :>> outcome = VerdictKind::pass; :>> judgedAgainst = "16b106c"; :>> judgedAt = "2026-07-15"; :>> judgedBy = "claudeOpus"; }
    verification rqReviewGate : Test { :>> id = "63940516-2c7d-4e8f-c226-51627384c00a"; :>> title = "Sprint 226 review gate"; :>> createdAt = "2026-07-15"; :>> createdBy = "claudeOpus"; :>> method = VerificationMethod::inspect; :>> procedureText = "Reviewed. Closes the D0093 human-oversight loop: the human observes user-gated items at a URL and accepts/rejects with rationale recorded as fact via the write API (D0106 — never AI-fabricated). Two human-driven corrections were folded in THIS session: (a) ceremony detection is model-driven from the DECLARED workflow (not hardcoded), which honestly surfaced that 'retro' isn't declared in the Delivery workflow; (b) Reject-with-rationale added symmetrically. The reject status flip correctly routed through a frozen-schema CR (D0122), not freelanced. Clean."; }
    part rqReviewGateR1 : TestResult { :>> id = "63940516-2c7d-4e8f-c226-51627384c00b"; :>> outcome = VerdictKind::pass; :>> judgedAgainst = "16b106c"; :>> judgedAt = "2026-07-15"; :>> judgedBy = "claudeOpus"; }
    verification rqCloseOutGate : Test { :>> id = "63940516-2c7d-4e8f-c226-51627384c00c"; :>> title = "Sprint 226 closeOut gate (autonomous, D0049)"; :>> createdAt = "2026-07-15"; :>> createdBy = "claudeOpus"; :>> method = VerificationMethod::inspect; :>> procedureText = "Autonomous closeOut (D0049): DoD pass; the review loop (queue + Review tab + accept/reject write-backs) is built + verified. Reject's schema change (D0122) awaits explicit human sign-off before commit (frozen schema/core). NEXT: on D0122 acceptance, commit; then hand the human the serve URL to review/accept-or-reject the pending items (D0118-D0122 + N-18)."; }
    part rqCloseOutGateR1 : TestResult { :>> id = "63940516-2c7d-4e8f-c226-51627384c00d"; :>> outcome = VerdictKind::pass; :>> judgedAgainst = "16b106c"; :>> judgedAt = "2026-07-15"; :>> judgedBy = "claudeOpus"; }
    verification rqRetroGate : Test { :>> id = "63940516-2c7d-4e8f-c226-51627384c00e"; :>> title = "Sprint 226 retro gate (autonomous, D0049)"; :>> createdAt = "2026-07-15"; :>> createdBy = "claudeOpus"; :>> method = VerificationMethod::analyze; :>> procedureText = "Autonomous retro (D0049). WELL: built the exact human-oversight loop the user described, and absorbed two mid-build corrections without freelancing — model-driven ceremony detection (user: 'dynamically adjust to existing processes') and Reject-with-rationale (user: 'we have accept but not reject'). The reject status-flip correctly triggered a frozen-schema CR (D0122) with sign-off rather than a silent enum edit. Tested model-mutating write-backs against a throwaway copy. AVOIDABLE-ISSUE: making ceremony model-driven surfaced that the Delivery workflow doesn't declare 'retro' (so retro gates aren't recognized) — a real declaration gap to address (declare retro, or migrate legacy confirmation retro gates to analyze). LESSON: derive process-specific vocabulary from the declared model, never hardcode it — and let the honest surfacing of gaps drive follow-ups. Estimate 5 pts. NEXT: D0122 sign-off -> commit -> hand off the review URL."; }
    part rqRetroGateR1 : TestResult { :>> id = "63940516-2c7d-4e8f-c226-51627384c00f"; :>> outcome = VerdictKind::pass; :>> judgedAgainst = "16b106c"; :>> judgedAt = "2026-07-15"; :>> judgedBy = "claudeOpus"; }
}
