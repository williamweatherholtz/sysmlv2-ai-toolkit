// ProjectDeliveryS477 - Sprint 477: three bodies of the gate with three different bars, and the PUSH gate was the weakest - it omitted the one layer a downstream project can author. EXECUTE. 3 pts.
package ProjectDeliveryS477 {
    private import EngineElement::*;
    private import EngineWork::*;
    private import EngineVerification::*;
    private import EngineRelationships::*;

    #CharteredBy dependency from oneGateStory to d0234;

    part oneGateStory : Story {
        :>> id = "0cb94804-bfb4-4056-becf-682a19913592";
        :>> title = "Sprint 477: one gate body, three callers - and the declared-rule layer now reaches the push gate (3 pts)";
        :>> createdAt = "2026-08-27"; :>> createdBy = "claudeOpus5"; :>> kind = WorkKind::code; :>> priority = WorkPriority::p2; :>> owner = "claudeOpus5"; :>> estimatedPoints = 3;
    }

    action def DeliveryRunS477 {
        action storyOneGate;
        verification storyOneGateDoD : Test { :>> id = "4a8bd5aa-941a-4273-93b1-3874f525e732"; :>> method = VerificationMethod::test; :>> procedureText = "DELIVERED: dcOneGateDefinition (issue282). workspace::gate_problems is now the ONE body - validate, every guard, and the DECLARED rules - returning a problem LIST rather than printing, which is what lets one body serve callers that format differently. Three callers: gate --workspace (what the scaffolded pre-commit hook runs since D0238), sync, and land, the last two via gate_passes which previously ran a parallel definition containing ZERO occurrences of the word rules. The declared-rule layer is how a downstream project adds a blocking control without writing Rust, so such a project had its only control enforced at commit and unenforced on the merged tree - the exact class the merged-tree gate exists to catch. sync's doc comment claimed it was deliberately the SAME entry point as the commit hook; that is now true of the code."; }
    // RAN: cargo test --release => 14 suites 0 failures, incl the new keel-cli/tests/one_gate_definition.rs | ISOLATED fixture, asserted not assumed: a downstream ElementRule (everyStoryHasAnOwnerRule, predicate nonBlank(owner)) with NO Rust behind it, violated by an ownerless Story - validate CLEAN, all guards CLEAN, only the declared-rule layer objects | all three callers refuse: gate --workspace => exit 1 'RULE everyStoryHasAnOwnerRule' and now names the layer as (rules); land => exit 1 REFUSING to push; sync => exit 1 'the integrated tree does NOT pass the gate' | disable-and-rerun with the OLD sync body restored from backup: land exited 0 and PUSHED the violating tree ('keel land: landed.'), which is the definitive proof the old gate ignored the declared-rule layer; restored => exit 1 again | an earlier untriaged-Issue fixture was DISCARDED as non-isolating, because it also tripped guard:issues and guard:actors and so would have failed the old gate too | cargo clippy --release --all-targets => 0 errors.
        part storyOneGateDoDR1 : TestResult { :>> id = "b824d223-4e52-4d96-95f5-ee09babbd07d"; :>> outcome = VerdictKind::pass; :>> judgedAgainst = "3bb8e77"; :>> judgedAt = "2026-08-27"; :>> judgedBy = "claudeOpus5"; }
    }

    verification oneGateRefineGate : Test { :>> id = "cc3a1832-8df0-449d-8c9c-89c172e40b21"; :>> title = "Sprint 477 refine gate (DoR)"; :>> createdAt = "2026-08-27"; :>> createdBy = "claudeOpus5"; :>> method = VerificationMethod::inspect; :>> procedureText = "DoR: dcOneGateDefinition ranked first after sprint 476, and it completes the gate arc of sprints 472-476 - which is also why it was taken now rather than left: sprint 475 explicitly avoided adding a FOURTH gate body, and that constraint only pays off if the three collapse to one. Confirmed the panel's measurement first: sync.rs contained zero occurrences of `rules`. No new Decision - D0234 already asserts one standard, and this brings the code to it. Resolver: dcOneGateDefinition. estimatedPoints=3. #CharteredBy d0234."; }
    part oneGateRefineGateR1 : TestResult { :>> id = "74cba948-96f6-4cf5-b226-ad963851e753"; :>> outcome = VerdictKind::pass; :>> judgedAgainst = "3bb8e77"; :>> judgedAt = "2026-08-27"; :>> judgedBy = "claudeOpus5"; }
    verification oneGateStandupGate : Test { :>> id = "c6008885-b713-4f10-a006-af5e099d918e"; :>> title = "Sprint 477 standup gate"; :>> createdAt = "2026-08-27"; :>> createdBy = "claudeOpus5"; :>> method = VerificationMethod::inspect; :>> procedureText = "Approach: make the one body return a problem LIST rather than print. That is the design decision that makes a single definition possible at all - the commit gate wants problems printed per project as it goes, sync and land want them aggregated across the workspace with a project tag, and a printing function cannot serve both. Formatting is the caller's; the BAR is not. gate_one keeps the printing and now also names the FIRST failing layer in the order the gate applies them, so the reader knows which tool to reach for."; }
    part oneGateStandupGateR1 : TestResult { :>> id = "af2b1335-c994-4f8c-819d-1f31dae2c257"; :>> outcome = VerdictKind::pass; :>> judgedAgainst = "3bb8e77"; :>> judgedAt = "2026-08-27"; :>> judgedBy = "claudeOpus5"; }
    verification oneGateImplementGate : Test { :>> id = "9a50e99c-e4ac-4716-8d3b-0a91e23bcd7b"; :>> title = "Sprint 477 implement gate"; :>> createdAt = "2026-08-27"; :>> createdBy = "claudeOpus5"; :>> method = VerificationMethod::test; :>> procedureText = "Implemented, then verified with a fixture whose ISOLATION was asserted rather than assumed. The first fixture - an untriaged Issue - was DISCARDED: it also trips guard:issues and guard:actors, so it would have failed the old gate too and proved nothing. The kept fixture is a downstream-authored ElementRule with no Rust behind it, violated so that validate is clean and every guard is clean. The engine's own attribute-vocabulary guard caught my first attempt at authoring that rule - I used requiredAttribute, which ElementRule does not declare, and the guard named the nine fields it does. Then disable-and-rerun by restoring the OLD sync body from backup: land exited 0 and PUSHED the violating tree."; }
    // RAN: cargo test --release => 14 suites 0 failures, incl the new keel-cli/tests/one_gate_definition.rs | ISOLATED fixture, asserted not assumed: a downstream ElementRule (everyStoryHasAnOwnerRule, predicate nonBlank(owner)) with NO Rust behind it, violated by an ownerless Story - validate CLEAN, all guards CLEAN, only the declared-rule layer objects | all three callers refuse: gate --workspace => exit 1 'RULE everyStoryHasAnOwnerRule' and now names the layer as (rules); land => exit 1 REFUSING to push; sync => exit 1 'the integrated tree does NOT pass the gate' | disable-and-rerun with the OLD sync body restored from backup: land exited 0 and PUSHED the violating tree ('keel land: landed.'), which is the definitive proof the old gate ignored the declared-rule layer; restored => exit 1 again | an earlier untriaged-Issue fixture was DISCARDED as non-isolating, because it also tripped guard:issues and guard:actors and so would have failed the old gate too | cargo clippy --release --all-targets => 0 errors.
    part oneGateImplementGateR1 : TestResult { :>> id = "c81c7a8c-c252-4458-be4e-7157aa0b1248"; :>> outcome = VerdictKind::pass; :>> judgedAgainst = "3bb8e77"; :>> judgedAt = "2026-08-27"; :>> judgedBy = "claudeOpus5"; }
    verification oneGateReviewGate : Test { :>> id = "1e89c6bc-3bda-4cc1-896f-e168a52bb7f4"; :>> title = "Sprint 477 review gate"; :>> createdAt = "2026-08-27"; :>> createdBy = "claudeOpus5"; :>> method = VerificationMethod::inspect; :>> procedureText = "Diff reviewed. The old body is deleted rather than left beside the new one, which is the whole point - two definitions that can drift is the defect, and keeping one as a fallback would have preserved it. A stale doc comment above the old gate_one was removed in the same commit rather than left describing a function that no longer exists. The scaffolded hook needed no change, because D0238 had already pointed it at gate --workspace; that is the first time in this arc that an earlier sprint's decision paid for a later one."; }
    part oneGateReviewGateR1 : TestResult { :>> id = "1beb0bf7-e3da-4e75-8dce-6e8329eb4d50"; :>> outcome = VerdictKind::pass; :>> judgedAgainst = "3bb8e77"; :>> judgedAt = "2026-08-27"; :>> judgedBy = "claudeOpus5"; }
    verification oneGateCloseOutGate : Test { :>> id = "eeb5aeda-b760-449b-b31b-38f6f883d16e"; :>> title = "Sprint 477 closeOut gate (autonomous, D0049)"; :>> createdAt = "2026-08-27"; :>> createdBy = "claudeOpus5"; :>> method = VerificationMethod::inspect; :>> procedureText = "Autonomous closeOut (D0049): the DoD is recorded pass with its RAN receipt; the frontier was read back from keel whats-next. The gate arc is closed: discovery (472), wiring (472), the unowned surface (473), the blind compensating control (473), gate-before-push (475), and one definition (477). Remaining from the panel: dcPanelRecordCorrections and dcEveryAdvertisedViewIsBound. Self-evidencing (D0051): no human confirmation claimed."; }
    part oneGateCloseOutGateR1 : TestResult { :>> id = "f997af33-968b-49be-ba79-7aa67969a026"; :>> outcome = VerdictKind::pass; :>> judgedAgainst = "3bb8e77"; :>> judgedAt = "2026-08-27"; :>> judgedBy = "claudeOpus5"; }
    verification oneGateRetroGate : Test { :>> id = "8c4e7cd0-7d2b-4f54-873b-911f4396279f"; :>> title = "Sprint 477 retro gate (autonomous, D0049)"; :>> createdAt = "2026-08-27"; :>> createdBy = "claudeOpus5"; :>> method = VerificationMethod::analyze; :>> procedureText = "Autonomous retro (D0049). WELL: discarding the first fixture was the single most valuable decision in this sprint. It PASSED - all three callers refused - and it was worthless, because the violation also tripped two guards, so the old gate would have refused too. A test that passes for the wrong reason is indistinguishable from one that passes for the right reason unless you check what ELSE the fixture trips, and the check took two commands. FINDING: the doc comment on the sync gate asserted the property the code lacked - the third instance in four sprints of prose claiming a property the code did not have (D0234 clause 4 in sprint 475, the issue277 compensating control in sprint 473, this comment). All three read as authoritative and all three were checked by nothing. AVOIDABLE-ISSUE SCAN: the comment even said DELIBERATELY, which is the tell - it was written to forestall exactly the question it was wrong about, so a reader who wondered was talked out of checking. Candidate forward control, stated not built: a doc-comment claim of the form 'the same X as Y' is checkable when both are named symbols; nothing checks any of them today. Estimate 3 pts held."; }
    part oneGateRetroGateR1 : TestResult { :>> id = "a90d9b39-98cb-4e6a-bd96-9c8a55ee610c"; :>> outcome = VerdictKind::pass; :>> judgedAgainst = "3bb8e77"; :>> judgedAt = "2026-08-27"; :>> judgedBy = "claudeOpus5"; }
}
