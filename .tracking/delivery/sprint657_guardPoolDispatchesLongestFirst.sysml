// ProjectDeliveryS657 — Sprint 657: Close dcGuardPoolDispatchesLongestFirst (issue455) on its own DoD: PROBE FIRST, DO only if the probe says ordering matters, done when the wall-clock floor of the guard pool is MEASURED and either lowered or named. The probe (scripts/probes/guard_dispatch_order.py) said ordering matters by simulation; longest-first dispatch was built from the receipt's per-guard durations, A/B-timed in six interleaved pairs against declaration order, found indistinguishable (wall medians 2567 vs 2544 ms, inside a 300 ms spread) because the git-spawning guards contend when packed into one wave, and removed. What stays is the instrument: every guard's ms in the guard receipt, the probe's --ab with its interleaving refusal, and D0431 (proposed, process-change) recording that the pool stays in declaration order on measurement.. EXECUTE. 2 pts.
package ProjectDeliveryS657 {
    private import EngineElement::*;
    private import EngineWork::*;
    private import EngineVerification::*;
    private import EngineRelationships::*;

    #CharteredBy dependency from guardPoolDispatchesLongestFirstStory to d0431;

    part guardPoolDispatchesLongestFirstStory : Story {
        :>> id = "0d420ec3-19c4-467a-850c-4f88b4dcbb11";
        :>> title = "Sprint 657: Close dcGuardPoolDispatchesLongestFirst (issue455) on its own DoD: PROBE FIRST, DO only if the probe says ordering matters, done when the wall-clock floor of the guard pool is MEASURED and either lowered or named. The probe (scripts/probes/guard_dispatch_order.py) said ordering matters by simulation; longest-first dispatch was built from the receipt's per-guard durations, A/B-timed in six interleaved pairs against declaration order, found indistinguishable (wall medians 2567 vs 2544 ms, inside a 300 ms spread) because the git-spawning guards contend when packed into one wave, and removed. What stays is the instrument: every guard's ms in the guard receipt, the probe's --ab with its interleaving refusal, and D0431 (proposed, process-change) recording that the pool stays in declaration order on measurement. (2 pts)";
        :>> createdAt = "2026-09-10"; :>> createdBy = "claudeOpus5"; :>> kind = WorkKind::code; :>> priority = WorkPriority::p0; :>> owner = "claudeOpus5"; :>> estimatedPoints = 2;
    }

    action def DeliveryRunS657 {
        action storyGuardPoolDispatchesLongestFirst;
        verification storyGuardPoolDispatchesLongestFirstDoD : Test { :>> id = "9017aa62-1f09-4e83-890c-c5ee50ede228"; :>> method = VerificationMethod::test; :>> procedureText = "The DoD of dcGuardPoolDispatchesLongestFirst is met on the NAMED branch: probe run before the real set (--probe: six 1s and one 4 on two workers, declared 7 vs LPT 5; all-equal ties); longest-first built (dispatch_order over receipt ms, untimed first) and co-drafted with D0431 per D0209 clause 2; VERIFY as written - KEEL_PERF=2 keel guard --no-receipt . three consecutive runs before and after, wall and critical path reported, sorted guard output identical (diff empty) - and then, because two windows of identical code differed by thirty percent, six interleaved pairs with the order switched by an env var on one binary: declared median 2567 ms (2521-2681, n=5, first cold run excluded), longest-first 2544 ms (2436-2736, n=6); guard sum 21.3 vs 23.3 s; git x40 5.2 vs 7.3 s; critical path acceptance-binds-to-text 1553-1679 vs 2156-2339 ms. The wall clock did not fall under 4500 ms because it was already under it (the sprint 653 figure of 5.0 s was measured before dcOneCorpusPerProcess landed); the bound it hits is named - shared-resource contention among the git-spawning, tree-walking guards, tracked by dcGitReadsStayInProcess and dcBatchGitReads - and the scheduler is not adopted. VERIFY: guards.rs has no dispatch_order and run_all's comment states the A/B numbers; receipt.rs StoredGuard carries ms and record_green fills it from guards::last_durations; cargo test last_durations_names_every_guard_that_ran and run_all_reports_are_in_guard_names_order pass; clippy -D warnings clean; keel validate and keel guard green; dcGuardPoolDispatchesLongestFirst leaves whats-next."; }
        // RAN: guard_dispatch_order.py --ab: declared median 2567 ms (n=5) vs longest-first 2544 ms (n=6), 22 ms apart inside the 300 ms spread, NO MEASURED DIFFERENCE; guard sum 21313 vs 23256 ms; git median 5221 vs 7271 ms; critical path acceptance-binds-to-text 1553-1679 vs 2156-2339 ms; cargo test 6 passed 0 failed; clippy exit 0; keel validate . clean; keel guard . ALL PASS
        part storyGuardPoolDispatchesLongestFirstDoDR1 : TestResult { :>> id = "ffa81924-7e31-4725-a056-2491c727c1ae"; :>> outcome = VerdictKind::pass; :>> judgedAgainst = "a430c387eb140bd1884df1050b99a6d1332eafa7"; :>> judgedAt = "2026-09-10T16:39:02Z"; :>> judgedBy = "claudeOpus5"; }
    }

    verification guardPoolDispatchesLongestFirstRefineGate : Test { :>> id = "57f6d4ea-6cc0-42d8-9360-d91e3defbdd7"; :>> title = "Sprint 657 refine gate (DoR)"; :>> createdAt = "2026-09-10"; :>> createdBy = "claudeOpus5"; :>> method = VerificationMethod::inspect; :>> procedureText = "Two points: a scheduler in guards.rs behind a probe, a receipt field, a Decision, timed runs. Ready: the item is head of whats-next after the refineAssessPriority reorder (keel show priority read 0 inversions), its DoD names the probe and the verify command, and the receipt (D0371) already exists to carry the durations. PROBED FIRST: python scripts/probes/guard_dispatch_order.py --probe holds on both known cases; --real over three KEEL_PERF=2 runs at HEAD a430c38 simulated declaration order 1849 ms against longest-first 1314 ms on 20 workers - the DO branch is taken."; }
    // RAN: python scripts/probes/guard_dispatch_order.py --probe: known-positive declared 7 -> LPT 5, known-negative 4 == 4, both hold; keel whats-next .: dcGuardPoolDispatchesLongestFirst first; keel advance 657 .: cursor at Refine
    part guardPoolDispatchesLongestFirstRefineGateR1 : TestResult { :>> id = "ef0116ee-382c-44af-811a-1a5422a97549"; :>> outcome = VerdictKind::pass; :>> judgedAgainst = "a430c387eb140bd1884df1050b99a6d1332eafa7"; :>> judgedAt = "2026-09-10T16:39:02Z"; :>> judgedBy = "claudeOpus5"; }
    verification guardPoolDispatchesLongestFirstStandupGate : Test { :>> id = "e1a6a7c3-5eaf-4a3d-923f-f3e195dac2da"; :>> title = "Sprint 657 standup gate"; :>> createdAt = "2026-09-10"; :>> createdBy = "claudeOpus5"; :>> method = VerificationMethod::inspect; :>> procedureText = "No blocker. The guards.rs change needs a co-committed Decision (D0209 clause 2) - D0431 is drafted with the process-change marker and stays proposed for the human; the sprint does not wait on it (the item's DoD is a measurement, and the code that lands is the measured outcome, not the scheduler). Host risk noted at the start: timing on this machine is shared with Defender and whatever JVMs are alive, so runs are consecutive and the sorted guard output is diffed each time."; }
    // RAN: keel advance 657 .: cursor at Refine, passed (none) before this record; keel check-engine .: .engine instance files validated clean; no blocker
    part guardPoolDispatchesLongestFirstStandupGateR1 : TestResult { :>> id = "f6866966-9bf0-4621-b5b9-2d2fed132d83"; :>> outcome = VerdictKind::pass; :>> judgedAgainst = "a430c387eb140bd1884df1050b99a6d1332eafa7"; :>> judgedAt = "2026-09-10T16:39:02Z"; :>> judgedBy = "claudeOpus5"; }
    verification guardPoolDispatchesLongestFirstImplementGate : Test { :>> id = "76afcedb-d9d9-4601-9745-42e0da94af8b"; :>> title = "Sprint 657 implement gate"; :>> createdAt = "2026-09-10"; :>> createdBy = "claudeOpus5"; :>> method = VerificationMethod::test; :>> procedureText = "Built: guards.rs dispatch_order (stable sort by Reverse(receipt ms), untimed first), DURATIONS mutex filled in note_critical_path and cleared per run_in_parallel, last_durations(); receipt.rs StoredGuard.ms (serde default) filled from last_durations in record_green, durations(root) reader; three unit tests. Seeded the receipt (68 of 69 guards timed). Measured three runs each way: 2147-2252 ms before, 2600-2991 ms after, guard sum 16.9 -> 28.0 s, git x40 3977 -> 9404 ms - and wrote 'slower' into the code comment. Then the same declaration-order code, rebuilt, measured 2853-3039 ms: the host had moved thirty percent with no code change (13 stale kernel JVMs swept, Defender at the top of CPU). Added an env-gated longest-first to one binary (keel-ab.exe, source restored before anything else was touched) and ran six interleaved pairs: 2567 vs 2544 ms medians, no difference inside the spread; under longest-first the longest guard itself stretched 1.6 -> 2.2 s and git x40 5.2 -> 7.3 s. Reverted: dispatch_order and receipt::durations removed, run_all comment states the A/B and the mechanism, the three dispatch tests replaced by last_durations_names_every_guard_that_ran (placed above the run_all test's doc comment, not between the comment and its #[test] - the sprint 655 slip), ms kept in the receipt. Probe script: docstring states what measurement found, --real's verdict names its independence assumption, --ab summarises two interleaved sets and REFUSES two sets whose mtimes do not interleave (probed: alternating accepted, two blocks refused; the refusal fired on this sprint's own before/after files). CLAUDE.md section 5 states the order and why. D0431 recorded (proposed). issue458 recorded in-field with D0431 as resolver. Final binary rebuilt from the restored source: KEEL_GUARD_LPT=1 prints no TEMP-AB line."; }
    // RAN: cargo test --release -p keel-cli --lib -- last_durations run_all_reports receipt::: test result ok, 6 passed 0 failed (last_durations_names_every_guard_that_ran ok); cargo clippy --release -p keel-cli -- -D warnings: exit 0; grep -c 'pub fn durations' receipt.rs: 0; guard_dispatch_order.py --ab: A median 2567 ms vs B 2544 ms, differ by 22 ms inside the 300 ms spread, NO MEASURED DIFFERENCE; grep -c 'ms = [1-9]' .keel/metrics/guard-receipt.toml: 59
    part guardPoolDispatchesLongestFirstImplementGateR1 : TestResult { :>> id = "71d71ae3-c8b5-43ab-8221-55695660adc9"; :>> outcome = VerdictKind::pass; :>> judgedAgainst = "a430c387eb140bd1884df1050b99a6d1332eafa7"; :>> judgedAt = "2026-09-10T16:39:02Z"; :>> judgedBy = "claudeOpus5"; }
    verification guardPoolDispatchesLongestFirstReviewGate : Test { :>> id = "9ecc36fb-9550-494f-b599-bca6d08f8341"; :>> title = "Sprint 657 review gate — three passes per D0172"; :>> createdAt = "2026-09-10"; :>> createdBy = "claudeOpus5"; :>> method = VerificationMethod::inspect; :>> procedureText = "Three passes (D0172). Substance: the DoD's question - does dispatch order own the wall clock - is answered no, by the only measurement shape that can answer it on a noisy host, and the answer is written where the next person will look (run_all's comment, the probe's verdict, CLAUDE.md). Stated plainly: the sprint's first two conclusions were both wrong - 'thirty percent faster' (simulation) and 'thirty percent slower' (two windows) - and the second was written into a code comment before its known-negative ran; that is issue458, and its control is the instrument's refusal, not a gate, because no gate can read where a number came from. Record: the item's DoD said done when the floor is MEASURED and either lowered or NAMED; it is named, with the two backlog items that own it cited and no third added (the issue457 lesson). Not delivered by design: no scheduling change, no new gate. The receipt gained a field an older receipt parses with as zero."; }
    // RAN: keel guard --no-receipt .: ALL PASS, 38 actionable warnings not blocking; keel validate .: 748 tracking files validated clean; issue458 at issues-claudeOpus5.sysml:1879 with #Resolves from d0431 at :1888; issue458 named in decision 0431
    part guardPoolDispatchesLongestFirstReviewGateR1 : TestResult { :>> id = "a7e2b20b-6978-482d-8fd8-cfb6b4f1b581"; :>> outcome = VerdictKind::pass; :>> judgedAgainst = "a430c387eb140bd1884df1050b99a6d1332eafa7"; :>> judgedAt = "2026-09-10T16:39:02Z"; :>> judgedBy = "claudeOpus5"; }
    verification guardPoolDispatchesLongestFirstCloseOutGate : Test { :>> id = "943b42cf-0a48-42dc-9537-fd23029e0e05"; :>> title = "Sprint 657 closeOut gate (autonomous, D0049)"; :>> createdAt = "2026-09-10"; :>> createdBy = "claudeOpus5"; :>> method = VerificationMethod::inspect; :>> procedureText = "Delivered: per-guard ms in the guard receipt (the measured profile), the probe script's --ab with interleaving refusal, run_all's measured comment, CLAUDE.md section 5, D0431 (proposed), issue458 (in-field, resolver D0431), dcGuardPoolDispatchesLongestFirst's DoD verdict on the interleaved A/B. Not delivered: the longest-first scheduler - built, measured, removed. The floor is named, not lowered; lowering it is dcGitReadsStayInProcess and dcBatchGitReads, already in the backlog."; }
    // RAN: keel gate --fast .: fast gate clean (748 files); git diff --cached --stat: 8 files changed, 334 insertions, 8 deletions
    part guardPoolDispatchesLongestFirstCloseOutGateR1 : TestResult { :>> id = "ca7b8f62-44be-4374-91a4-978295cde690"; :>> outcome = VerdictKind::pass; :>> judgedAgainst = "a430c387eb140bd1884df1050b99a6d1332eafa7"; :>> judgedAt = "2026-09-10T16:39:02Z"; :>> judgedBy = "claudeOpus5"; }
    verification guardPoolDispatchesLongestFirstRetroGate : Test { :>> id = "8ace157a-3209-45e9-b263-e8566afc2b7a"; :>> title = "Sprint 657 retro gate (autonomous, D0049)"; :>> createdAt = "2026-09-10"; :>> createdBy = "claudeOpus5"; :>> method = VerificationMethod::analyze; :>> procedureText = "Autonomous retro (D0049). AVOIDABLE-ISSUE SCAN: one Issue recorded this sprint, issue458, and it was avoidable: a timing comparison stated from two windows without the A/A case, written into a code comment before the like-for-like run - D0388's class (a number stated before its check was probed against a known case), a third time after issue455 and sprint 655's retro finding; recorded for the priority lens (D0311) and given a control that is an instrument's refusal (--ab refuses non-interleaved sets, probed both ways), with its limit stated - nothing reads a number in a comment and knows its host state. Finding 2, a recurrence, not an Issue: textpatch insert_before anchored on a #[test] line split the run_all test from its doc comment exactly as in sprint 655 - caught by reading the diff, fixed by anchoring on the doc comment's first line; two occurrences of a slip whose fix is anchor choice, and a linter for 'a doc comment followed by a blank line then #[test]' would be the control if it recurs again - noted, not built, at two. Finding 3, not avoidable: the simulation's independent-duration assumption is the kind of thing only the measurement can falsify, and the DoD's PROBE-FIRST/DO-ONLY-IF shape is what made the wrong DO branch cheap to reverse. Finding 4, hygiene: 13 stale kernel JVMs were alive on a host where timing was being read; the sweep (kill_stale_kernels.py) ran mid-sprint, after they had already coloured two windows - a timing sprint starts with the sweep, which the probe's docstring now says."; }
    // RAN: keel guard --no-receipt .: ALL PASS (retro-backlog guard among them); issue458 recorded with resolver d0431; guard_dispatch_order.py --probe: --ab accepts alternating mtimes and refuses two blocks
    part guardPoolDispatchesLongestFirstRetroGateR1 : TestResult { :>> id = "3406e647-d98f-406a-a264-51fe8c036c86"; :>> outcome = VerdictKind::pass; :>> judgedAgainst = "a430c387eb140bd1884df1050b99a6d1332eafa7"; :>> judgedAt = "2026-09-10T16:39:02Z"; :>> judgedBy = "claudeOpus5"; }
}
