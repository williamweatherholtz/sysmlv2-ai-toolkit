// ProjectDeliveryS516 — Sprint 516: the CI keel ships can run where it lands. EXECUTE. 3 pts.
// Step 5 of 5 in the D0275 migration plan — the one that makes the other four visible downstream.
package ProjectDeliveryS516 {
    private import EngineElement::*;
    private import EngineWork::*;
    private import EngineVerification::*;
    private import EngineRelationships::*;

    #CharteredBy dependency from shippedCiStory to d0281;

    part shippedCiStory : Story {
        :>> id = "4d2e6f1a-8b93-4c07-a5e1-9f3b7c2d0e84";
        :>> title = "Sprint 516: shipped CI installs the pin it finds, and builds only where the crate exists (3 pts)";
        :>> createdAt = "2026-09-01"; :>> createdBy = "claudeOpus5"; :>> kind = WorkKind::code; :>> priority = WorkPriority::p0; :>> owner = "claudeOpus5"; :>> estimatedPoints = 3;
    }

    action def DeliveryRunS516 {
        action storyShippedCi;
        verification storyShippedCiDoD : Test { :>> id = "5e3f702b-9ca4-4d18-b6f2-0a4c8d3e1f95"; :>> method = VerificationMethod::test; :>> procedureText = "DELIVERED BACKLOG ITEMS: dcShippedCiRunsWhereItLands (resolves issue326 and issue327). Step 5 of 5 in the D0275 plan. ONE ROOT UNDER BOTH DEFECTS: every CI workflow keel shipped was written for the engine's own repository and had never been observed to run anywhere else - decision-channel's two workflows built a crate no consumer has, and keel init's scaffolded gate had an install step of three echoes. DONE: one install step correct in both homes - build where keel-cli/Cargo.toml exists, otherwise read the project's pin and download that exact release asset to the same path; toolchain steps gated the same way; the scaffold does the download half and proves the binary runs before any gate step trusts it. VERIFY: three structural controls plus the fixture's fourth property, AND the step run for real - the pin read as 0.3.1 and an 11.6 MB x86-64 ELF downloaded from that release. Not a live consumer Actions run, and said so."; }
        // RAN: the_scaffolded_gate_installs_the_pinned_release_not_an_echo 1/1; the_shipped_workflows_build_here_and_download_the_pin_downstream 1/1 over both YAML files; a_lived_in_projects_own_ci_survives_migration_and_installs_the_pin 1/1; the download step executed against the real release for pin 0.3.1 and produced an ELF x86-64 executable of 11672632 bytes
        part storyShippedCiDoDR1 : TestResult { :>> id = "6f40813c-adb5-4e29-c703-1b5d9e4f20a6"; :>> outcome = VerdictKind::pass; :>> judgedAgainst = "6eafa86"; :>> judgedAt = "2026-09-01"; :>> judgedBy = "claudeOpus5"; }
    }

    verification shippedCiRefineGate : Test { :>> id = "70519240-bec6-4f3a-d814-2c6e0f5a31b7"; :>> title = "Sprint 516 refine gate (DoR)"; :>> createdAt = "2026-09-01"; :>> createdBy = "claudeOpus5"; :>> method = VerificationMethod::inspect; :>> procedureText = "READY because the two hard facts were already established when the issues were recorded: the repository is PUBLIC so a runner needs no secret, and release.yml attaches keel-linux-x86_64 per tag with releases through v0.3.1. The non-obvious requirement - install the PIN not latest, because D0251 skew would refuse every gate step - was written into both issues before any code, so the naive fix was ruled out at DoR time rather than discovered red in CI."; }
    verification shippedCiStandupGate : Test { :>> id = "8162a351-cfd7-404b-e925-3d7f106b42c8"; :>> title = "Sprint 516 standup gate"; :>> createdAt = "2026-09-01"; :>> createdBy = "claudeOpus5"; :>> method = VerificationMethod::inspect; :>> procedureText = "ONE FILE, TWO HOMES was the design choice, over the peer's offered consumer variant. Extras ship a file from path X to path X, so two variants at one destination would need a from/to mapping in unit-extras.toml - a contract change to carry two copies of a file that a three-line conditional handles. And the engine repo MUST still build from source: its decision-channel workflows gate recorder commits, and a recorder commit gated by yesterday's release binary would be a gate testing the wrong thing. The other choice: the binary lands at target/release/keel in both branches, so every downstream invocation in the workflow is untouched - a smaller diff and a smaller surface for the next reader."; }
    verification shippedCiImplementGate : Test { :>> id = "9273b462-d0e8-415c-fa36-4e8021706d39"; :>> title = "Sprint 516 implement gate"; :>> createdAt = "2026-09-01"; :>> createdBy = "claudeOpus5"; :>> method = VerificationMethod::test; :>> procedureText = "RAN: the three structural tests pass. RUN FOR REAL, because a structural test cannot tell whether a URL resolves: keel init into a scratch project, then the scaffolded step's own commands - PIN read as 0.3.1 from engine-version.toml, curl to releases/download/v0.3.1/keel-linux-x86_64 returned 11672632 bytes, `file` reports ELF 64-bit LSB pie executable x86-64. TWO DEFECTS IN MY OWN EDITS caught before commit: a Python octal escape turned the sed backreference into a 0x01 control byte in all three files (the scaffold emitted `.*//p`, which extracts nothing - found by reading the scaffolded output back, not the source); and CI_TEMPLATE was a plain r-string that the new double quotes would have terminated, widened to r#. Both are the class of defect a test would not have caught, because both would have produced a workflow that LOOKED right."; }
    verification shippedCiReviewGate : Test { :>> id = "a384c573-e1f9-426d-0b47-5f9132817e4a"; :>> title = "Sprint 516 review gate — three passes per D0172"; :>> createdAt = "2026-09-01"; :>> createdBy = "claudeOpus5"; :>> method = VerificationMethod::inspect; :>> procedureText = "THREE PASSES. (1) WHAT HAPPENS ON A PROJECT WITH NO PIN: the step fails loudly with a ::error naming the file, rather than downloading latest - a project without a pin is a project that has not declared what it runs, and guessing would reintroduce the skew the pin exists to prevent. (2) WHAT HAPPENS WHEN THE RELEASE ASSET IS MISSING for a pinned version: curl -f fails the step, red, with the URL in the log. Correct - a pin to a version with no release is a real misconfiguration. (3) IS THE CLAIM PROPORTIONATE TO THE EVIDENCE: the issues, the DoD and D0281 all say the same thing - verified by construction and by a real download, not by a runner. The first downstream project to report a green keel-gate run supplies the arming this repo cannot, and pm5FeedBack exists to carry it back."; }
    verification shippedCiCloseOutGate : Test { :>> id = "b495d684-f20a-437e-1c58-60a243928f5b"; :>> title = "Sprint 516 closeOut gate (autonomous, D0049)"; :>> createdAt = "2026-09-01"; :>> createdBy = "claudeOpus5"; :>> method = VerificationMethod::inspect; :>> procedureText = "CLOSED, and with it the D0275 migration plan: issue324 (deadlock) landed, D0252 clause A (capability refusal) landed, the realistic fixture landed with all four properties, D0273 (clean break) landed as a D0067 migration, and now the shipped CI can run where it lands. Every step was armed against its own prior behaviour. The plan's stated limit stands: the migration path is verified by fixture and by construction, and only a downstream project can supply the live evidence."; }
    verification shippedCiRetroGate : Test { :>> id = "c5a6e795-031b-4480-2d69-71b354a39c6c"; :>> title = "Sprint 516 retro gate (autonomous, D0049)"; :>> createdAt = "2026-09-01"; :>> createdBy = "claudeOpus5"; :>> method = VerificationMethod::analyze; :>> procedureText = "no new item - already tracked: this sprint's findings are the two defects it resolves (issue326, issue327) and one general observation already carried by D0275 and pm5FeedBack - that this repository is structurally blind to its own downstream path and a downstream report is the only evidence that anything here works. The 0x01 control-byte slip is a tooling hazard of writing shell through Python string literals, caught by reading the output back, and is the same lesson as syntax-bearing-content-uses-the-Write-tool, which is already a recorded feedback memory. Nothing here needs a new home."; }
}
