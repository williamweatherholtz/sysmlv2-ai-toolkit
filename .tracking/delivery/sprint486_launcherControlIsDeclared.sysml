// ProjectDeliveryS486 — Sprint 486: the launcher is proven and its control is declared. EXECUTE. 3 pts.
package ProjectDeliveryS486 {
    private import EngineElement::*;
    private import EngineWork::*;
    private import EngineVerification::*;
    private import EngineRelationships::*;

    #CharteredBy dependency from launcherControlIsDeclaredStory to d0254;

    part launcherControlIsDeclaredStory : Story {
        :>> id = "2a475916-700f-4ff8-aa12-4e971900b107";
        :>> title = "Sprint 486: the launcher controls are proven to fire, and one of them enters the control map (3 pts)";
        :>> createdAt = "2026-08-29"; :>> createdBy = "claudeOpus5"; :>> kind = WorkKind::code; :>> priority = WorkPriority::p0; :>> owner = "claudeOpus5"; :>> estimatedPoints = 3;
    }

    action def DeliveryRunS486 {
        action storyLauncherControlIsDeclared;
        verification storyLauncherControlIsDeclaredDoD : Test { :>> id = "765cd91b-49fc-4984-8d14-38fa2af2b8a0"; :>> method = VerificationMethod::test; :>> procedureText = "RESOLVES issue304 in part. The launcher was the largest single assurance gap: enforcement-report said launcherFraction unavailable, .keel/runs/ did not exist, and prepare/finish were reachable only from serve.rs's SSE handler despite the module doc stating they are the parts that must be TESTABLE outside it. DO: (1) probe all three launcher behaviours; (2) declare ctlLaunchDirtyRefusal in the control map with its hazard edge to EHZ2 and a provenBy naming the test; (3) file the class - implemented-but-undeclared - rather than sweeping the map on a guess. VERIFY: three tests pass; keel controls lists ten controls including the launcher; clippy, full suite, validate, check-engine, 53 guards.: DELIVERED BACKLOG ITEMS: <items>. <what done means, verified how>."; }
        // RAN: / RAN: cargo test --release -p keel-cli --test launcher_controls_actually_fire -> 3 passed; cargo clippy --workspace --all-targets -D warnings clean; cargo test --workspace --release -> 16 suites ok, 0 failed; keel guard -> 53 guards, 0 FAIL; keel gate --fast 547 clean; keel controls -> 10 declared controls, launcher present
        part storyLauncherControlIsDeclaredDoDR1 : TestResult { :>> id = "e044194d-5b05-4308-a5a0-dce47bb81e30"; :>> outcome = VerdictKind::pass; :>> judgedAgainst = "253e899"; :>> judgedAt = "2026-08-29"; :>> judgedBy = "claudeOpus5"; }
    }

    verification launcherControlIsDeclaredRefineGate : Test { :>> id = "b180337b-9fc5-4fc4-ba71-13c4b8b74b41"; :>> title = "Sprint 486 refine gate (DoR)"; :>> createdAt = "2026-08-29"; :>> createdBy = "claudeOpus5"; :>> method = VerificationMethod::inspect; :>> procedureText = "READY: chartered by D0254, which itself rests on D0253's finding that arming may be proven by TEST where a read-only view cannot establish it. The mechanism was already implemented and already documented as testable outside the SSE stream, so nothing needed designing - only exercising. Scope EXCLUDES the map-wide reconciliation, which is issue304 and is not estimated here."; }
    verification launcherControlIsDeclaredStandupGate : Test { :>> id = "3d718404-7533-4c94-b3b5-da4f1591f653"; :>> title = "Sprint 486 standup gate"; :>> createdAt = "2026-08-29"; :>> createdBy = "claudeOpus5"; :>> method = VerificationMethod::inspect; :>> procedureText = "One environment blocker, resolved and worth recording because CLAUDE.md warns about exactly it: the release build failed with Access is denied removing target/release/keel.exe. keel-serve.exe was running - the console COPY, per the documented workaround - so it was not the holder and the lock was transient. Retried and built. Notably the console being UP is the correct state: issue150 is the case where the human's queue fills while it is down."; }
    verification launcherControlIsDeclaredImplementGate : Test { :>> id = "3f6e9dc5-6d90-418c-8830-cc190da0c5b4"; :>> title = "Sprint 486 implement gate"; :>> createdAt = "2026-08-29"; :>> createdBy = "claudeOpus5"; :>> method = VerificationMethod::test; :>> procedureText = "RAN: cargo test --release -p keel-cli --test launcher_controls_actually_fire -> 3 passed. (1) the_dirty_tree_refusal_actually_refuses: a CLEAN tree prepares first, so the refusal below proves something - a control that refuses everything is stuck, not armed - then a dirtied tree REFUSES naming the reason. (2) a_prepared_run_captures_the_spawn_time_head: head_at_spawn equals the repo's actual HEAD (K12), and approved_by is carried rather than resolved from a binding. (3) finish_writes_a_record_carrying_every_declared_field: all fourteen RUN_RECORD_FIELDS are asserted present, and an empty-diff run writes NO tracked summary. The fourteen-field assertion matters because the schema is declared exempt from existence checks by design, so nothing else verified it. Read back: keel controls now reports 10 declared controls, launcher present."; }
    verification launcherControlIsDeclaredReviewGate : Test { :>> id = "b150239c-4337-4285-8dc5-9eec74b0d47a"; :>> title = "Sprint 486 review gate — three passes per D0172"; :>> createdAt = "2026-08-29"; :>> createdBy = "claudeOpus5"; :>> method = VerificationMethod::inspect; :>> procedureText = "THREE PASSES. (1) THE TESTS DISCRIMINATE: each builds a real git repository, because prepare shells out to git status and rev-parse - a fake directory would exercise the error path and pass for the wrong reason. The actor is bound through .keel/actor rather than KEEL_ACTOR, since the env var is process-wide and a test must not depend on or disturb another's environment. (2) THE ARMED COUNT DID NOT MOVE, deliberately: the census still reads 1 ARMED of 10 because checkable drives it and this control is proven by TEST, not establishable by a view. Inflating it would rebuild the false comfort D0253 removed. (3) SCOPE HONESTY: one control declared, the map-wide gap filed unestimated. Saying roughly N controls are missing would put a number in the record that nothing computed."; }
    verification launcherControlIsDeclaredCloseOutGate : Test { :>> id = "4c51167c-686d-4eb0-888f-0ebcce2f0de5"; :>> title = "Sprint 486 closeOut gate (autonomous, D0049)"; :>> createdAt = "2026-08-29"; :>> createdBy = "claudeOpus5"; :>> method = VerificationMethod::inspect; :>> procedureText = "CLOSED WITH THE RESIDUAL IN NUMBERS. Controls with evidence: 3 of 10 - one armed by view-probe (ctlCommitGate), two proven by test (ctlWriteLock, ctlLaunchDirtyRefusal). Seven have neither. issue303 and issue304 both stay OPEN. .keel/runs/ still does not exist here and that is CORRECT: no run has been launched, and the tests use throwaway repositories. What changed is that the absence now means nobody has launched one, rather than the launcher may not work - a different and much smaller problem."; }
    verification launcherControlIsDeclaredRetroGate : Test { :>> id = "7b800ace-e485-4043-b1b1-71b6e3cb67cf"; :>> title = "Sprint 486 retro gate (autonomous, D0049)"; :>> createdAt = "2026-08-29"; :>> createdBy = "claudeOpus5"; :>> method = VerificationMethod::analyze; :>> procedureText = "FINDING: three failure classes are now named, and they form a ladder of decreasing visibility. Declared-but-never-fired (D0217) is visible to a reader who looks. Declared-and-unprobeable (D0253) is visible as a classification. Implemented-but-undeclared (D0254) is visible to NOBODY - and its perverse property is that the coverage measure IMPROVES as the map gets less complete, because fewer declared controls with no gaps reads better than more with gaps. That is the third time this session a metric has been truthful about its own question and misleading about the reader's: the Need-set inversion, the arming census, and now the control map. BECOMES TRACKED WORK: issue304, whose fix is the doc-sync shape applied to controls - reconcile the map against the binary's enforcement surface, and make the reconciliation a check so it cannot silently fall behind again."; }
}
