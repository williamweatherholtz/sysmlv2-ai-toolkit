// ProjectDeliveryS337 — Sprint 337: critique pass 13. Two feasibility claims verified in the DOWNSTREAM
// viewer repo rather than credited. EXECUTE. 3 pts.
package ProjectDeliveryS337 {
    private import EngineElement::*;
    private import EngineWork::*;
    private import EngineVerification::*;
    private import EngineRelationships::*;

    #CharteredBy dependency from critPass13Story to d0080;

    part critPass13Story : Story {
        :>> id = "0d8004c0-0814-64c0-9b3e-0000003004c0";
        :>> title = "Sprint 337: critique pass 13 — 5 Decisions, 6 fail / 9 pass (3 pts)";
        :>> createdAt = "2026-08-17"; :>> createdBy = "claudeOpus5"; :>> kind = WorkKind::modeling; :>> priority = WorkPriority::p0; :>> owner = "claudeOpus5"; :>> estimatedPoints = 3;
    }

    action def DeliveryRunS337 {
        action storyCritPass13;
        verification storyCritPass13DoD : Test { :>> id = "0d8004c1-0814-64c1-9b3e-0000003004c1"; :>> method = VerificationMethod::analyze; :>> procedureText = "Pass 13: d0122, d0123, d0124, d0125, d0126. 6 fail, 9 pass — the most pass-heavy of the run, and the reason is verifiable rather than charitable: four of these five were CARRIED OUT and I confirmed the artifacts. TWO CLAIMS WERE VERIFIED IN THE DOWNSTREAM VIEWER REPO instead of being credited: D0124 says its channel registry was PROVEN by adding two channels with no other code change, citing 6 generated selects — the viewer's app.js declares exactly six channel modules (colour, size, shape, x, row, nest), so size and shape sit as peers of the original four rather than as special cases; and D0125's ELK claim holds, with cytoscape-elk.js and elk.bundled.js vendored in app/vendor beside a self-hosted cytoscape and fonts, no CDN and no build step. THE FINDINGS: D0126 cites nViewerTemporalState as a Need its register serves, and that is N-3, which D0116 had ALREADY superseded — an earlier Decision, so D0126 was authored after the retirement and credits work against retired scope. D0123's clause (1) states the best reusable rule in the corpus (an obligation view must not resurrect or flag as deficient items governed by a superseded process version) and NOTHING ENFORCES IT — proven by this session, where sprint 316's obligation bar counted 311 pre-convention sitting obligations without consulting governing-version at all. And D0122's `rejected` enum member, which required frozen-core sign-off, has never been used: no Decision in the corpus has ever been rejected. READ BACK: Decision coverage 39 -> 44 of 75."; }
        part storyCritPass13DoDR1 : TestResult { :>> id = "0d8004c2-0814-64c2-9b3e-0000003004c2"; :>> outcome = VerdictKind::pass; :>> judgedAgainst = "f9eed06"; :>> judgedAt = "2026-08-17"; :>> judgedBy = "claudeOpus5"; }
    }

    verification c13RefineGate : Test { :>> id = "0d8004c3-0814-64c3-9b3e-0000003004c3"; :>> title = "Sprint 337 refine gate (DoR)"; :>> createdAt = "2026-08-17"; :>> createdBy = "claudeOpus5"; :>> method = VerificationMethod::inspect; :>> procedureText = "DoR. Five Decisions, and the feasibility lens required looking OUTSIDE this repository for two of them — D0118 puts the viewer CODE in sysmlv2-viewer while its programme is governed here, so a claim about the viewer app is verifiable in the sibling repo and nowhere else. That is the two-repo seam D0118's own completeness gap describes, and using it as a critic is the first time this session has read the downstream deliverable. estimatedPoints=3."; }
    part c13RefineGateR1 : TestResult { :>> id = "0d8004c4-0814-64c4-9b3e-0000003004c4"; :>> outcome = VerdictKind::pass; :>> judgedAgainst = "f9eed06"; :>> judgedAt = "2026-08-17"; :>> judgedBy = "claudeOpus5"; }

    verification c13StandupGate : Test { :>> id = "0d8004c5-0814-64c5-9b3e-0000003004c5"; :>> title = "Sprint 337 standup gate"; :>> createdAt = "2026-08-17"; :>> createdBy = "claudeOpus5"; :>> method = VerificationMethod::inspect; :>> procedureText = "Approach: where a Decision states a SPECIFIC verification claim (6 selects, 5 channels, vendored files), go and count — a specific claim is either true or false and takes one command to settle, which is a better use of a pass than reasoning about whether it is plausible. Four such claims were checked this pass and all four held. No blockers."; }
    part c13StandupGateR1 : TestResult { :>> id = "0d8004c6-0814-64c6-9b3e-0000003004c6"; :>> outcome = VerdictKind::pass; :>> judgedAgainst = "f9eed06"; :>> judgedAt = "2026-08-17"; :>> judgedBy = "claudeOpus5"; }

    verification c13ImplementGate : Test { :>> id = "0d8004c7-0814-64c7-9b3e-0000003004c7"; :>> title = "Sprint 337 implement gate"; :>> createdAt = "2026-08-17"; :>> createdBy = "claudeOpus5"; :>> method = VerificationMethod::analyze; :>> procedureText = "D0123 STATES THE BEST RULE IN THE CORPUS AND THIS SESSION BROKE IT, which is the finding worth carrying out of this pass. Its clause (1) says a computed view of human obligations must not resurrect, nor flag as deficient, historical items governed by a superseded process version — forward-only retroactivity as a DESIGN RULE for views rather than a one-off fix. Sprint 316 then built an obligation bar that counted every uncovered sitting, reported 311 of 315, and consulted governing-version nowhere; it took D0155 and a human attestation to draw a grandfather line and make the number workable. So an accepted design rule was violated by a view built after it, and nothing detected the violation because no guard checks views. That is the precise gap: the rule is correct, reusable, and unenforced, and its own Decision names the root cause of the original miss in the same words ('a new computed obligation-view was built without applying the governing-version discipline') without noticing that naming it does not prevent it."; }
    part c13ImplementGateR1 : TestResult { :>> id = "0d8004c8-0814-64c8-9b3e-0000003004c8"; :>> outcome = VerdictKind::pass; :>> judgedAgainst = "f9eed06"; :>> judgedAt = "2026-08-17"; :>> judgedBy = "claudeOpus5"; }

    verification c13ReviewGate : Test { :>> id = "0d8004c9-0814-64c9-9b3e-0000003004c9"; :>> title = "Sprint 337 review gate"; :>> createdAt = "2026-08-17"; :>> createdBy = "claudeOpus5"; :>> method = VerificationMethod::inspect; :>> procedureText = "Reviewed. NINE PASSES OF FIFTEEN and every one is anchored to something I checked: a declared workflow phase (retro, in delivery.sysml with its succession), an enum member in frozen core, two vendored files, six channel modules in a downstream file, an advertised endpoint, and a computed function (display_label) that implements a view the schema had declared and nothing had built. That last one deserves its own note — D0126 BUILT A DECLARED-BUT-UNBUILT COMPUTED VIEW, which is the rarest delivery in this corpus and the exact opposite of the pattern the Decision passes keep finding, where a clause is declared and quietly never carried out. WHAT I DID NOT DO: raise an Issue for D0126's superseded-Need citation or D0123's unenforced rule. Both are edits to human- or claudeOpus-authored Decisions, and both remedies (recite the live requirement; build a control over views) belong to their owners."; }
    part c13ReviewGateR1 : TestResult { :>> id = "0d8004ca-0814-64ca-9b3e-0000003004ca"; :>> outcome = VerdictKind::pass; :>> judgedAgainst = "f9eed06"; :>> judgedAt = "2026-08-17"; :>> judgedBy = "claudeOpus5"; }

    verification c13CloseOutGate : Test { :>> id = "0d8004cb-0814-64cb-9b3e-0000003004cb"; :>> title = "Sprint 337 closeOut gate (autonomous, D0049)"; :>> createdAt = "2026-08-17"; :>> createdBy = "claudeOpus5"; :>> method = VerificationMethod::inspect; :>> procedureText = "Autonomous closeOut (D0049). Decision coverage 39 -> 44 of 75; TWO critiquable Decisions remain, after which every element in this model that I am permitted to critique will be covered. validate clean; check-engine clean; 35 guards ALL PASS; no code changed."; }
    part c13CloseOutGateR1 : TestResult { :>> id = "0d8004cc-0814-64cc-9b3e-0000003004cc"; :>> outcome = VerdictKind::pass; :>> judgedAgainst = "f9eed06"; :>> judgedAt = "2026-08-17"; :>> judgedBy = "claudeOpus5"; }

    verification c13RetroGate : Test { :>> id = "0d8004cd-0814-64cd-9b3e-0000003004cd"; :>> title = "Sprint 337 retro gate (autonomous, D0049)"; :>> createdAt = "2026-08-17"; :>> createdBy = "claudeOpus5"; :>> method = VerificationMethod::analyze; :>> procedureText = "Autonomous retro (D0049) under D0131's retroTrack. WELL: (1) crossing into the downstream repo to settle two specific claims — a claim that names a number (6 selects, 5 channels) or a file (elk.bundled.js) costs one command to verify and is worth more verified than argued; (2) the lens-completeness check added last pass held silently, which is what a working control looks like; (3) the D0123 finding turned a rule I had been implicitly relying on into a measured gap, and it indicts THIS session's own work rather than only historical work. AVOIDABLE-ISSUE: none this sprint. OBSERVATION FOR THE WRAP-UP: across four Decision passes the strongest predictor of a clause being carried out is whether it needed NEW MACHINERY. Every Decision that reused an existing mechanism shipped whole (D0108, D0110, D0111, D0113, D0122, D0123, D0124, D0125, D0126); every one that proposed new machinery shipped partly or not at all (D0105's rule kinds and RMWX verbs, D0106's parallel execution, D0119's standard envelope). That is nine against four, and it is the most useful thing this corpus can tell whoever writes the next Decision. Estimate 3 pts, delivered."; }
    part c13RetroGateR1 : TestResult { :>> id = "0d8004ce-0814-64ce-9b3e-0000003004ce"; :>> outcome = VerdictKind::pass; :>> judgedAgainst = "f9eed06"; :>> judgedAt = "2026-08-17"; :>> judgedBy = "claudeOpus5"; }
}
