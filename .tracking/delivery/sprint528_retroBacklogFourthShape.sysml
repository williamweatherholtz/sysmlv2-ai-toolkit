// ProjectDeliveryS528 — Sprint 528: retro-backlog's fourth shape - a justification names its item, and every retro is read. EXECUTE. 2 pts.
package ProjectDeliveryS528 {
    private import EngineElement::*;
    private import EngineWork::*;
    private import EngineVerification::*;
    private import EngineRelationships::*;

    #CharteredBy dependency from retroFourthShapeStory to d0294;

    part retroFourthShapeStory : Story {
        :>> id = "9308006e-8857-445a-92e7-bcc1068cf950";
        :>> title = "Sprint 528: 'already tracked' must name the item; the extraction that skipped 27 of 510 retros is replaced; the control-defect entry leaves with the fix (2 pts)";
        :>> createdAt = "2026-09-03"; :>> createdBy = "claudeOpus5"; :>> kind = WorkKind::code; :>> priority = WorkPriority::p0; :>> owner = "claudeOpus5"; :>> estimatedPoints = 2;
    }

    action def DeliveryRunS528 {
        action storyRetroFourthShape;
        verification storyRetroFourthShapeDoD : Test { :>> id = "0f865ab2-d3f6-4b8b-942a-5657d180a676"; :>> method = VerificationMethod::test; :>> procedureText = "DELIVERED BACKLOG ITEMS: dcRetroAlreadyTrackedMustName (resolves issue364, both shapes). DONE: a justified retro must name an existing item - issueNNN, dcTask or dNNNN (a Decision counts, Invariant 4) - added by the commit or in the tree, else a violation quoting the phrase; retro gates are extracted from line-leading verification blocks, never by splitting on the word, so every retro is read; twelve unit tests; control-defects.toml no longer names retro-backlog; issue364's description carries the second shape and the invalidation count. VERIFY: the arming test for shape one failed with RETROS=[] and exposed shape two; 27 of 510 retro gates (20 unjustified) had never been examined; 452 tests pass; clippy clean."; }
        // RAN: cargo test --lib retro 12/12; count_retros over .tracking/delivery with the fixed extraction: 510 retro gates, 27 containing 'verification ', 7 of those justified; full suite 452/0; clippy clean; keel guard control-defect-registry 2 scanned after the entry left
        part storyRetroFourthShapeDoDR1 : TestResult { :>> id = "dd246a50-e0a5-45c8-b5ef-aa3e9643d8e1"; :>> outcome = VerdictKind::pass; :>> judgedAgainst = "4506a05"; :>> judgedAt = "2026-09-03"; :>> judgedBy = "claudeOpus5"; }
    }

    verification retroFourthShapeRefineGate : Test { :>> id = "19d5bfb5-ce29-425c-bd80-69e63a1c90f3"; :>> title = "Sprint 528 refine gate (DoR)"; :>> createdAt = "2026-09-03"; :>> createdBy = "claudeOpus5"; :>> method = VerificationMethod::inspect; :>> procedureText = "READY from D0293: the defect was established against guards.rs:1611 and :1681, the direction was under, the invalidation was stated, and the fix's shape - name the item - was in the DoD. The one design question, whether a Decision may be the named item, was answered by Invariant 4."; }
    verification retroFourthShapeStandupGate : Test { :>> id = "9ec65141-658c-4ab3-ace1-cb4ffe5a2d02"; :>> title = "Sprint 528 standup gate"; :>> createdAt = "2026-09-03"; :>> createdBy = "claudeOpus5"; :>> method = VerificationMethod::inspect; :>> procedureText = "ONE CHOICE stated plainly: the guard checks FORM (the named item exists), not RELEVANCE (the named item covers the finding). The two retros that motivated D0293 named real items and pass the new check; a test says so rather than letting the reader believe otherwise. The alternative - no justification accepted at all - would force a duplicate item every time a control already exists, which is the noise D0131 was written to avoid."; }
    verification retroFourthShapeImplementGate : Test { :>> id = "a1b13a91-22f4-47c9-a3b9-184c83b861ef"; :>> title = "Sprint 528 implement gate"; :>> createdAt = "2026-09-03"; :>> createdBy = "claudeOpus5"; :>> method = VerificationMethod::test; :>> procedureText = "RAN: the arming test for shape one FAILED - RETROS=[] - because its fixture text contained the word verification and the old extraction cut the retro in half; that is how shape two was found. Extraction rewritten to line-leading blocks; the count over this repository's own retros run with the fixed extraction: 27 of 510 never examined, 20 unjustified. Two heredoc backslash traps in the edit (a newline char literal, a regex class), fixed through the Edit and Write tools as the memory says."; }
    verification retroFourthShapeReviewGate : Test { :>> id = "513ca446-a43e-40a2-9fae-516f7e6138ed"; :>> title = "Sprint 528 review gate — three passes per D0172"; :>> createdAt = "2026-09-03"; :>> createdBy = "claudeOpus5"; :>> method = VerificationMethod::inspect; :>> procedureText = "THREE PASSES. (1) IS THE FIX ARMED: two violation tests for shape one, one extraction test for shape two, and the fixed extraction re-counts the corpus. (2) IS THE REGISTRY HONEST: the entry leaves in the same commit as the fix, and issue364 carries the invalidation the entry carried. (3) WERE THE 27 RE-CHECKED: no, and it is said - a reader can run the count and open them; re-judging 27 retros is a sitting review the human may choose (D0204), never owed."; }
    verification retroFourthShapeCloseOutGate : Test { :>> id = "0f0fc353-dc79-4e45-beaf-7d0d46943451"; :>> title = "Sprint 528 closeOut gate (autonomous, D0049)"; :>> createdAt = "2026-09-03"; :>> createdBy = "claudeOpus5"; :>> method = VerificationMethod::inspect; :>> procedureText = "CLOSED. This retro is the first written under the fourth shape; the guard will read it, and it names issue364."; }
    verification retroFourthShapeRetroGate : Test { :>> id = "176ad9d0-4be5-4f0b-b140-e6fdad2ca362"; :>> title = "Sprint 528 retro gate (autonomous, D0049)"; :>> createdAt = "2026-09-03"; :>> createdBy = "claudeOpus5"; :>> method = VerificationMethod::analyze; :>> procedureText = "no new item - already tracked: the finding of this sprint is issue364's second shape, recorded in issue364 itself and in D0294; the generalisable lesson - a guard over text must extract by structure, not by splitting on a word - is the same one issue329 taught about substring verdicts, and dcAppendResultFindsTheClosingBrace (issue353, issue354) is its next instance on the write path."; }
}
