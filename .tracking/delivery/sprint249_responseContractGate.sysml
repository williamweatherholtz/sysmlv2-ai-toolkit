// ProjectDeliveryS249 — Sprint 249: move the response contract into the system prompt (output style)
// and wire the Tier-3 in-loop Stop gate (D0130, proposed; chartered by the accepted D0128).
// Delivers the DELIVERED SLICE only — keelInLoopGates stays open for measurement + Tier-1/2. EXECUTE. 3 pts.
package ProjectDeliveryS249 {
    private import EngineElement::*;
    private import EngineWork::*;
    private import EngineVerification::*;
    private import EngineRelationships::*;

    #CharteredBy dependency from responseContractGateStory to d0128;

    part responseContractGateStory : Story {
        :>> id = "0d660001-0813-4601-9b3e-000000160001";
        :>> title = "Sprint 249: response contract as a system-prompt output style + Tier-3 in-loop Stop gate (3 pts)";
        :>> createdAt = "2026-08-13"; :>> createdBy = "claudeOpus5"; :>> kind = WorkKind::code; :>> priority = WorkPriority::p0; :>> owner = "claudeOpus5"; :>> estimatedPoints = 3;
    }

    action def DeliveryRunS249 {
        action storyResponseContractGate;
        verification storyResponseContractGateDoD : Test { :>> id = "0d660002-0813-4602-9b3e-000000160002"; :>> method = VerificationMethod::demo; :>> procedureText = "Delivers dcResponseContractGate (D0130). The human asked whether the AI's output format can be defined LOCALLY for consistency and said they understood that to be stronger than CLAUDE.md — it is, and placement was the whole lever. Verified hierarchy: hooks are HARNESS-executed (a Stop hook can refuse to end a turn — the only enforcing layer); an output style modifies the SYSTEM PROMPT; CLAUDE.md is user-turn context (weakest layer that can hold a rule); AI memory is weaker still and per-agent. DELIVERED: .claude/output-styles/keel.md + outputStyle=keel (committed at project scope so every contributor gets the identical contract); the Stop hook wired to .engine/tools/stop_gate.py; two REAL defects fixed in the prototype (Windows-only keel.exe -> would have silently NO-OPPED on every other machine, the issue076 class inside the governance control itself; platform-default decoding -> corrective feedback arrived as mojibake); CLAUDE.md doc-synced to REFERENCE rather than restate. VERIFY (pipe-test, all four paths): green -> exit 0 silent; injected parse error -> decision=block with violations in reason; stop_hook_active + still red -> allows with a loud systemMessage (loop-safe); missing binary -> visible message, never silent. Encoding confirmed at BYTE level (U+2014 present, no U+FFFD, no cp1252 mojibake) after the console had misleadingly rendered a replacement char. settings.json: JSON valid, keys resolve, pre-existing 10 denies + 2 UserPromptSubmit hooks preserved. keel validate + all 18 guards + check-engine green at 7740eb0."; }
        part storyResponseContractGateDoDR1 : TestResult { :>> id = "0d660003-0813-4603-9b3e-000000160003"; :>> outcome = VerdictKind::pass; :>> judgedAgainst = "7740eb0"; :>> judgedAt = "2026-08-13"; :>> judgedBy = "claudeOpus5"; }
    }

    verification rcRefineGate : Test { :>> id = "0d660004-0813-4604-9b3e-000000160004"; :>> title = "Sprint 249 refine gate (DoR)"; :>> createdAt = "2026-08-13"; :>> createdBy = "claudeOpus5"; :>> method = VerificationMethod::inspect; :>> procedureText = "DoR: chartered by d0128 (ACCEPTED 2026-08-13), whose governance clause names exactly this work — in-loop gates at the turn boundary, affordance/channeling, and 'a concise per-project workflow spec' (which is what an output style is). Scope fixed: the Tier-3 Stop gate + the output style + doc-sync. EXCLUDED with reasons: the D0128 measurement, Tier-2 PostToolUse per-edit gating and Tier-1 PreToolUse deny (D0128 makes them conditional on measurement), and shipping the output style as a keel-init artifact (belongs to keelProcessPortability; authoring it twice now would create the dual truth this sprint exists to remove). estimatedPoints=3. DoR met."; }
    part rcRefineGateR1 : TestResult { :>> id = "0d660005-0813-4605-9b3e-000000160005"; :>> outcome = VerdictKind::pass; :>> judgedAgainst = "7740eb0"; :>> judgedAt = "2026-08-13"; :>> judgedBy = "claudeOpus5"; }

    verification rcStandupGate : Test { :>> id = "0d660006-0813-4606-9b3e-000000160006"; :>> title = "Sprint 249 standup gate"; :>> createdAt = "2026-08-13"; :>> createdBy = "claudeOpus5"; :>> method = VerificationMethod::inspect; :>> procedureText = "Approach: read the harness settings SCHEMA to confirm outputStyle and Stop are real, rather than asserting the capability from memory; invoke the sanctioned update-config skill instead of hand-editing settings.json; PIPE-TEST the gate on every path before wiring it, since a governance control that silently fails is worse than none; and merge settings rather than replace, so the existing triage hooks and permission denies survive. No blockers."; }
    part rcStandupGateR1 : TestResult { :>> id = "0d660007-0813-4607-9b3e-000000160007"; :>> outcome = VerdictKind::pass; :>> judgedAgainst = "7740eb0"; :>> judgedAt = "2026-08-13"; :>> judgedBy = "claudeOpus5"; }

    verification rcImplementGate : Test { :>> id = "0d660008-0813-4608-9b3e-000000160008"; :>> title = "Sprint 249 implement gate"; :>> createdAt = "2026-08-13"; :>> createdBy = "claudeOpus5"; :>> method = VerificationMethod::demo; :>> procedureText = "Implemented at 7740eb0. All four gate paths pipe-tested green/block/loop-safe/binary-missing. The prototype's two defects were found BY productionising it rather than by review, which is the argument for wiring prototypes properly instead of leaving them untracked: it sat unwired in the working tree for weeks with a Windows-only path that would have made it a no-op for the entire distributed team. NOT verifiable from inside the turn that wires it: that the hook actually fires — the harness must reload settings (/hooks or restart), and that limitation is stated rather than glossed."; }
    part rcImplementGateR1 : TestResult { :>> id = "0d660009-0813-4609-9b3e-000000160009"; :>> outcome = VerdictKind::pass; :>> judgedAgainst = "7740eb0"; :>> judgedAt = "2026-08-13"; :>> judgedBy = "claudeOpus5"; }

    verification rcReviewGate : Test { :>> id = "0d66000a-0813-460a-9b3e-00000016000a"; :>> title = "Sprint 249 review gate"; :>> createdAt = "2026-08-13"; :>> createdBy = "claudeOpus5"; :>> method = VerificationMethod::inspect; :>> procedureText = "Reviewed. The strongest decision in this sprint was a REFUSAL: keelInLoopGates was NOT marked delivered, because its DoD also demands the D0128 measurement plus Tier-1/Tier-2, and closing it on a partial would have been the exact mis-identification issue082 tracks — the delivered slice got its own action instead. Second: the dual-truth risk was named and partially mitigated in the same breath rather than left implicit, and the RESIDUE was tracked as issue086 rather than described. Weakness accepted: an output style modifies the default system prompt and can suppress default harness behaviour, so it is deliberately scoped to the response contract, committed at project scope for consistency, and reversible by deleting one settings key — the risk is recorded in D0130 rather than discovered later."; }
    part rcReviewGateR1 : TestResult { :>> id = "0d66000b-0813-460b-9b3e-00000016000b"; :>> outcome = VerdictKind::pass; :>> judgedAgainst = "7740eb0"; :>> judgedAt = "2026-08-13"; :>> judgedBy = "claudeOpus5"; }

    verification rcCloseOutGate : Test { :>> id = "0d66000c-0813-460c-9b3e-00000016000c"; :>> title = "Sprint 249 closeOut gate (autonomous, D0049)"; :>> createdAt = "2026-08-13"; :>> createdBy = "claudeOpus5"; :>> method = VerificationMethod::inspect; :>> procedureText = "Autonomous closeOut (D0049). dcResponseContractGate carries a passing DoD TestResult at 7740eb0; keel validate + all 18 guards + check-engine green. keelInLoopGates remains OPEN at frontier position 6 with its measurement + Tier-1/2 scope intact. D0130 is PROPOSED and awaits the human, together with the per-sitting review; no acceptance was fabricated. One item requires the HUMAN to act before the change takes effect at all: the harness must reload settings (/hooks once, or restart)."; }
    part rcCloseOutGateR1 : TestResult { :>> id = "0d66000d-0813-460d-9b3e-00000016000d"; :>> outcome = VerdictKind::pass; :>> judgedAgainst = "7740eb0"; :>> judgedAt = "2026-08-13"; :>> judgedBy = "claudeOpus5"; }

    verification rcRetroGate : Test { :>> id = "0d66000e-0813-460e-9b3e-00000016000e"; :>> title = "Sprint 249 retro gate (autonomous, D0049)"; :>> createdAt = "2026-08-13"; :>> createdBy = "claudeOpus5"; :>> method = VerificationMethod::analyze; :>> procedureText = "Autonomous retro (D0049), run under the issue085 obligation: every finding terminates in a TRACKED item. WELL: (1) the capability was confirmed from the harness SCHEMA rather than asserted from memory, which is what made the layer hierarchy defensible instead of plausible; (2) pipe-testing before wiring found two real defects in a prototype that had passed casual reading for weeks; (3) the sprint refused to close keelInLoopGates on a partial. AVOIDABLE-ISSUE 1: I reported the encoding fix as NOT working based on a replacement character in the console, then re-checked at byte level and found it was fine all along — I diagnosed from RENDERED output. This is the same principle dcVerificationTrace encodes (read the computed answer back, never the rendering or the transform's self-report); no new item, the practice is recorded here and the control already exists at frontier #1. AVOIDABLE-ISSUE 2: I wrote a validation command around `jq`, which is not installed on this host — the same don't-assume-the-toolchain error the portable-gate work (issue076) just fixed in the hooks; recovered with python. Lesson recorded; no new item because dcPortableGate already generalises it. AVOIDABLE-ISSUE 3 (TRACKED as issue086/dcContractDedup, severity Low): D0130 makes the output style canonical, but CLAUDE.md section 3 still RESTATES the Parsed-block mandate and label vocabulary, so one rule now has two live copies — dual truth (D0105), with the weaker copy the one that will drift. Ranked LOW deliberately: no functional effect while the copies agree. Estimate 3 pts, delivered. This retro is the first exercise of the issue085 rule, and it produced exactly one new tracked, prioritized item — which is the intended behaviour, not a failure to find more."; }
    part rcRetroGateR1 : TestResult { :>> id = "0d66000f-0813-460f-9b3e-00000016000f"; :>> outcome = VerdictKind::pass; :>> judgedAgainst = "7740eb0"; :>> judgedAt = "2026-08-13"; :>> judgedBy = "claudeOpus5"; }
}
