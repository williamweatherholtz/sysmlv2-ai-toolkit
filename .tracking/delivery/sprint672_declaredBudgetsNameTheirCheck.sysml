// ProjectDeliveryS672 — Sprint 672: Declared budgets name their check. The skill file carries a Budget table with 9 rows; 7 bear a number. Before the edit, every numeric row failed the contract because it names no check and does not say unheld. The table gains a Held by column and each row names either a check (examples: check_templates.py --brief, tests/exec_summary) or says unheld (Courses row); the check_templates.py --budgets live census runs before every commit via --self-test, so the contract is enforced by an existing CI step with zero new surface.. EXECUTE. 2 pts.
package ProjectDeliveryS672 {
    private import EngineElement::*;
    private import EngineWork::*;
    private import EngineVerification::*;
    private import EngineRelationships::*;

    #CharteredBy dependency from declaredBudgetsNameTheirCheckStory to d0446;

    part declaredBudgetsNameTheirCheckStory : Story {
        :>> id = "700b4c71-73c5-4637-9677-177199843b2e";
        :>> title = "Sprint 672: Declared budgets name their check. The skill file carries a Budget table with 9 rows; 7 bear a number. Before the edit, every numeric row failed the contract because it names no check and does not say unheld. The table gains a Held by column and each row names either a check (examples: check_templates.py --brief, tests/exec_summary) or says unheld (Courses row); the check_templates.py --budgets live census runs before every commit via --self-test, so the contract is enforced by an existing CI step with zero new surface. (2 pts)";
        :>> createdAt = "2026-09-11"; :>> createdBy = "claudeOpus5"; :>> kind = WorkKind::code; :>> priority = WorkPriority::p0; :>> owner = "claudeOpus5"; :>> estimatedPoints = 2;
    }

    action def DeliveryRunS672 {
        action storyDeclaredBudgetsNameTheirCheck;
        verification storyDeclaredBudgetsNameTheirCheckDoD : Test { :>> id = "22772748-c5f6-480e-8122-e34b988e2027"; :>> method = VerificationMethod::test; :>> procedureText = "scripts/check_templates.py gains --budgets flag (live census over Budget tables in .engine/skills/*/SKILL.md), --probe (D0388 pair with fixtures), --self-test now runs the pair and the live census; docstring Usage block updated. .engine/skills/asi-templates/SKILL.md section 2.1 table gains Held by column; paragraph under the table names the rule and the check; section 4 names the budget-census commands. Every numeric row names a check or says unheld; live census reports 0 violations on exit=0. Tests: 27 ok lines from --self-test (unchanged 20 brief-contract cases, D0388 pair, live skill set pass). Rust: no change. Tracking: no .tracking/ or .engine/decisions/ files written."; }
        // RAN: verifier receipt batch1: check_templates.py --probe pass exit 0; --self-test pass exit 0; live census 7 held 0 unheld
        part storyDeclaredBudgetsNameTheirCheckDoDR1 : TestResult { :>> id = "e470e030-6941-4d16-90d9-0da0d3a7aaee"; :>> outcome = VerdictKind::pass; :>> judgedAgainst = "b8fab64"; :>> judgedAt = "2026-09-11"; :>> judgedBy = "claudeOpus5"; }
    }

    verification declaredBudgetsNameTheirCheckRefineGate : Test { :>> id = "c85e3222-040d-446e-b770-23bcc19331c4"; :>> title = "Sprint 672 refine gate (DoR)"; :>> createdAt = "2026-09-11"; :>> createdBy = "claudeOpus5"; :>> method = VerificationMethod::inspect; :>> procedureText = "Chartered by D0446 (Decision, recorded proposed/HELD per D0337 for the process-change naming the skill file is a locked process definition). Depends on dcSetJudgmentWritePath (sprint 668, done). 2 points: scripts/check_templates.py new flags, SKILL.md table edit, live census enforcement. The receipt-shape rule was measured before written: D0388 pair on 20 existing brief cases, 6 new budget cases (one fixture set with held/held/unheld/unheld/held/held reads correctly), plus the live tree pass on asi-templates skill with 7 numeric rows all holding a check now."; }
    // RAN: verifier receipt batch1: chartered by d0446; 2 point; validate 766 clean exit 0
    part declaredBudgetsNameTheirCheckRefineGateR1 : TestResult { :>> id = "cb1d8f01-4a1e-4aad-b174-1617b32eff8d"; :>> outcome = VerdictKind::proposed; :>> judgedAgainst = "b8fab64"; :>> judgedAt = "2026-09-11"; :>> judgedBy = "claudeOpus5"; }
    verification declaredBudgetsNameTheirCheckStandupGate : Test { :>> id = "c6aa1a37-6d33-4818-a0ea-dae201d5a37c"; :>> title = "Sprint 672 standup gate"; :>> createdAt = "2026-09-11"; :>> createdBy = "claudeOpus5"; :>> method = VerificationMethod::inspect; :>> procedureText = "Order: check_templates.py (--budgets reads the Budget columns, --probe fixtures before tree read, --self-test runs all), SKILL.md section 2.1 table (Held by column, paragraph names the check locations and rule), section 4 names the commands, D0446 text, the integration trace in --self-test output. Blocker: none. The skill file is locked per D0370 so the process-change marker is the gatekeeping constraint; D0446 records it proposed/HELD and the write path refuses the script-to-repo edit until the human accepts."; }
    // RAN: verifier receipt batch1: check_templates.py --probe pass exit 0; --self-test pass exit 0; D0446 process-change marker holds
    part declaredBudgetsNameTheirCheckStandupGateR1 : TestResult { :>> id = "33c9272c-aede-4259-96f2-eca48657b605"; :>> outcome = VerdictKind::proposed; :>> judgedAgainst = "b8fab64"; :>> judgedAt = "2026-09-11"; :>> judgedBy = "claudeOpus5"; }
    verification declaredBudgetsNameTheirCheckImplementGate : Test { :>> id = "0d6fa699-bd76-433a-a852-4936c12e39ff"; :>> title = "Sprint 672 implement gate"; :>> createdAt = "2026-09-11"; :>> createdBy = "claudeOpus5"; :>> method = VerificationMethod::test; :>> procedureText = "scripts/check_templates.py: --budgets flag (census live tables in SKILL.md files), --probe D0388 pair (6 fixtures for both positive and negative rows), --self-test runs unchanged brief contract, then the pair, then --budgets on live tree and names the pass. .engine/skills/asi-templates/SKILL.md: section 2.1 Budget table header gains Held by column (8 rows list their check or say unheld); paragraph under table names check_templates.py --budgets and the rule; section 4 (commands) names --budgets; existing sections 2.2-2.4 untouched (no Budget column, not scanned)."; }
    // RAN: verifier receipt batch1: check_templates.py --probe positive pass exit 0; --self-test negative pass exit 0; 27 ok lines; live census asi-templates 7 held 0 unheld
    part declaredBudgetsNameTheirCheckImplementGateR1 : TestResult { :>> id = "cfd5820b-0721-4231-b1ab-e442400b5aef"; :>> outcome = VerdictKind::pass; :>> judgedAgainst = "b8fab64"; :>> judgedAt = "2026-09-11"; :>> judgedBy = "claudeOpus5"; }
    verification declaredBudgetsNameTheirCheckReviewGate : Test { :>> id = "3dc2f5c7-c2e7-401c-9525-d8b818a64b4f"; :>> title = "Sprint 672 review gate — three passes per D0172"; :>> createdAt = "2026-09-11"; :>> createdBy = "claudeOpus5"; :>> method = VerificationMethod::inspect; :>> procedureText = "Delivered: every numeric Budget row declares what measure holds it and when that measure fails the live census reports the violation by row name and line, so the skill author can trace it. 7 of 7 numeric rows in asi-templates hold a check; 1 row (Courses) declares unheld - that state is correct (the exhibits row carries the two-figure minimum, outside scope). Residual: the DoD's VERIFY names tests/exec_summary as holding four rows (why now, decision rule, why this wins, what would change my mind), and they do - but exec-summary's word caps live in check_templates.BUDGETS driver/why/flip/conf constants and the brief markup has no anchor for those four sections. Making it measurable needs a brief-markup contract change (scripts/exec_brief family), outside this item; tracked as issue486 with resolver dcBriefRowsAreMeasuredOnTheBriefPage (added this commit)."; }
    // RAN: verifier receipt batch1: check-engine clean exit 0; sync-claude --check matches 46 registry skills exit 0; guard ALL PASS 38 actionable warnings exit 0
    part declaredBudgetsNameTheirCheckReviewGateR1 : TestResult { :>> id = "ec73101a-1d34-461e-be4d-1b346ecf2c87"; :>> outcome = VerdictKind::proposed; :>> judgedAgainst = "b8fab64"; :>> judgedAt = "2026-09-11"; :>> judgedBy = "claudeOpus5"; }
    verification declaredBudgetsNameTheirCheckCloseOutGate : Test { :>> id = "96fd3546-ff5d-48ba-9053-8878c9fb37b5"; :>> title = "Sprint 672 closeOut gate (autonomous, D0049)"; :>> createdAt = "2026-09-11"; :>> createdBy = "claudeOpus5"; :>> method = VerificationMethod::inspect; :>> procedureText = "Sprint 672 closes on the verifier's receipt only (D0425). dcDeclaredBudgetsNameTheirCheck gets its DoD result. D0446 stays proposed/HELD for the human (D0337). Issue486 and dcBriefRowsAreMeasuredOnTheBriefPage are added to backlog this commit. Nothing else in the frontier moved."; }
    // RAN: verifier receipt batch1: DISCREPANCIES NONE; OWED WRITES NONE; dcDeclaredBudgetsNameTheirCheck DoD result recorded; issue486 resolves through dcBriefRowsAreMeasuredOnTheBriefPage
    part declaredBudgetsNameTheirCheckCloseOutGateR1 : TestResult { :>> id = "f6d0aec1-6ebb-4fad-8975-91dd18c61f3b"; :>> outcome = VerdictKind::proposed; :>> judgedAgainst = "b8fab64"; :>> judgedAt = "2026-09-11"; :>> judgedBy = "claudeOpus5"; }
    verification declaredBudgetsNameTheirCheckRetroGate : Test { :>> id = "2dfc628e-45c9-44e3-8f30-5228078bdc9a"; :>> title = "Sprint 672 retro gate (autonomous, D0049)"; :>> createdAt = "2026-09-11"; :>> createdBy = "claudeOpus5"; :>> method = VerificationMethod::analyze; :>> procedureText = "AVOIDABLE-ISSUE SCAN: issue486 and dcBriefRowsAreMeasuredOnTheBriefPage are the items added this commit. The 7-row contract failure before the edit (every numeric row unnamed) was avoidable at authoring time - a Budget table with a number names nothing until the check is written in; a template for new Budget rows names the empty check spot and is what prevents the next author from naming no check. No other finding."; }
    // RAN: verifier receipt batch1: no new Issue beyond issue486 and dcBriefRowsAreMeasuredOnTheBriefPage (added this commit); avoidable at authoring time: template for new Budget rows names empty check spot
    part declaredBudgetsNameTheirCheckRetroGateR1 : TestResult { :>> id = "89b4b7f1-a47f-4183-89e8-b780530725d5"; :>> outcome = VerdictKind::proposed; :>> judgedAgainst = "b8fab64"; :>> judgedAt = "2026-09-11"; :>> judgedBy = "claudeOpus5"; }
}
