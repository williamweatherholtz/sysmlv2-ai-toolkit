// ProjectDeliveryS686 — Sprint 686: The instruments enter the propriety. Six defects in one day came from things that MEASURE and none had been assessed by the panel that every blocking control passes (D0257); D0361 declares the measures and D0363 makes them model items with a computed assessed state. This sprint runs the FIRST TRANCHE over the two whose numbers reach a human with no gate between - the standing-brief facts script and the chart builders - one ProprietyFinding per target per lens with a defeater actually TRIED against the shipped form, independence stated, every unsound verdict routed to an Issue with a resolver, and the count of UNASSESSED instruments read back from the computed structure. Delivers dcInstrumentsEnterThePropriety. EXECUTE.. EXECUTE. 3 pts.
package ProjectDeliveryS686 {
    private import EngineElement::*;
    private import EngineWork::*;
    private import EngineVerification::*;
    private import EngineRelationships::*;

    #CharteredBy dependency from instrumentsEnterTheProprietyStory to d0361;

    part instrumentsEnterTheProprietyStory : Story {
        :>> id = "e672cd3d-8b96-4876-80ca-7df305f665fd";
        :>> title = "Sprint 686: The instruments enter the propriety. Six defects in one day came from things that MEASURE and none had been assessed by the panel that every blocking control passes (D0257); D0361 declares the measures and D0363 makes them model items with a computed assessed state. This sprint runs the FIRST TRANCHE over the two whose numbers reach a human with no gate between - the standing-brief facts script and the chart builders - one ProprietyFinding per target per lens with a defeater actually TRIED against the shipped form, independence stated, every unsound verdict routed to an Issue with a resolver, and the count of UNASSESSED instruments read back from the computed structure. Delivers dcInstrumentsEnterThePropriety. EXECUTE. (3 pts)";
        :>> createdAt = "2026-09-13"; :>> createdBy = "claudeFable5"; :>> kind = WorkKind::code; :>> priority = WorkPriority::p0; :>> owner = "claudeFable5"; :>> estimatedPoints = 3;
    }

    action def DeliveryRunS686 {
        action storyInstrumentsEnterThePropriety;
        verification storyInstrumentsEnterTheProprietyDoD : Test { :>> id = "eb938366-e593-4a63-a386-afc73639d0cc"; :>> method = VerificationMethod::test; :>> procedureText = "DELIVERED: .tracking/propriety-instruments.sysml (ProprietyRound6, pf56-pf65: instrument:execBriefFacts x five lenses, instrument:execBriefCharts x five lenses; each defeater names what was TRIED - the command, the fixture, the worktree - or what STANDS; header states independence: targets authored by claudeOpus5, assessor claudeFable5, same lineage, the one sound verdict named as testimony per D0080); two unsound verdicts routed: issue511 (facts.py typed-figure control fitted to the version shape; a false 37 in cliShowLenses provenance) with resolver dcFactsTypedFiguresAreRefused, issue512 (text painted over by a later shape measured by no fit_check kind) with resolver dcFiguresRefuseOccludedText, both tasks on the backlog with DoDs and D0388 pairs named; `keel show control-structure .` reads execBriefFacts and execBriefCharts with five lens rows each and 18 of 20 sensors UNASSESSED; dcInstrumentsEnterTheProprietyDoD re-recorded at this commit with the count as receipt."; }
        // RAN: ProprietyRound6 pf56-pf65 in .tracking/propriety-instruments.sysml; issue511/issue512 with resolvers in the tree; keel show control-structure . -> execBriefFacts 5 lens rows (overfit unsound, 4 conditional), execBriefCharts 5 lens rows (overfit unsound, 3 conditional, measurability sound), 18 of 20 sensors UNASSESSED; keel show view propriety . -> 10 instrument: rows; keel gate validate . -> 786 clean
        part storyInstrumentsEnterTheProprietyDoDR1 : TestResult { :>> id = "7b6c4d88-4505-4221-9115-c500b6214f2a"; :>> outcome = VerdictKind::pass; :>> judgedAgainst = "584df9a"; :>> judgedAt = "2026-09-12"; :>> judgedBy = "claudeFable5"; }
    }

    verification instrumentsEnterTheProprietyRefineGate : Test { :>> id = "b7b01361-343c-45c7-a34a-9028cb64356c"; :>> title = "Sprint 686 refine gate (DoR)"; :>> createdAt = "2026-09-13"; :>> createdBy = "claudeFable5"; :>> method = VerificationMethod::inspect; :>> procedureText = "Chartered by D0361. Three points: ten adversarial experiments against two shipped scripts (a facts run over the tree, a mutated worktree run, headless-Chromium measurement of four builders, a stale-file probe, independent re-derivation of four counts, two binary hashes), ten findings authored, two Issues and two resolver tasks, the ceremony. DoR: the DoD is on the backlog item; the previous result (dcInstrumentsEnterTheProprietyDoDR1, fail, PARTIAL) names exactly the clause this sprint closes; the item is chartered by d0361. NOT A PROCESS CHANGE: findings do not fix (control-propriety skill); no guard, hook, schema or workflow changes; the two repairs are backlog tasks. NOT A FORK: the panel's five lenses and its verdict vocabulary are D0257's; the tranche's two targets are the DoD's own words."; }
    // RAN: DoD on the backlog item; prior result DoDR1 fail PARTIAL names the tranche clause; #CharteredBy to d0361 in the sprint file; keel show control-structure . -> execBriefFacts 5 lens rows (overfit unsound, 4 conditional), execBriefCharts 5 lens rows (overfit unsound, 3 conditional, measurability sound), 18 of 20 sensors UNASSESSED; keel show view propriety . -> 10 instrument: rows; keel gate validate . -> 786 clean
    part instrumentsEnterTheProprietyRefineGateR1 : TestResult { :>> id = "e1e23da4-6a7b-429f-b40e-67b00202ce65"; :>> outcome = VerdictKind::proposed; :>> judgedAgainst = "584df9a"; :>> judgedAt = "2026-09-12"; :>> judgedBy = "claudeFable5"; }
    verification instrumentsEnterTheProprietyStandupGate : Test { :>> id = "83a68892-5324-4604-8ec7-d69150159643"; :>> title = "Sprint 686 standup gate"; :>> createdAt = "2026-09-13"; :>> createdBy = "claudeFable5"; :>> method = VerificationMethod::inspect; :>> procedureText = "Order: run the shipped facts.py by path over 584df9a and read the facts back; try each defeater before its verdict is written (overfit: mutate the issue389 specimen's shape; classCoverage: grep builders for typed numerals and check_brief for a facts cross-check; changeRobustness: rename CliCommand in a detached worktree and re-run; circumventability: hand require_complete a complete file with tree 0000000; measurability: re-derive four counts by independent grep, hash both binaries); for charts, feed the shipped builders long labels and a zero and measure with the shipped fit_check in both font passes, then check every number reaches the aria-label; write ProprietyRound6; record the two resolver tasks, then the two Issues (the resolver must exist first); record the sprint and the DoD result; gate validate, check-engine, guard --no-receipt, sync-claude --check; read back control-structure; remove the worktree; commit."; }
    // RAN: the standup order was carried out in this commit: facts run 1m53s 143 facts over 584df9a; worktree kwt686 mutated and removed (git worktree list -> 0 kwt686); charts_defeaters.py measured 4 fixtures with shipped fit_check; record task x2 then record issue x2 (resolver-first, refused otherwise)
    part instrumentsEnterTheProprietyStandupGateR1 : TestResult { :>> id = "01a14ba9-ccd0-4c50-9735-64963d2dbf09"; :>> outcome = VerdictKind::proposed; :>> judgedAgainst = "584df9a"; :>> judgedAt = "2026-09-12"; :>> judgedBy = "claudeFable5"; }
    verification instrumentsEnterTheProprietyImplementGate : Test { :>> id = "2bb3c2d3-ae6f-47a9-b1ac-48a706fba11e"; :>> title = "Sprint 686 implement gate"; :>> createdAt = "2026-09-13"; :>> createdBy = "claudeFable5"; :>> method = VerificationMethod::test; :>> procedureText = "Ten findings from ten experiments, all against the shipped files at 584df9a. FACTS: overfit UNSOUND - the only typed-figure control matches the version shape vN.N.N; cliShowLenses `how` says '37 is the number to publish' against a value of 51, routingThreeSamplesMinutes is a literal 60, scopeDaysSinceRule a typed date. classCoverage conditional - numerals typed in builder prose (build_2026_09_11_two_safety_folds.py:185) reach the page with no `how` and check_brief holds no facts cross-check. changeRobustness conditional - with CliCommand renamed in a worktree the script published cliRecords=cliShowLenses=cliTopLevel=cliLive=0 with complete=true; only the builder's census cross-check (34) would refuse; glob/grep counts have no second source. circumventability conditional - require_complete accepted tree=0000000 generatedAt=2026-01-01; KEEL_BIN names any binary and no fact records which. measurability conditional - 85/51/297/458 re-derived and matched; perf timings name no host, routing facts are parsed from issue392 prose, eight `how` strings name keel.exe while keel-serve.exe answered (sha256 4cf849bd vs 003548f2, both 0.4.1). CHARTS: overfit UNSOUND - bars() 70-char label painted under the rect drawn after it, shipped fit_check CLEAN in both passes while dots/two_lane/timeline long labels were caught (OVERLAP 7px, OVERRUN 101px, OVERLAP 12px). classCoverage conditional - a zero drawn as a 2px bar; occlusion unmeasured. changeRobustness conditional - ten CSS tokens and the face inherited from the previous page head, all present 3x today, unresolved var() paints black silently. circumventability conditional - aria= override emitted verbatim ('every count is zero' over a bar reading 17); check_brief requires only role=img and 25 chars; no shipped builder passes aria (habit, not control). measurability SOUND (testimony) - every number handed to bars/stacked/timeline/dots appears in its aria-label. Records: ProprietyRound6 pf56-pf65; issue511 + dcFactsTypedFiguresAreRefused; issue512 + dcFiguresRefuseOccludedText."; }
    // RAN: python scratchpad/s686/charts_defeaters.py -> bars_long_label CLEAN, dots OVERLAP 7px, two_lane OVERRUN 101px, timeline OVERLAP 12px, aria all numbers present x4, override verbatim, zero rect width=2; stale_route.py -> require_complete ACCEPTED tree 0000000; facts_mut.json -> cliRecords 0 cliTopLevel 0 census topLevel 34 complete true; re-derived 85/51/297/458 equal; keel show control-structure . -> execBriefFacts 5 lens rows (overfit unsound, 4 conditional), execBriefCharts 5 lens rows (overfit unsound, 3 conditional, measurability sound), 18 of 20 sensors UNASSESSED; keel show view propriety . -> 10 instrument: rows; keel gate validate . -> 786 clean
    part instrumentsEnterTheProprietyImplementGateR1 : TestResult { :>> id = "62c36615-6096-45c8-ae95-b992372a5f9b"; :>> outcome = VerdictKind::pass; :>> judgedAgainst = "584df9a"; :>> judgedAt = "2026-09-12"; :>> judgedBy = "claudeFable5"; }
    verification instrumentsEnterTheProprietyReviewGate : Test { :>> id = "19645807-da50-48e7-8d71-a4552c711092"; :>> title = "Sprint 686 review gate — three passes per D0172"; :>> createdAt = "2026-09-13"; :>> createdBy = "claudeFable5"; :>> method = VerificationMethod::inspect; :>> procedureText = "Three passes (D0172). Correctness: every verdict's defeater names the command, fixture or file that established it, and the two unsound ones were reproduced against the shipped files, not a copy (the worktree was a git worktree of the same commit with one shape mutated, and the facts script run from it was the tracked file). Honesty: the one sound verdict is labelled testimony because the assessor shares the targets' lineage (D0080); the conditional verdicts record what STANDS rather than being softened to sound; UNASSESSED is reported as 18 of 20, read from the computed structure, and the DoD is recorded proposed at this tree because its method is inspect (D0312 B), not pass on my word. Scope: no fix rides in this commit - findings do not fix; the two repairs are backlog tasks with their own DoDs and D0388 pairs; no guard, hook, process or schema touched."; }
    // RAN: three passes read against the shipped files: every defeater names its command or fixture; sound verdict labelled testimony in pf65; git diff --stat -> no scripts/ change in this commit (findings do not fix); keel show control-structure . -> execBriefFacts 5 lens rows (overfit unsound, 4 conditional), execBriefCharts 5 lens rows (overfit unsound, 3 conditional, measurability sound), 18 of 20 sensors UNASSESSED; keel show view propriety . -> 10 instrument: rows; keel gate validate . -> 786 clean
    part instrumentsEnterTheProprietyReviewGateR1 : TestResult { :>> id = "cab566f1-0548-41db-88f5-7a443df7277f"; :>> outcome = VerdictKind::proposed; :>> judgedAgainst = "584df9a"; :>> judgedAt = "2026-09-12"; :>> judgedBy = "claudeFable5"; }
    verification instrumentsEnterTheProprietyCloseOutGate : Test { :>> id = "3a0819c0-c4bc-4f8a-a7ef-4f6722625c2c"; :>> title = "Sprint 686 closeOut gate (autonomous, D0049)"; :>> createdAt = "2026-09-13"; :>> createdBy = "claudeFable5"; :>> method = VerificationMethod::inspect; :>> procedureText = "Closes on gate validate, gate check-engine, gate guard --no-receipt and sync-claude --check over the tree holding ProprietyRound6, issue511, issue512 and the two resolver tasks; on `keel show control-structure .` reading five lens rows for execBriefFacts and execBriefCharts and 18 UNASSESSED; on the mutated worktree removed before staging. dcInstrumentsEnterTheProprietyDoD re-recorded at this commit."; }
    // RAN: keel gate validate . -> 786 clean; keel gate check-engine . and keel gate guard --no-receipt . and keel sync-claude --check run after this record (see storyDoD receipt); git worktree list -> kwt686 absent; keel show control-structure . -> execBriefFacts 5 lens rows (overfit unsound, 4 conditional), execBriefCharts 5 lens rows (overfit unsound, 3 conditional, measurability sound), 18 of 20 sensors UNASSESSED; keel show view propriety . -> 10 instrument: rows; keel gate validate . -> 786 clean
    part instrumentsEnterTheProprietyCloseOutGateR1 : TestResult { :>> id = "7a3e80a0-bec8-4a02-8c6f-7c305f5ab0ba"; :>> outcome = VerdictKind::proposed; :>> judgedAgainst = "584df9a"; :>> judgedAt = "2026-09-12"; :>> judgedBy = "claudeFable5"; }
    verification instrumentsEnterTheProprietyRetroGate : Test { :>> id = "573bd7db-e1e7-4acb-8253-4cd8d5d58b1c"; :>> title = "Sprint 686 retro gate (autonomous, D0049)"; :>> createdAt = "2026-09-13"; :>> createdBy = "claudeFable5"; :>> method = VerificationMethod::analyze; :>> procedureText = "AVOIDABLE-ISSUE SCAN, two findings tracked, one root fix in this commit, one not a finding (D0131). TRACKED: issue511 - the issue389 control was fitted to its specimen and a false figure stands in provenance today - with resolver dcFactsTypedFiguresAreRefused; issue512 - occlusion is a hiding fit_check does not measure - with resolver dcFiguresRefuseOccludedText; both added to the backlog in this commit. FIXED AT THE ROOT, no item: `record issue --resolver X` refused because the resolver did not yet exist (issue109's control working as built) - the order is task first, Issue second, and this sprint's standup records that order for the skill to inherit. NOT A FINDING: the six conditional verdicts each name what STANDS and a one-line repair; they are propriety findings, not defects, and pf03/pf04 precedent is that a conditional stands as recorded until the panel is re-run after a change to the target. STATED: eighteen instruments remain UNASSESSED; the next tranche is chosen by the same rule this one was - the ones whose numbers reach a human with no gate between - and is not declared here, because declaring it would be authoring priority in prose."; }
    // RAN: two findings tracked: issue511 -> dcFactsTypedFiguresAreRefused, issue512 -> dcFiguresRefuseOccludedText, both in .tracking/backlog.sysml this commit; retro-backlog guard read on the working tree
    part instrumentsEnterTheProprietyRetroGateR1 : TestResult { :>> id = "458b20b8-5ec1-4003-8933-0bc8653cb55a"; :>> outcome = VerdictKind::proposed; :>> judgedAgainst = "584df9a"; :>> judgedAt = "2026-09-12"; :>> judgedBy = "claudeFable5"; }
}
