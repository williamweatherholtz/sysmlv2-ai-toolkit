// ProjectDeliveryS608 — Sprint 608: Sprint 608 resolves issue393 under D0379: sync-claude deploys a skill's references/ directory beside its SKILL.md, and the claude-surface-drift check fails a deployed skill whose instructions name a relative reference that does not resolve. The stpa SOP the deployed skill tells the agent to read is present after this sprint, and the class - an instruction the agent cannot follow - is caught by the guard that already owns the surface.. EXECUTE. 2 pts.
package ProjectDeliveryS608 {
    private import EngineElement::*;
    private import EngineWork::*;
    private import EngineVerification::*;
    private import EngineRelationships::*;

    #CharteredBy dependency from skillReferencesAreDeployedStory to d0379;

    part skillReferencesAreDeployedStory : Story {
        :>> id = "89247b71-e3d9-4982-a27b-93013039ec11";
        :>> title = "Sprint 608: Sprint 608 resolves issue393 under D0379: sync-claude deploys a skill's references/ directory beside its SKILL.md, and the claude-surface-drift check fails a deployed skill whose instructions name a relative reference that does not resolve. The stpa SOP the deployed skill tells the agent to read is present after this sprint, and the class - an instruction the agent cannot follow - is caught by the guard that already owns the surface. (2 pts)";
        :>> createdAt = "2026-09-08"; :>> createdBy = "claudeOpus5"; :>> kind = WorkKind::code; :>> priority = WorkPriority::p0; :>> owner = "claudeOpus5"; :>> estimatedPoints = 2;
    }

    action def DeliveryRunS608 {
        action storySkillReferencesAreDeployed;
        verification storySkillReferencesAreDeployedDoD : Test { :>> id = "dd5f0dcb-339d-4155-87c3-402e7e87c496"; :>> method = VerificationMethod::test; :>> procedureText = "DONE MEANS: .claude/skills/stpa/references/sop.md exists after keel sync-claude and is byte-equal to .engine/skills/stpa/references/sop.md; a unit test constructs a skill whose SKILL.md names references/missing.md with no such file and asserts sync_claude(check) reports it, and constructs a skill naming no reference and asserts the check reports nothing for it; the count of skills naming an unresolved reference is read from the check's output over the live surface before the fix (computed) and is zero after; keel guard ALL PASS; cargo test --release green."; }
        // RAN: cmp .engine/skills/stpa/references/sop.md .claude/skills/stpa/references/sop.md -> BYTE-EQUAL; sync-claude --check before the fix: 2 deployed skill(s) name a reference that does not resolve (stpa -> references/sop.md, requirement-quality -> references/ears.md, references/ruleset.md); after: keel-owned subset matches (46 skills); cargo test --release claude_surface 13 passed 0 failed (a_deployed_instruction_that_cannot_be_followed_is_drift, a_skills_references_deploy_beside_it); keel guard --no-receipt ALL PASS (WARN only)
        part storySkillReferencesAreDeployedDoDR1 : TestResult { :>> id = "8c84bc34-153a-428e-a2e6-978f6b9fcb68"; :>> outcome = VerdictKind::pass; :>> judgedAgainst = "748746a"; :>> judgedAt = "2026-09-08"; :>> judgedBy = "claudeOpus5"; }
    }

    verification skillReferencesAreDeployedRefineGate : Test { :>> id = "520fcdf6-eab7-4c64-a5e9-f94659f12628"; :>> title = "Sprint 608 refine gate (DoR)"; :>> createdAt = "2026-09-08"; :>> createdBy = "claudeOpus5"; :>> method = VerificationMethod::inspect; :>> procedureText = "Scope: claude_surface.rs only - sync_claude deploys references and scans deployed SKILL.md text; a test module fixture; the deployed reference files. Sized 2: a generator change with a fixture test and no schema. Chartered by D0379 (accepted under standing consent at record time). Blocking dependency: none."; }
    // RAN: cmp .engine/skills/stpa/references/sop.md .claude/skills/stpa/references/sop.md -> BYTE-EQUAL; sync-claude --check before the fix: 2 deployed skill(s) name a reference that does not resolve (stpa -> references/sop.md, requirement-quality -> references/ears.md, references/ruleset.md); after: keel-owned subset matches (46 skills); cargo test --release claude_surface 13 passed 0 failed (a_deployed_instruction_that_cannot_be_followed_is_drift, a_skills_references_deploy_beside_it); keel guard --no-receipt ALL PASS (WARN only)
    part skillReferencesAreDeployedRefineGateR1 : TestResult { :>> id = "f47db4ab-c141-4852-b4c8-72348b063691"; :>> outcome = VerdictKind::pass; :>> judgedAgainst = "748746a"; :>> judgedAt = "2026-09-08"; :>> judgedBy = "claudeOpus5"; }
    verification skillReferencesAreDeployedStandupGate : Test { :>> id = "6dd4ba93-50a5-49f3-a56e-c3c30a231181"; :>> title = "Sprint 608 standup gate"; :>> createdAt = "2026-09-08"; :>> createdBy = "claudeOpus5"; :>> method = VerificationMethod::inspect; :>> procedureText = "Plan: (1) run sync-claude --check on the live tree with the scan added, read the computed count of affected skills; (2) deploy references in sync_claude; (3) fixture test both directions; (4) sync-claude, guard, suite; (5) close."; }
    // RAN: cmp .engine/skills/stpa/references/sop.md .claude/skills/stpa/references/sop.md -> BYTE-EQUAL; sync-claude --check before the fix: 2 deployed skill(s) name a reference that does not resolve (stpa -> references/sop.md, requirement-quality -> references/ears.md, references/ruleset.md); after: keel-owned subset matches (46 skills); cargo test --release claude_surface 13 passed 0 failed (a_deployed_instruction_that_cannot_be_followed_is_drift, a_skills_references_deploy_beside_it); keel guard --no-receipt ALL PASS (WARN only)
    part skillReferencesAreDeployedStandupGateR1 : TestResult { :>> id = "011b80e5-848d-49ed-a72d-8cf279849be2"; :>> outcome = VerdictKind::pass; :>> judgedAgainst = "748746a"; :>> judgedAt = "2026-09-08"; :>> judgedBy = "claudeOpus5"; }
    verification skillReferencesAreDeployedImplementGate : Test { :>> id = "80b107c5-8615-4af3-aee9-57dd2ba8b490"; :>> title = "Sprint 608 implement gate"; :>> createdAt = "2026-09-08"; :>> createdBy = "claudeOpus5"; :>> method = VerificationMethod::test; :>> procedureText = "RAN: Write/Edit on keel-cli/src/claude_surface.rs; cargo build --release; keel sync-claude --check before the deploy (the computed count); keel sync-claude; keel guard --no-receipt; cargo test --release claude_surface."; }
    // RAN: cmp .engine/skills/stpa/references/sop.md .claude/skills/stpa/references/sop.md -> BYTE-EQUAL; sync-claude --check before the fix: 2 deployed skill(s) name a reference that does not resolve (stpa -> references/sop.md, requirement-quality -> references/ears.md, references/ruleset.md); after: keel-owned subset matches (46 skills); cargo test --release claude_surface 13 passed 0 failed (a_deployed_instruction_that_cannot_be_followed_is_drift, a_skills_references_deploy_beside_it); keel guard --no-receipt ALL PASS (WARN only)
    part skillReferencesAreDeployedImplementGateR1 : TestResult { :>> id = "a8dd4edf-20d7-4cac-8fb9-ffc7a4851284"; :>> outcome = VerdictKind::pass; :>> judgedAgainst = "748746a"; :>> judgedAt = "2026-09-08"; :>> judgedBy = "claudeOpus5"; }
    verification skillReferencesAreDeployedReviewGate : Test { :>> id = "50ec00ee-fcb9-4cb0-a711-fed3dc889251"; :>> title = "Sprint 608 review gate — three passes per D0172"; :>> createdAt = "2026-09-08"; :>> createdBy = "claudeOpus5"; :>> method = VerificationMethod::inspect; :>> procedureText = "Reviewed against the DoD: the deployed sop.md is byte-equal to its source; the fixture test fails the missing-reference skill and is silent on the reference-free skill; the affected-skill count was computed by the scan, not written by hand."; }
    // RAN: cmp .engine/skills/stpa/references/sop.md .claude/skills/stpa/references/sop.md -> BYTE-EQUAL; sync-claude --check before the fix: 2 deployed skill(s) name a reference that does not resolve (stpa -> references/sop.md, requirement-quality -> references/ears.md, references/ruleset.md); after: keel-owned subset matches (46 skills); cargo test --release claude_surface 13 passed 0 failed (a_deployed_instruction_that_cannot_be_followed_is_drift, a_skills_references_deploy_beside_it); keel guard --no-receipt ALL PASS (WARN only)
    part skillReferencesAreDeployedReviewGateR1 : TestResult { :>> id = "6a2aa750-6752-4708-9fd3-79cb7153780f"; :>> outcome = VerdictKind::pass; :>> judgedAgainst = "748746a"; :>> judgedAt = "2026-09-08"; :>> judgedBy = "claudeOpus5"; }
    verification skillReferencesAreDeployedCloseOutGate : Test { :>> id = "3f298791-f017-4829-8277-f1b19770606e"; :>> title = "Sprint 608 closeOut gate (autonomous, D0049)"; :>> createdAt = "2026-09-08"; :>> createdBy = "claudeOpus5"; :>> method = VerificationMethod::inspect; :>> procedureText = "Sprint 608 closes when dcSkillReferencesAreDeployedDoD carries a pass at the commit that deployed the references and issue393 computes resolved."; }
    // RAN: cmp .engine/skills/stpa/references/sop.md .claude/skills/stpa/references/sop.md -> BYTE-EQUAL; sync-claude --check before the fix: 2 deployed skill(s) name a reference that does not resolve (stpa -> references/sop.md, requirement-quality -> references/ears.md, references/ruleset.md); after: keel-owned subset matches (46 skills); cargo test --release claude_surface 13 passed 0 failed (a_deployed_instruction_that_cannot_be_followed_is_drift, a_skills_references_deploy_beside_it); keel guard --no-receipt ALL PASS (WARN only)
    part skillReferencesAreDeployedCloseOutGateR1 : TestResult { :>> id = "8dd8fdfb-f938-4ec4-ac32-eb5652177fa0"; :>> outcome = VerdictKind::pass; :>> judgedAgainst = "748746a"; :>> judgedAt = "2026-09-08"; :>> judgedBy = "claudeOpus5"; }
    verification skillReferencesAreDeployedRetroGate : Test { :>> id = "992f5e63-655a-4d15-bbe1-0ae1cc15a49a"; :>> title = "Sprint 608 retro gate (autonomous, D0049)"; :>> createdAt = "2026-09-08"; :>> createdBy = "claudeOpus5"; :>> method = VerificationMethod::analyze; :>> procedureText = "Retro held; avoidable-issue scan: one avoidable issue surfaced while this sprint was open - the project's first rejection of a proposed Decision (d0376, the human's brief answer) had no CLI write path and was a hand edit, recorded as issue414 with resolver dcRejectHasACliPath. Process improvement from the sprint's own work: none beyond D0379 - the claude-surface-drift guard now asks whether a deployed instruction is followable, which is the class the sprint closed."; }
    // RAN: cmp .engine/skills/stpa/references/sop.md .claude/skills/stpa/references/sop.md -> BYTE-EQUAL; sync-claude --check before the fix: 2 deployed skill(s) name a reference that does not resolve (stpa -> references/sop.md, requirement-quality -> references/ears.md, references/ruleset.md); after: keel-owned subset matches (46 skills); cargo test --release claude_surface 13 passed 0 failed (a_deployed_instruction_that_cannot_be_followed_is_drift, a_skills_references_deploy_beside_it); keel guard --no-receipt ALL PASS (WARN only)
    part skillReferencesAreDeployedRetroGateR1 : TestResult { :>> id = "53f01ad5-32b6-460f-9d03-8ed6a6dfcea6"; :>> outcome = VerdictKind::pass; :>> judgedAgainst = "748746a"; :>> judgedAt = "2026-09-08"; :>> judgedBy = "claudeOpus5"; }
}
