// ProjectDeliveryS339 — Sprint 339: a count is a link to the work it counts. Fixes an off-by-four
// binding defect the human hit in the live console. EXECUTE. 5 pts.
package ProjectDeliveryS339 {
    private import EngineElement::*;
    private import EngineWork::*;
    private import EngineVerification::*;
    private import EngineRelationships::*;

    #CharteredBy dependency from obligationActionableStory to d0152;

    part obligationActionableStory : Story {
        :>> id = "0d8004e0-0814-64e0-9b3e-0000003004e0";
        :>> title = "Sprint 339: obligation cards act — UC-C7, srConsoleObligationActionable, issue141 (5 pts)";
        :>> createdAt = "2026-08-17"; :>> createdBy = "claudeOpus5"; :>> kind = WorkKind::code; :>> priority = WorkPriority::p0; :>> owner = "claudeOpus5"; :>> estimatedPoints = 5;
    }

    action def DeliveryRunS339 {
        action storyObligationActionable;
        verification storyObligationActionableDoD : Test { :>> id = "0d8004e1-0814-64e1-9b3e-0000003004e1"; :>> method = VerificationMethod::demo; :>> procedureText = "Requested by wweatherholtz from the live console: clicking a card, especially on the act surface, should take them to the place to act. INVESTIGATING IT FOUND A DEFECT I INTRODUCED IN SPRINT 316 (issue141, discoveredInField): the arrival view bound clicks POSITIONALLY — main.querySelectorAll('.c') indexed against the viewpoint array — and sprint 316 then prepended the obligation bar into the SAME container, where each class is rendered by the same card() helper and carries the same `.c` class. So the four obligation cards took indices 0..3: an obligation card selected an arbitrary viewpoint, every viewpoint card was off by four, and the last four selected undefined and rendered nothing. Both card kinds are correct in isolation; the defect exists only in their combination, which is the check-narrower-than-its-subject shape of issue109/136/139. DELIVERED: (1) every obligation class now carries the viewpoint IDENTITY (server-side), so the destination is derived from the same declaration as the count and cannot drift into a hardcoded class-to-page map; (2) clicks bind by identity through ONE delegated handler on the container, so there is no index to be off by and a render path added later inherits the behaviour rather than producing dead cards; (3) selecting a card selects its SURFACE too, so the nav agrees with what is rendered; (4) only cards with a resolvable target get the affordance; (5) a GENERIC viewpoint panel over a new /api/computed/:cmd, because two of the four act destinations — authority-queue and sitting-coverage — had NO endpoint at all and would have been dead clicks. VERIFIED LIVE, all four: each card's target resolves to a declared viewpoint on the act surface and its view computes 200; an unbound command (diagram) is REFUSED with the CLI command to run rather than rendering blank; the positional binding is absent from the SERVED console; obligation counts unchanged through the unified dispatch (1 / 10 / 8 / 19). clippy clean; 228 tests; validate 367 clean; 35 guards ALL PASS."; }
        part storyObligationActionableDoDR1 : TestResult { :>> id = "0d8004e2-0814-64e2-9b3e-0000003004e2"; :>> outcome = VerdictKind::pass; :>> judgedAgainst = "844b4ca"; :>> judgedAt = "2026-08-17"; :>> judgedBy = "claudeOpus5"; }
    }

    verification oaRefineGate : Test { :>> id = "0d8004e3-0814-64e3-9b3e-0000003004e3"; :>> title = "Sprint 339 refine gate (DoR)"; :>> createdAt = "2026-08-17"; :>> createdBy = "claudeOpus5"; :>> method = VerificationMethod::inspect; :>> procedureText = "DoR. The request named a UseCase gap and a defect at once. UC-C2 already covers DISCHARGING an obligation where it was found; nothing covered GETTING there from the count, which is the step the reader performs FIRST — so UC-C7 is the traversal UC-C2 presumes, not a duplicate of it. Recorded as a UseCase plus a derived requirement under the already-accepted N-C1, so no new acceptance gate was needed: this decomposes an accepted Need rather than adding scope. estimatedPoints=5."; }
    part oaRefineGateR1 : TestResult { :>> id = "0d8004e4-0814-64e4-9b3e-0000003004e4"; :>> outcome = VerdictKind::pass; :>> judgedAgainst = "844b4ca"; :>> judgedAt = "2026-08-17"; :>> judgedBy = "claudeOpus5"; }

    verification oaStandupGate : Test { :>> id = "0d8004e5-0814-64e5-9b3e-0000003004e5"; :>> title = "Sprint 339 standup gate"; :>> createdAt = "2026-08-17"; :>> createdBy = "claudeOpus5"; :>> method = VerificationMethod::inspect; :>> procedureText = "Approach: derive the DESTINATION from the same declaration that produced the COUNT rather than mapping class to page — the count is already read from the view the renderer names, so the destination is free and cannot drift. Bind by identity on the element, never by list position. Extend the EXISTING dispatch table (obligation_count's) into one shared computed_view rather than adding a second table that could disagree with it. No blockers."; }
    part oaStandupGateR1 : TestResult { :>> id = "0d8004e6-0814-64e6-9b3e-0000003004e6"; :>> outcome = VerdictKind::pass; :>> judgedAgainst = "844b4ca"; :>> judgedAt = "2026-08-17"; :>> judgedBy = "claudeOpus5"; }

    verification oaImplementGate : Test { :>> id = "0d8004e7-0814-64e7-9b3e-0000003004e7"; :>> title = "Sprint 339 implement gate"; :>> createdAt = "2026-08-17"; :>> createdBy = "claudeOpus5"; :>> method = VerificationMethod::test; :>> procedureText = "THE FEATURE WOULD HAVE BEEN HOLLOW FOR HALF ITS CARDS AND CHECKING IS WHAT CAUGHT IT: I traced each of the four act renderers to the panel that would render it and found only two — orient and dispositions. `keel authority-queue` and `keel sitting-coverage` had NO endpoint (both 404) and the console's render chain had no final else, so those two clicks would have changed nothing at all while the card advertised 'click to act'. That is worse than the defect being fixed. Hence /api/computed/:cmd plus a generic viewpoint panel: any declared viewpoint's computed view renders, so a newly declared act class is reachable with no route and no console change, and a command with no binding FAILS LOUD naming the CLI command instead of showing a blank panel. THE DISPATCH WAS UNIFIED rather than duplicated — obligation_count now reads its JSON from computed_view, so the counter and the panel cannot disagree about which view a renderer names. FOUR THINGS THE COMPILER AND THE HOST CAUGHT: three wrong function paths (suspect lives in govern, orphans in algo, verification is a module not a view fn), indicators' arity, an err_json helper that does not exist, and the build refusing because MY OWN serve process held keel.exe — kill, then build, then serve, which is sprint 317's recorded ordering."; }
    part oaImplementGateR1 : TestResult { :>> id = "0d8004e8-0814-64e8-9b3e-0000003004e8"; :>> outcome = VerdictKind::pass; :>> judgedAgainst = "844b4ca"; :>> judgedAt = "2026-08-17"; :>> judgedBy = "claudeOpus5"; }

    verification oaReviewGate : Test { :>> id = "0d8004e9-0814-64e9-9b3e-0000003004e9"; :>> title = "Sprint 339 review gate"; :>> createdAt = "2026-08-17"; :>> createdBy = "claudeOpus5"; :>> method = VerificationMethod::inspect; :>> procedureText = "Reviewed. THE CONTROL FOR ISSUE141 IS STRUCTURAL, AND THE REASON I GAVE WAS WRONG - CORRECTED 2026-08-17 (sprint 340). I wrote that no automated check in this engine can read a browser, so no gate would have caught a DOM index bug and none would catch the next one. The human asked whether Playwright would fix it, and it would; a cheaper text-level test over the embedded asset would too, and now does. What was true is that this repository has no such test - an absence I asserted as an impossibility. What replaces the guard is making the error unrepresentable — the target travels ON the element and is resolved by identity, so there is no position to be off by, and srConsoleObligationActionable states that as a REQUIREMENT rather than leaving it as a habit I might not repeat. Delegation does the same for the other half: the handler is bound once on the container, so a future render path cannot forget to attach it. THE DEFECT'S PROVENANCE IS RECORDED HONESTLY: discoveredInField = true, because the human found it by using the console, not I by testing it — sprint 316 shipped the obligation bar into a container whose click handler I did not re-read, and no gate, test or review caught it for two sprints."; }
    part oaReviewGateR1 : TestResult { :>> id = "0d8004ea-0814-64ea-9b3e-0000003004ea"; :>> outcome = VerdictKind::pass; :>> judgedAgainst = "844b4ca"; :>> judgedAt = "2026-08-17"; :>> judgedBy = "claudeOpus5"; }

    verification oaCloseOutGate : Test { :>> id = "0d8004eb-0814-64eb-9b3e-0000003004eb"; :>> title = "Sprint 339 closeOut gate (autonomous, D0049)"; :>> createdAt = "2026-08-17"; :>> createdBy = "claudeOpus5"; :>> method = VerificationMethod::inspect; :>> procedureText = "Autonomous closeOut (D0049). UC-C7 and srConsoleObligationActionable recorded under the accepted N-C1; issue141 recorded and resolved by dcObligationActionable. /api/computed/:cmd is advertised in the API's read contract so a client discovers it rather than guessing. clippy clean; 228 tests; validate 367 clean; check-engine clean; 35 guards ALL PASS. NOT DONE, and stated: the generic panel renders a computed view READ-ONLY — for authority-queue and sitting-coverage the reader can now see the work but still discharges it elsewhere, so UC-C2's acting half is served by a purpose-built panel for two of four classes only. The human's confirmation that a click lands where the work is has NOT been recorded as a verification: that is theirs to give."; }
    part oaCloseOutGateR1 : TestResult { :>> id = "0d8004ec-0814-64ec-9b3e-0000003004ec"; :>> outcome = VerdictKind::pass; :>> judgedAgainst = "844b4ca"; :>> judgedAt = "2026-08-17"; :>> judgedBy = "claudeOpus5"; }

    verification oaRetroGate : Test { :>> id = "0d8004ed-0814-64ed-9b3e-0000003004ed"; :>> title = "Sprint 339 retro gate (autonomous, D0049)"; :>> createdAt = "2026-08-17"; :>> createdBy = "claudeOpus5"; :>> method = VerificationMethod::analyze; :>> procedureText = "Autonomous retro (D0049) under D0131's retroTrack. AVOIDABLE-ISSUE: issue141 is mine, it shipped in sprint 316, and the human found it by using the console. The precise miss is worth stating because it is not carelessness about the new code: I ADDED the obligation bar to a container and did not re-read the click handler that already indexed that container's children. The lesson generalises past the DOM — prepending to a shared container changes the meaning of every positional reference into it, and positional references are invisible at the point of the change. ALSO: this is the second time in two days that a console defect was found by the human rather than by me, the first being the pipe that killed the server. The console has no tests, no gate reads it, and my only verification of it is curling the served HTML for markers — which catches a stale binary and cannot catch wrong behaviour. WELL: (1) tracing every destination to its panel BEFORE declaring the feature done found that half the cards would have been dead clicks, which is the part the request did not mention and would have been the real disappointment; (2) the two dispatch tables were unified rather than duplicated; (3) the unbound-command path fails loud with the CLI command, so the generic panel cannot pass off an empty result as a computed one. Estimate 5 pts, delivered."; }
    part oaRetroGateR1 : TestResult { :>> id = "0d8004ee-0814-64ee-9b3e-0000003004ee"; :>> outcome = VerdictKind::pass; :>> judgedAgainst = "844b4ca"; :>> judgedAt = "2026-08-17"; :>> judgedBy = "claudeOpus5"; }
}
