// ProjectDeliveryS614 — Sprint 614: Sprint 614 makes the probe a step (dcAdHocChecksAreProbedFirst, resolves issue400) under D0388: the two defective checks from the issue are re-run against known cases and shown to fail their probe while their corrections pass it, the practice is written in CLAUDE.md section 4 with the two fates of the probe cases, and every kept python check carries its cases as --probe.. EXECUTE. 2 pts.
package ProjectDeliveryS614 {
    private import EngineElement::*;
    private import EngineWork::*;
    private import EngineVerification::*;
    private import EngineRelationships::*;

    #CharteredBy dependency from checksAreProbedFirstStory to d0388;

    part checksAreProbedFirstStory : Story {
        :>> id = "f62cea31-4e28-4fa2-96bd-0a99603c7a13";
        :>> title = "Sprint 614: Sprint 614 makes the probe a step (dcAdHocChecksAreProbedFirst, resolves issue400) under D0388: the two defective checks from the issue are re-run against known cases and shown to fail their probe while their corrections pass it, the practice is written in CLAUDE.md section 4 with the two fates of the probe cases, and every kept python check carries its cases as --probe. (2 pts)";
        :>> createdAt = "2026-09-08"; :>> createdBy = "claudeOpus5"; :>> kind = WorkKind::code; :>> priority = WorkPriority::p0; :>> owner = "claudeOpus5"; :>> estimatedPoints = 2;
    }

    action def DeliveryRunS614 {
        action storyChecksAreProbedFirst;
        verification storyChecksAreProbedFirstDoD : Test { :>> id = "916b1e15-324f-48ff-a875-6cd1f08b2d30"; :>> method = VerificationMethod::test; :>> procedureText = "DONE MEANS: no number from a hand-written check is stated before the check has been probed against a known answer. Resolves issue400: two ad-hoc checks in one session returned wrong answers on their first run - a census that scored 64 of 64 by matching its own registry, caught only because the answer was too good, and a controller check that reported the human's process model missing by comparing a role name to an anchor name case-sensitively, which was stated in a response before being recomputed. DO: make the probe a step rather than a virtue - for any check written to answer a question, run it first against one case known to be positive and one known to be negative, and only then read the real tree. Decide whether the probe cases are recorded with the check (which makes it an instrument under D0361, inheriting the propriety lenses) or discarded with it, and record which. VERIFY: the two checks from this issue are re-run against their known cases and the artefacts of the original defects are reproduced - a census that matches its own registry, a comparison that fails on case - so the probe is shown to catch what it is for rather than asserted to; and the practice is written where a future session reads it, not only in this criterion."; }
        // RAN: issue400_reproduction.py 10 pass; CLAUDE.md section 4 rule; D0388
        part storyChecksAreProbedFirstDoDR1 : TestResult { :>> id = "8d0a85dc-1579-4330-a795-c07cba863718"; :>> outcome = VerdictKind::pass; :>> judgedAgainst = "82d826c43bb5b1d4e20e9f5e8ef8735638a7a693"; :>> judgedAt = "2026-09-08"; :>> judgedBy = "claudeOpus5"; }
    }

    verification checksAreProbedFirstRefineGate : Test { :>> id = "9706c02c-c34c-432a-b4fd-313e9d11a15d"; :>> title = "Sprint 614 refine gate (DoR)"; :>> createdAt = "2026-09-08"; :>> createdBy = "claudeOpus5"; :>> method = VerificationMethod::inspect; :>> procedureText = "Scope: scripts/probes/issue400_reproduction.py (both defective checks, both corrections, known-positive and known-negative per check); CLAUDE.md section 4; D0388. Out of scope: a hook that detects an unprobed check - no gate reads conversational output (D0151), and the item asks for a step, not a control; running the probes in CI is dcScriptProbesRunInCi. Estimate 2 points: one reproduction script, one doc rule, one Decision. DoR: points set, charter d0388, scope clear, no blocking dependency, DoD authored."; }
    // RAN: DoR inspected: 2 points, charter d0388, scope in the refine text, DoD authored, no blocking dependency
    part checksAreProbedFirstRefineGateR1 : TestResult { :>> id = "da3e0db0-29f2-40d6-8b97-4c22d3e7bbc0"; :>> outcome = VerdictKind::pass; :>> judgedAgainst = "82d826c43bb5b1d4e20e9f5e8ef8735638a7a693"; :>> judgedAt = "2026-09-08"; :>> judgedBy = "claudeOpus5"; }
    verification checksAreProbedFirstStandupGate : Test { :>> id = "38821ca6-4fb5-4be4-8de2-06b5461021a2"; :>> title = "Sprint 614 standup gate"; :>> createdAt = "2026-09-08"; :>> createdBy = "claudeOpus5"; :>> method = VerificationMethod::inspect; :>> procedureText = "Plan: (1) reconstruct the 2026-09-06 census (name near FAIL/violation across every .rs) and the 2026-09-07 anchor comparison (role == anchor) as written; (2) choose the probe cases before reading the tree - instruments-declared / doc-guard-count for the census, the human controller for the anchor; (3) run defective and corrected checks against them and over the tree; (4) D0388 with the two fates; (5) the CLAUDE.md rule through textpatch; gates."; }
    // RAN: plan of five steps recorded in the standup text; all five executed in this commit
    part checksAreProbedFirstStandupGateR1 : TestResult { :>> id = "d9e8b77c-009d-4e6b-90e2-1da50a3ff89a"; :>> outcome = VerdictKind::pass; :>> judgedAgainst = "82d826c43bb5b1d4e20e9f5e8ef8735638a7a693"; :>> judgedAt = "2026-09-08"; :>> judgedBy = "claudeOpus5"; }
    verification checksAreProbedFirstImplementGate : Test { :>> id = "10d24507-90de-4499-b6c6-07a00b12fc65"; :>> title = "Sprint 614 implement gate"; :>> createdAt = "2026-09-08"; :>> createdBy = "claudeOpus5"; :>> method = VerificationMethod::test; :>> procedureText = "RAN: python scripts/probes/issue400_reproduction.py (10 pass, exit 0); keel guard instruments-declared . ; keel gate --fast; keel guard."; }
    // RAN: python scripts/probes/issue400_reproduction.py: 10 pass 0 failures exit 0 - defective census reads doc-guard-count covered and scores 67 of 67, corrected reads it uncovered; defective anchor comparison reads human anchorless and 7 of 7, corrected reads ctHuman; CLAUDE.md rule inserted through textpatch (8 insertions); keel guard instruments-declared PASS; keel gate --fast clean
    part checksAreProbedFirstImplementGateR1 : TestResult { :>> id = "a5fd9852-2289-4a86-9941-a976cf84d28b"; :>> outcome = VerdictKind::pass; :>> judgedAgainst = "82d826c43bb5b1d4e20e9f5e8ef8735638a7a693"; :>> judgedAt = "2026-09-08"; :>> judgedBy = "claudeOpus5"; }
    verification checksAreProbedFirstReviewGate : Test { :>> id = "274a212a-3b13-43ba-ae0c-0a7aae464abd"; :>> title = "Sprint 614 review gate — three passes per D0172"; :>> createdAt = "2026-09-08"; :>> createdBy = "claudeOpus5"; :>> method = VerificationMethod::inspect; :>> procedureText = "Reviewed against the DoD: the census artefact is reproduced (67 of 67 on today's tree, doc-guard-count read as covered) and the probe's known-negative catches it; the case comparison artefact is reproduced (human read as anchorless, 7 of 7) and the known-positive catches it; the corrections pass both cases; the practice is in CLAUDE.md section 4 with D0388 recording where the cases live."; }
    // RAN: reviewed against the DoD: both original artefacts reproduced on their known cases, both corrections hold, the practice is in CLAUDE.md section 4, the two fates of the probe cases are D0388
    part checksAreProbedFirstReviewGateR1 : TestResult { :>> id = "2d89ed28-c62c-46f0-baad-1ad403eb317e"; :>> outcome = VerdictKind::pass; :>> judgedAgainst = "82d826c43bb5b1d4e20e9f5e8ef8735638a7a693"; :>> judgedAt = "2026-09-08"; :>> judgedBy = "claudeOpus5"; }
    verification checksAreProbedFirstCloseOutGate : Test { :>> id = "7ed1523d-d1e0-42eb-8d92-d0ebb1211eed"; :>> title = "Sprint 614 closeOut gate (autonomous, D0049)"; :>> createdAt = "2026-09-08"; :>> createdBy = "claudeOpus5"; :>> method = VerificationMethod::inspect; :>> procedureText = "Sprint 614 closes when dcAdHocChecksAreProbedFirstDoD carries a pass at the commit that carries the reproduction, the rule and the Decision, and issue400 leaves keel show open-issues."; }
    // RAN: DoD pass recorded on storyChecksAreProbedFirstDoD and dcAdHocChecksAreProbedFirstDoD at this SHA; issue400 resolution read back from keel show open-issues after the record
    part checksAreProbedFirstCloseOutGateR1 : TestResult { :>> id = "7daccece-fe0a-42f8-a4b9-95fdada1eff2"; :>> outcome = VerdictKind::pass; :>> judgedAgainst = "82d826c43bb5b1d4e20e9f5e8ef8735638a7a693"; :>> judgedAt = "2026-09-08"; :>> judgedBy = "claudeOpus5"; }
    verification checksAreProbedFirstRetroGate : Test { :>> id = "e9dda9ee-2efd-4125-932d-9bc0f87f3387"; :>> title = "Sprint 614 retro gate (autonomous, D0049)"; :>> createdAt = "2026-09-08"; :>> createdBy = "claudeOpus5"; :>> method = VerificationMethod::analyze; :>> procedureText = "Retro held; avoidable-issue scan: no new item - the reproduction runs by hand, the gap dcScriptProbesRunInCi already tracks. Process improvement: the corrected census in the reproduction reads 3 of 67 by a crude test-body match and is labelled a figure, not a measure - a real census of which guards have a defect-constructing test would be an instrument with its own probe, and is not this sprint's claim."; }
    // RAN: retro held; avoidable-issue scan: none - the hand-run gap is dcScriptProbesRunInCi; no new Issue recorded in this commit
    part checksAreProbedFirstRetroGateR1 : TestResult { :>> id = "f6aa9777-8bcd-4ed1-8262-7c52da53e9e2"; :>> outcome = VerdictKind::pass; :>> judgedAgainst = "82d826c43bb5b1d4e20e9f5e8ef8735638a7a693"; :>> judgedAt = "2026-09-08"; :>> judgedBy = "claudeOpus5"; }
}
