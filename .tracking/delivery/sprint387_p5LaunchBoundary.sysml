// ProjectDeliveryS387 — Sprint 387: P5 - the launch boundary: run records, the post-run gate, spawn hardening, the headless-ask mapping. EXECUTE. 13 pts.
package ProjectDeliveryS387 {
    private import EngineElement::*;
    private import EngineWork::*;
    private import EngineVerification::*;
    private import EngineRelationships::*;

    #CharteredBy dependency from p5LaunchBoundaryStory to d0182;

    part p5LaunchBoundaryStory : Story {
        :>> id = "4736bc8b-6f45-4293-818e-12074cbb1140";
        :>> title = "Sprint 387: P5 - launched runs are recorded, gated, and reviewable (13 pts)";
        :>> createdAt = "2026-08-21"; :>> createdBy = "claudeFable5"; :>> kind = WorkKind::code; :>> priority = WorkPriority::p0; :>> owner = "claudeFable5"; :>> estimatedPoints = 13;
    }

    action def DeliveryRunS387 {
        action storyP5LaunchBoundary;
        verification storyP5LaunchBoundaryDoD : Test { :>> id = "27a36956-c54f-4282-a039-3fcfa3bd41e0"; :>> method = VerificationMethod::test; :>> procedureText = "DELIVERED BACKLOG ITEMS: p5RunRecords, p5PostRunGate, p5CompletionCheck, p5SpawnHardening, p5Forms. THE LIFECYCLE (keel-cli/src/launcher.rs): prepare REFUSES a dirty tree (proven by test; the refusal is PM's launch-dirty-refusal ledger event - the PESS-2 watch metric now reports real data), snapshots the spawn HEAD and fingerprint, and resolves the run's actor or refuses; finish computes the post-run gate (validate + activation-filtered guards + blocking rules) over the run-start-to-clean-tree diff, writes the machine-local run record ALWAYS (schema declared: id/process/actor/startedTs/headAtSpawn/fingerprintAtSpawn/exit/turns/durationMs/timedOut/gate/diffFiles), and for NON-EMPTY diffs writes ONE tracked summary - a Test + TestResult pair with judgedAgainst = the spawn HEAD (K12) under the RUN'S stamped actor, whose text routes the diff to human review UNCONDITIONALLY green or red (proven by test both ways). K5 minimal completion: a run that changed files but recorded nothing in .tracking gets a gate problem (no checker over free-text producedArtifact - that waits for D0185's typed field, the recorded trigger). SPAWN HARDENING in the SSE launch path: absolute KEEL_BIN from current_exe, the run's KEEL_ACTOR, KEEL_RUN_ID arming the headless mapping, a 1800s wall-clock silence timeout that kills the tree and records timed-out (max-turns bounds turns, not stalls), and assistant-turn counting into the record. HEADLESS-ASK (d0182 charter note 2): the ask-pending entry is registered BEFORE any wait, the wait is bounded at 60s (well under the hook deadline), and expiry/absent-console maps to DENY plus a queued obligation - the serve side (POST /api/run/ask, GET /api/run/asks, GET+POST /api/run/answer) exercised LIVE over real HTTP (pending -> human allow -> poll reads allow), and the hook deny branch exercised LIVE against a 404ing console with the obligation file read back. THE FRICTION VALVE (charter note 3): POST /api/commit - the human's click integrates their uncommitted console accepts through the NORMAL commit path (pre-commit gate unbypassed; a sub-8-char message refused, run live). FORMS (p5Forms, THIN per its own scope-pressure clause): GET /api/launch/form generates the per-process form from the MODEL (purpose + declared steps + the one free-text field), refuses undeclared targets (run live); typed inputs arrive with D0185. All five new routes declared in the write contract (the route-accounting control caught them undeclared first - its job). 223 tests; clippy 0; 41 guards ALL PASS."; }
        part storyP5LaunchBoundaryDoDR1 : TestResult { :>> id = "23edd7c6-8368-48f1-af54-6932a7585064"; :>> outcome = VerdictKind::pass; :>> judgedAgainst = "7061513"; :>> judgedAt = "2026-08-21"; :>> judgedBy = "claudeFable5"; }
    }

    verification p5LaunchBoundaryRefineGate : Test { :>> id = "c951b41c-80f7-48de-959d-2ae90a020727"; :>> title = "Sprint 387 refine gate (DoR)"; :>> createdAt = "2026-08-21"; :>> createdBy = "claudeFable5"; :>> method = VerificationMethod::inspect; :>> procedureText = "DoR. P5's five chartered items under d0181/d0182, the recommended-next boundary work after P1. The accepted decision texts and the charter notes (ask-pending-before-blocking, the friction valve, pre-approved scopes as control-plane data) were the spec. estimatedPoints=13."; }
    part p5LaunchBoundaryRefineGateR1 : TestResult { :>> id = "6615997d-3a3d-4c63-8ca3-a3acd11c43b6"; :>> outcome = VerdictKind::pass; :>> judgedAgainst = "7061513"; :>> judgedAt = "2026-08-21"; :>> judgedBy = "claudeFable5"; }
    verification p5LaunchBoundaryStandupGate : Test { :>> id = "ac9481cb-d20c-45cd-bbf3-ea9e1286eb65"; :>> title = "Sprint 387 standup gate"; :>> createdAt = "2026-08-21"; :>> createdBy = "claudeFable5"; :>> method = VerificationMethod::inspect; :>> procedureText = "Approach: the lifecycle lives in a module TESTABLE OUTSIDE the SSE stream (prepare/finish), with the stream owning only spawn mechanics - the seam chosen so the gate logic is provable without spawning claude. In-place execution with concurrency 1 and single-writer-per-tree is the committed mode; worktrees stay deferred behind their named DoR. HONEST LIMITS, stated: the console-proxy APPROVE branch is proven over live HTTP at the endpoint seam while the hook's own approve path shares every line except the port constant with the proven deny path; and a full claude -p acceptance run rides the first real console launch - the mechanics (env injection, timeout, gate, records) are each individually proven."; }
    part p5LaunchBoundaryStandupGateR1 : TestResult { :>> id = "a26a0cba-f1f1-41ca-814c-bc408975cf45"; :>> outcome = VerdictKind::pass; :>> judgedAgainst = "7061513"; :>> judgedAt = "2026-08-21"; :>> judgedBy = "claudeFable5"; }
    verification p5LaunchBoundaryImplementGate : Test { :>> id = "f81af00c-cdf2-4880-9c9e-8214699d605a"; :>> title = "Sprint 387 implement gate"; :>> createdAt = "2026-08-21"; :>> createdBy = "claudeFable5"; :>> method = VerificationMethod::test; :>> procedureText = "Every branch run or tested: dirty-refuse + ledger event (test), clean-prepare snapshot (test), empty-diff local-only (test), non-empty-diff gated summary with spawn-HEAD judgedAgainst under the run actor (test), completion problem on no-tracked-output (in-gate), ask lifecycle pending->allow (live HTTP), form refusal (live), commit-action message floor (live), hook deny + obligation file (live against a 404ing console). THE ROUTE-ACCOUNTING CONTROL fired on the five new routes before they were declared - the second control this program has seen catch its own author mid-sprint. NOTABLE ENVIRONMENT FINDING: the human's live console on 7777 is running a STALE pre-program binary - flagged for restart in the report."; }
    part p5LaunchBoundaryImplementGateR1 : TestResult { :>> id = "a7cc6725-9f9f-4bc8-a3b0-bf96b1658641"; :>> outcome = VerdictKind::pass; :>> judgedAgainst = "7061513"; :>> judgedAt = "2026-08-21"; :>> judgedBy = "claudeFable5"; }
    verification p5LaunchBoundaryReviewGate : Test { :>> id = "26b2a55a-ea31-4049-a1d2-4ee37344ac4b"; :>> title = "Sprint 387 review gate — three passes per D0172"; :>> createdAt = "2026-08-21"; :>> createdBy = "claudeFable5"; :>> method = VerificationMethod::inspect; :>> procedureText = "PASS 1, CLAIMS vs computed/emitted: 223 tests, clippy 0 after real findings (a derive severed from its struct by a type-alias insertion - compile-caught; a route-accounting failure; redundant clones); every live claim from actual HTTP responses quoted in the transcript. PASS 2, BOUNDARY: the timeout path swaps in a disarmed TreeKiller so a dead PID is never taskkilled; the ask poll treats unknown ids as unknown, not denied; the commit action refuses thin messages. PASS 3, OWN DIFF: the alias-above-derive break was this sprint's own edit - the insertion-above-attributes variant of the doc-severing class already in the program retro. WHAT A REVIEWER SHOULD ATTACK: turns are counted as assistant-typed stream lines, an approximation until the transcript format is contracted; and the fire-ledger since-spawn check reads the last 200 lines, which a very chatty run could exceed - both stated here rather than discovered."; }
    part p5LaunchBoundaryReviewGateR1 : TestResult { :>> id = "5edb15b1-15af-44a4-b3aa-3ac7893a3922"; :>> outcome = VerdictKind::pass; :>> judgedAgainst = "7061513"; :>> judgedAt = "2026-08-21"; :>> judgedBy = "claudeFable5"; }
    verification p5LaunchBoundaryCloseOutGate : Test { :>> id = "4d53a839-7e13-4cea-a05f-ea22faacd032"; :>> title = "Sprint 387 closeOut gate (autonomous, D0049)"; :>> createdAt = "2026-08-21"; :>> createdBy = "claudeFable5"; :>> method = VerificationMethod::inspect; :>> procedureText = "Autonomous closeOut (D0049). Five p5 DoDs flipped at the judging HEAD; launcher module registered; five routes declared in the write contract; PM's dirtyTreeRefusals row now has a real data source. validate clean; 41 guards ALL PASS; 223 tests; clippy 0."; }
    part p5LaunchBoundaryCloseOutGateR1 : TestResult { :>> id = "294ef51e-107c-458e-8925-8e6552331310"; :>> outcome = VerdictKind::pass; :>> judgedAgainst = "7061513"; :>> judgedAt = "2026-08-21"; :>> judgedBy = "claudeFable5"; }
    verification p5LaunchBoundaryRetroGate : Test { :>> id = "667b05ac-0114-4739-a29c-2be274d2b41e"; :>> title = "Sprint 387 retro gate (autonomous, D0049)"; :>> createdAt = "2026-08-21"; :>> createdBy = "claudeFable5"; :>> method = VerificationMethod::analyze; :>> procedureText = "Autonomous retro (D0049). AVOIDABLE-ISSUE SCAN under rcRecurrence: (1) insertion-above-attributes joins the insertion-severs-docs class - occurrence three of insertion-placement defects this program; the preventing practice tightens to its final form: an insertion NEVER lands between an attribute/doc line and its item - anchor on the line ABOVE the attribute block; all three occurrences were machine-caught (clippy twice, rustc once), which is why no new control is proposed beyond the practice. (2) The heredoc-authoring escape-mangling recurred once more before the fix scripts moved fully to Write-tool files mid-sprint - the rule from sprint 384's retro, now actually followed, ended the recurrence within this same sprint. WELL: (1) the testable-seam split (launcher module vs SSE stream) meant the gate logic never needed a spawned agent to prove; (2) two controls (route-accounting, the dirty-refusal it now measures) each produced evidence within minutes of existing; (3) the stale-console finding came from a FAILED bind - an error message read instead of worked around. Estimate 13 pts, delivered."; }
    part p5LaunchBoundaryRetroGateR1 : TestResult { :>> id = "8fe3fd01-df90-4864-9ea6-894fa90f9099"; :>> outcome = VerdictKind::pass; :>> judgedAgainst = "7061513"; :>> judgedAt = "2026-08-21"; :>> judgedBy = "claudeFable5"; }
}
