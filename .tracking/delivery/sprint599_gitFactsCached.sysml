// ProjectDeliveryS599 — Sprint 599: Rank 2 of D0367: the facts orient asks git about an immutable commit are served from a content-addressed cache keyed by the full commit id (dcGitFactsAreContentAddressed, D0369). EXECUTE. 3 pts.
package ProjectDeliveryS599 {
    private import EngineElement::*;
    private import EngineWork::*;
    private import EngineVerification::*;
    private import EngineRelationships::*;

    #CharteredBy dependency from gitFactsCachedStory to d0369;

    part gitFactsCachedStory : Story {
        :>> id = "a3daf55c-957f-434b-9a04-5e9910ce85e0";
        :>> title = "Sprint 599: Rank 2 of D0367: the facts orient asks git about an immutable commit are served from a content-addressed cache keyed by the full commit id (dcGitFactsAreContentAddressed, D0369) (3 pts)";
        :>> createdAt = "2026-09-07"; :>> createdBy = "claudeOpus5"; :>> kind = WorkKind::code; :>> priority = WorkPriority::p0; :>> owner = "claudeOpus5"; :>> estimatedPoints = 3;
    }

    action def DeliveryRunS599 {
        action storyGitFactsCached;
        verification storyGitFactsCachedDoD : Test { :>> id = "bee14c48-7914-4a9c-9484-3b0893c370f2"; :>> method = VerificationMethod::test; :>> procedureText = "DELIVERED: new module keel-cli/src/gitfacts.rs - a machine-local cache at .keel/cache/git-facts.toml (gitignored under .keel/, written temp-then-rename through write::write_atomic, loaded once per process in 9 ms at 1 MB) of four fact kinds keyed by a FULL 40-hex commit id: is-commit positives, the DoD criterion of a task as a file held it at that commit, the grep fallback's answer, and the diff paths between that commit and a full HEAD id; orient's valid_commits, criterion_suspects, git_criterion_at and changed_paths_since answer from it on a hit and fill it from their existing batched spawns on a miss; a short id resolves in-process from the batch-check line git already returns (remember_resolution/full_id, never persisted); a negative is-commit and a git failure are never remembered. VERIFIED: gitfacts tests a_full_sha_entry_round_trips_and_a_short_sha_is_never_written (a full-sha entry is written, reloads from disk and answers; a bare short-sha query is not written; a short id resolved in-process lands under its FULL key and the short id is not on disk; a resolution that is not a full id is not trusted; a negative is not written), a_corrupt_cache_file_reads_as_empty and full_sha_is_forty_hex pass in cargo test --release; clippy pedantic clean. MEASURED on this tree from a shell timer, same binary shape: keel orient . with the previous binary 6284-37303 ms (the two long runs a cold host), this binary cache absent 6728 / 8753 ms with git x24 in 3263-3505 ms, warm 1727 / 1696 / 1669 ms with git x11 in 484-521 ms; stdout byte-identical across previous-binary, absent, cold and warm (diff, 4027 bytes). keel guard 11744 ms to 8151 / 7079 ms, stdout identical apart from timing lines. Resolves the spawn term of issue409."; }
        // RAN: cargo test --release -p keel-cli --lib -- gitfacts (3 passed: a_full_sha_entry_round_trips_and_a_short_sha_is_never_written, a_corrupt_cache_file_reads_as_empty, full_sha_is_forty_hex); keel orient . stdout byte-identical absent/cold/warm (diff, 4027 bytes); KEEL_PERF=2 cold git x24 in 3263ms, warm git x11 in 484-521ms
        part storyGitFactsCachedDoDR1 : TestResult { :>> id = "9ab669e3-2470-4cad-bc50-c1391c4db44a"; :>> outcome = VerdictKind::pass; :>> judgedAgainst = "7affb600940adc6447b361c51ef8b1826ecf7c61"; :>> judgedAt = "2026-09-07T23:58:00-06:00"; :>> judgedBy = "claudeOpus5"; }
    }

    verification gitFactsCachedRefineGate : Test { :>> id = "9ba7d53f-ca8b-469b-b3bd-92a9a97ba539"; :>> title = "Sprint 599 refine gate (DoR)"; :>> createdAt = "2026-09-07"; :>> createdBy = "claudeOpus5"; :>> method = VerificationMethod::inspect; :>> procedureText = "READY, 3 pts: one new module, four orient helpers rewired, three tests, a measurement - the DoD names the check for each. Chartered by D0369, a non-fork Decision that accepted at record time under D0207: neither orient.rs nor the new module is under the keystone lock. One DoD correction made before the pass, by its owner: the DoD named `keel orient --json`, a flag orient does not have (`keel orient [ROOT] [--html]`); the check is the plain output."; }
    // RAN: cargo clippy --release -p keel-cli --all-targets clean; cargo test --release -p keel-cli --lib -- gitfacts orient (6 passed); timed keel orient . cache-absent 6728ms git x24 / warm 1727-1669ms git x11, stdout diff identical across previous-binary/absent/cold/warm; keel guard 11744ms -> 7079-8151ms
    part gitFactsCachedRefineGateR1 : TestResult { :>> id = "10e6d928-c158-4741-be9a-9b73ea31eba7"; :>> outcome = VerdictKind::pass; :>> judgedAgainst = "7affb600940adc6447b361c51ef8b1826ecf7c61"; :>> judgedAt = "2026-09-07T23:58:00-06:00"; :>> judgedBy = "claudeOpus5"; }
    verification gitFactsCachedStandupGate : Test { :>> id = "1a80be84-3631-4168-873a-648d29675973"; :>> title = "Sprint 599 standup gate"; :>> createdAt = "2026-09-07"; :>> createdBy = "claudeOpus5"; :>> method = VerificationMethod::inspect; :>> procedureText = "ONE CHOICE that the measurement forced: the first cut cached only what a full 40-hex anchor asked, and the warm run still spawned x24 - 4993 of the 5527 judgedAgainst anchors in this tree are 7-hex. Resolving them on disk would have cached a mutable fact; resolving them in-process from the one cat-file --batch-check orient already runs (its output line carries the full oid) costs no new spawn and keeps every disk entry a function of an immutable object. A second choice: cache the EXTRACTED criterion, not the blob - a tracking file at a commit is 150 KB, the criterion is one line."; }
    // RAN: cargo clippy --release -p keel-cli --all-targets clean; cargo test --release -p keel-cli --lib -- gitfacts orient (6 passed); timed keel orient . cache-absent 6728ms git x24 / warm 1727-1669ms git x11, stdout diff identical across previous-binary/absent/cold/warm; keel guard 11744ms -> 7079-8151ms
    part gitFactsCachedStandupGateR1 : TestResult { :>> id = "bdba3243-ce58-49c1-bcda-a83bc2c9f60a"; :>> outcome = VerdictKind::pass; :>> judgedAgainst = "7affb600940adc6447b361c51ef8b1826ecf7c61"; :>> judgedAt = "2026-09-07T23:58:00-06:00"; :>> judgedBy = "claudeOpus5"; }
    verification gitFactsCachedImplementGate : Test { :>> id = "d5bc1c3b-f779-4a4c-9783-643f9347e089"; :>> title = "Sprint 599 implement gate"; :>> createdAt = "2026-09-07"; :>> createdBy = "claudeOpus5"; :>> method = VerificationMethod::test; :>> procedureText = "RAN: python patch_orient_gitfacts.py, fix_clippy_gitfacts.py, patch_resolution.py (each replacement refusing unless its anchor occurs once), cargo clippy --release -p keel-cli --all-targets (clean after eight lints: doc backticks, significant-drop, expect on Option, single-match-else x3, map_or_else), cargo build --release, cargo test --release -p keel-cli --lib -- gitfacts orient, the full lib suite, timed keel orient and keel guard runs from a copy of the binary (keel-serve.exe) with the cache removed then warm, diff of stdout against the previous binary's, cp to .keel/bin/keel.exe."; }
    // RAN: cargo clippy --release -p keel-cli --all-targets clean; cargo test --release -p keel-cli --lib -- gitfacts orient (6 passed); timed keel orient . cache-absent 6728ms git x24 / warm 1727-1669ms git x11, stdout diff identical across previous-binary/absent/cold/warm; keel guard 11744ms -> 7079-8151ms
    part gitFactsCachedImplementGateR1 : TestResult { :>> id = "69b7f975-7f4c-420f-8ca7-59030a5680b2"; :>> outcome = VerdictKind::pass; :>> judgedAgainst = "7affb600940adc6447b361c51ef8b1826ecf7c61"; :>> judgedAt = "2026-09-07T23:58:00-06:00"; :>> judgedBy = "claudeOpus5"; }
    verification gitFactsCachedReviewGate : Test { :>> id = "564aaad0-f4cd-4442-8b10-e08154a585fb"; :>> title = "Sprint 599 review gate — three passes per D0172"; :>> createdAt = "2026-09-07"; :>> createdBy = "claudeOpus5"; :>> method = VerificationMethod::inspect; :>> procedureText = "THREE QUESTIONS (D0172). Can a cached answer be wrong? Only if a value keyed by a full commit id is not a function of that commit: is-commit positives, a file's content at a commit, a grep over a commit's tree and a diff between two commits all are; the two mutable inputs - a short id's resolution and a negative - are refused by construction and pinned by the round-trip test. Is the output the same? Byte-identical stdout across four states on this tree, and the frontier, suspect set and reasons are all in that output. What is NOT claimed: that the wall time transfers (it is this host's spawn cost); that the guards' own batched blob reads in staleness are cached (they are not - rank 3's corpus work); that the residual 11 spawns are removable by this mechanism (they ask about HEAD and the remote, not about a commit - dcGitReadsStayInProcess judges them against its 500 ms line, and the warm figure sits on it at 484-521 ms)."; }
    // RAN: cargo clippy --release -p keel-cli --all-targets clean; cargo test --release -p keel-cli --lib -- gitfacts orient (6 passed); timed keel orient . cache-absent 6728ms git x24 / warm 1727-1669ms git x11, stdout diff identical across previous-binary/absent/cold/warm; keel guard 11744ms -> 7079-8151ms
    part gitFactsCachedReviewGateR1 : TestResult { :>> id = "425a5ce5-ff8b-4e9e-993c-edf561d4bb3f"; :>> outcome = VerdictKind::pass; :>> judgedAgainst = "7affb600940adc6447b361c51ef8b1826ecf7c61"; :>> judgedAt = "2026-09-07T23:58:00-06:00"; :>> judgedBy = "claudeOpus5"; }
    verification gitFactsCachedCloseOutGate : Test { :>> id = "8b71037d-020c-451c-be14-9cebd65ff72e"; :>> title = "Sprint 599 closeOut gate (autonomous, D0049)"; :>> createdAt = "2026-09-07"; :>> createdBy = "claudeOpus5"; :>> method = VerificationMethod::inspect; :>> procedureText = "CLOSED. keel orient 5.2 s to 1.7 s warm on this tree, git spawns 24 to 11; keel guard 11.7 s to 7-8 s. D0369 accepted at record time. The frontier's next item is dcOneCorpusPerProcess."; }
    // RAN: cargo clippy --release -p keel-cli --all-targets clean; cargo test --release -p keel-cli --lib -- gitfacts orient (6 passed); timed keel orient . cache-absent 6728ms git x24 / warm 1727-1669ms git x11, stdout diff identical across previous-binary/absent/cold/warm; keel guard 11744ms -> 7079-8151ms
    part gitFactsCachedCloseOutGateR1 : TestResult { :>> id = "1779a79a-eca3-4503-aaa7-fb9e78bb0e7a"; :>> outcome = VerdictKind::pass; :>> judgedAgainst = "7affb600940adc6447b361c51ef8b1826ecf7c61"; :>> judgedAt = "2026-09-07T23:58:00-06:00"; :>> judgedBy = "claudeOpus5"; }
    verification gitFactsCachedRetroGate : Test { :>> id = "537770da-b9cb-4e0b-b1e4-1c69a0525944"; :>> title = "Sprint 599 retro gate (autonomous, D0049)"; :>> createdAt = "2026-09-07"; :>> createdBy = "claudeOpus5"; :>> method = VerificationMethod::analyze; :>> procedureText = "AVOIDABLE-ISSUE SCAN HELD. One process finding: the DoD I authored in the spike named a flag that does not exist (`orient --json`), caught only when the check ran and every output file came back empty - the same class as issue372's 'a claim that names its check must have run it', here at DoD-authoring time; no new item, the correction is in this sprint's refine text and the existing dcGateAnswersFromItsReceipt DoD was re-read for the same defect (it names commands that exist). One design finding kept for rank 3: the first measurement showed the cache correct and useless (x24 warm) because the KEY the anchors carry is not the key the cache accepts - a cache keyed by what is on disk must be checked against what the data actually says, which is what the warm spawn count did here and what the (len, mtime) validation must do for dcOneCorpusPerProcess."; }
    // RAN: cargo clippy --release -p keel-cli --all-targets clean; cargo test --release -p keel-cli --lib -- gitfacts orient (6 passed); timed keel orient . cache-absent 6728ms git x24 / warm 1727-1669ms git x11, stdout diff identical across previous-binary/absent/cold/warm; keel guard 11744ms -> 7079-8151ms
    part gitFactsCachedRetroGateR1 : TestResult { :>> id = "fe90249c-b280-4cdf-ab14-ab51819c49a2"; :>> outcome = VerdictKind::pass; :>> judgedAgainst = "7affb600940adc6447b361c51ef8b1826ecf7c61"; :>> judgedAt = "2026-09-07T23:58:00-06:00"; :>> judgedBy = "claudeOpus5"; }
}
