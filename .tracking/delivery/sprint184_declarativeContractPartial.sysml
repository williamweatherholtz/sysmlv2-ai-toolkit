// ProjectDeliveryS184 — Sprint 184: declarativeContractPartial (D0105/D0107, CONTRACT phase).
// Accept the migration as PARTIAL (D0107) + CONTRACT the 5 clean-fit guards: rewire them to source their
// violations from their declared rule (view::rule_violations) — the single gate source — and retire the
// bespoke charter predicate. The ~8 bad-fit guards stay Rust (D0105 rollback). CR. 2 pt. AUTONOMOUS (D0049).
package ProjectDeliveryS184 {
    private import EngineElement::*;
    private import EngineWork::*;
    private import EngineVerification::*;
    private import EngineRelationships::*;

    #CharteredBy dependency from declContractStory to d0107;

    part declContractStory : Story {
        :>> id = "63940516-2c7d-4e8f-c184-51627384c001";
        :>> title = "Sprint 184: declarativeContractPartial (2 pt) - accept partial migration (D0107) + CONTRACT the 5 rule-at-parity guards";
        :>> createdAt = "2026-07-03"; :>> createdBy = "wweatherholtz"; :>> kind = WorkKind::code; :>> priority = WorkPriority::p1; :>> owner = "claudeOpus"; :>> estimatedPoints = 2;
    }

    action def DeliveryRunS184 {
        action storyDeclContract;
        verification storyDeclContractDoD : Test { :>> id = "63940516-2c7d-4e8f-c184-51627384c002"; :>> method = VerificationMethod::test; :>> procedureText = "D0107 (accepted by the human: 'Accept partial migration + CONTRACT the 5') + the D0105 CONTRACT phase. (1) view::rule_violations(root, rule_name) -> (subjects_scanned, sorted violations): the single-rule evaluator the guards source from. (2) CONTRACT: the 5 clean-fit guards rewired to source from their declared rule — requirement-rootedness->capabilityRootednessRule, issues->issuesTriagedRule, decision-rationale->decisionRationaleRule, acceptance-events->acceptanceEventRule, charter->charterRule; the bespoke charter predicate (added_delivery_files/chartered_work/charter_violations + charter_selftest) RETIRED (its logic + parity now live in the rule + view::tests::edge_rule_newly_added_scope_restricts_to_staged_files). Guard NAMES + report format + commit-gating UNCHANGED. (3) The ~8 bad-fit guards stay Rust (D0105 rollback). (4) doc-sync: CLAUDE.md Sec 5 declarative-controls note. VERIFY: keel guard ALL PASS (14 names; the 5 now rule-sourced: acceptance-events 103 / issues 56 / decision-rationale 107 / charter 0 / requirement-rootedness 0, all 0 violations); clippy -D warnings clean; cargo test (10 suites ok) green; keel validate (197) green; D0107 kernel-validated."; }
        part storyDeclContractDoDR1 : TestResult { :>> id = "63940516-2c7d-4e8f-c184-51627384c003"; :>> outcome = VerdictKind::pass; :>> judgedAgainst = "b1c81e9"; :>> judgedAt = "2026-07-03"; :>> judgedBy = "claudeOpus"; }
    }

    verification declContractRefineGate : Test { :>> id = "63940516-2c7d-4e8f-c184-51627384c004"; :>> title = "Sprint 184 refine gate (DoR)"; :>> createdAt = "2026-07-03"; :>> createdBy = "claudeOpus"; :>> method = VerificationMethod::inspect; :>> procedureText = "DoR: human accepted partial migration + CONTRACT the 5 (D0107). Parity for all 5 proven in sprints 178-183. estimatedPoints=2. #CharteredBy d0107. DoR met."; }
    part declContractRefineGateR1 : TestResult { :>> id = "63940516-2c7d-4e8f-c184-51627384c005"; :>> outcome = VerdictKind::pass; :>> judgedAgainst = "b1c81e9"; :>> judgedAt = "2026-07-03"; :>> judgedBy = "claudeOpus"; }
    verification declContractStandupGate : Test { :>> id = "63940516-2c7d-4e8f-c184-51627384c006"; :>> title = "Sprint 184 standup gate"; :>> createdAt = "2026-07-03"; :>> createdBy = "claudeOpus"; :>> method = VerificationMethod::inspect; :>> procedureText = "Approach: add view::rule_violations; rewire the 5 guards to it; delete the dead charter predicate fns + selftest; doc-sync; verify guard ALL PASS unchanged. Keep git_stdout (process-change uses it). The ~8 bad-fit guards untouched."; }
    part declContractStandupGateR1 : TestResult { :>> id = "63940516-2c7d-4e8f-c184-51627384c007"; :>> outcome = VerdictKind::pass; :>> judgedAgainst = "b1c81e9"; :>> judgedAt = "2026-07-03"; :>> judgedBy = "claudeOpus"; }
    verification declContractImplementGate : Test { :>> id = "63940516-2c7d-4e8f-c184-51627384c008"; :>> title = "Sprint 184 implement gate"; :>> createdAt = "2026-07-03"; :>> createdBy = "claudeOpus"; :>> method = VerificationMethod::test; :>> procedureText = "rule_violations added; 5 guards rewired; charter predicate + selftest retired; doc-sync done. keel guard ALL PASS (5 rule-sourced, 0 violations); clippy -D clean; cargo test 10 suites ok; keel validate 197 green."; }
    part declContractImplementGateR1 : TestResult { :>> id = "63940516-2c7d-4e8f-c184-51627384c009"; :>> outcome = VerdictKind::pass; :>> judgedAgainst = "b1c81e9"; :>> judgedAt = "2026-07-03"; :>> judgedBy = "claudeOpus"; }
    verification declContractReviewGate : Test { :>> id = "63940516-2c7d-4e8f-c184-51627384c00a"; :>> title = "Sprint 184 review gate"; :>> createdAt = "2026-07-03"; :>> createdBy = "claudeOpus"; :>> method = VerificationMethod::inspect; :>> procedureText = "Reviewed. The CONTRACT is honest: the 5 guards keep their names/format/gating but their VIOLATIONS now come from the declared rule (single source), and the duplicated charter predicate is genuinely gone (logic + test moved to the rule). Parity was proven per-rule before retirement (sprints 178-183). The bad-fit guards correctly stay Rust (D0107). Clean."; }
    part declContractReviewGateR1 : TestResult { :>> id = "63940516-2c7d-4e8f-c184-51627384c00b"; :>> outcome = VerdictKind::pass; :>> judgedAgainst = "b1c81e9"; :>> judgedAt = "2026-07-03"; :>> judgedBy = "claudeOpus"; }
    verification declContractCloseOutGate : Test { :>> id = "63940516-2c7d-4e8f-c184-51627384c00c"; :>> title = "Sprint 184 closeOut gate (autonomous, D0049)"; :>> createdAt = "2026-07-03"; :>> createdBy = "claudeOpus"; :>> method = VerificationMethod::inspect; :>> procedureText = "Autonomous closeOut (D0049): DoD pass; the declarative-controls migration is COMPLETE for its clean-fit scope — 5 guards rule-sourced (single source), bad-fit guards stay Rust, mechanism proven for downstream. keel guard ALL PASS; clippy + cargo test + keel validate green. Self-evidencing (D0051)."; }
    part declContractCloseOutGateR1 : TestResult { :>> id = "63940516-2c7d-4e8f-c184-51627384c00d"; :>> outcome = VerdictKind::pass; :>> judgedAgainst = "b1c81e9"; :>> judgedAt = "2026-07-03"; :>> judgedBy = "claudeOpus"; }
    verification declContractRetroGate : Test { :>> id = "63940516-2c7d-4e8f-c184-51627384c00e"; :>> title = "Sprint 184 retro gate (autonomous, D0049)"; :>> createdAt = "2026-07-03"; :>> createdBy = "claudeOpus"; :>> method = VerificationMethod::analyze; :>> procedureText = "Autonomous retro (D0049). WELL: the migration closed honestly — surfaced the partial-fit finding (a majority of conformance guards are bad-fit) to the human at D0105's own reconsider threshold, got an explicit decision (D0107), and CONTRACTed exactly the proven-parity set; no guard weakened (ALL PASS unchanged). AVOIDABLE-ISSUE SCAN: none new; the recurring clippy doc-lints on new code remain the only friction. LESSON: a declarative-controls migration's honest end-state is PARTIAL — the value is the mechanism + downstream declarability + retiring the clean duplicates, not converting every bespoke guard. Estimate 2 pt held. DELIVERABLE COMPLETE for D0105/D0107 clean scope. Remaining follow-ups (tracked, not blocking): keel-check name reconciliation; viewpoint-renderer (borderline) if desired; the earlier queue (serveBusinessNeedsView, issue056 C12, issue058 detecting rule)."; }
    part declContractRetroGateR1 : TestResult { :>> id = "63940516-2c7d-4e8f-c184-51627384c00f"; :>> outcome = VerdictKind::pass; :>> judgedAgainst = "b1c81e9"; :>> judgedAt = "2026-07-03"; :>> judgedBy = "claudeOpus"; }
}
