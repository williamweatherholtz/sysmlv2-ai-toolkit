// ProjectDeliveryS607 — Sprint 607: The brief contract's word budgets are held by the check, not hoped in the skill (dcBriefBudgetsAreHeld, D0355, issue413). EXECUTE. 2 pts.
package ProjectDeliveryS607 {
    private import EngineElement::*;
    private import EngineWork::*;
    private import EngineVerification::*;
    private import EngineRelationships::*;

    #CharteredBy dependency from briefBudgetsAreHeldStory to d0355;

    part briefBudgetsAreHeldStory : Story {
        :>> id = "dd854d2b-8896-4741-91c5-cef930524144";
        :>> title = "Sprint 607: The brief contract's word budgets are held by the check, not hoped in the skill (dcBriefBudgetsAreHeld, D0355, issue413) (2 pts)";
        :>> createdAt = "2026-09-08"; :>> createdBy = "claudeOpus5"; :>> kind = WorkKind::code; :>> priority = WorkPriority::p0; :>> owner = "claudeOpus5"; :>> estimatedPoints = 2;
    }

    action def DeliveryRunS607 {
        action storyBriefBudgetsAreHeld;
        verification storyBriefBudgetsAreHeldDoD : Test { :>> id = "17b17276-ce16-4320-b3f5-7cecf9e10158"; :>> method = VerificationMethod::test; :>> procedureText = "DELIVERED BACKLOG ITEMS: dcBriefBudgetsAreHeld. DONE MEANS: check_brief in scripts/check_templates.py refuses a page whose headline (data-digest='title') exceeds 18 words, whose ask block (class='ask') exceeds 70, or whose provenance strip (data-digest='provenance') exceeds 60, naming the section, its count and its limit; the whole-page ceiling (TERSE_CEILING, 450 reader words) is read from the decision file 0377 and applies only once that Decision carries DecisionStatus::accepted. VERIFIED HOW: `python scripts/check_templates.py --brief` on the page published on 2026-09-08 (the empty-queue page) reports three violations - headline 26 over 18, the ask 133 over 70, provenance strip 71 over 60 - and exits 1; on the page rewritten to replace it reports clean and, with the ceiling forced to 450 through check_brief(ceiling=450), clean at 447 reader words; `python scripts/check_templates.py --self-test` passes 5 of 5 (in-budget page passes, 27-word headline refused, 80-word ask refused, ceiling refused when given, no ceiling when not given) and exits 0. Resolves issue413."; }
        // RAN: python scripts/check_templates.py --self-test: 5 of 5 pass, exit 0; python scripts/check_templates.py --brief on the published 2026-09-08 empty-queue page: 3 violations (headline 26 over 18, the ask 133 over 70, provenance strip 71 over 60), exit 1; on the terse page: clean, and clean with ceiling=450 forced at 447 reader words (headline 15, ask 47, provenance 42); keel validate . 690 clean; keel guard --no-receipt ALL PASS
        part storyBriefBudgetsAreHeldDoDR1 : TestResult { :>> id = "0b52f3d1-285d-4bd7-9583-6332e1ef0e5a"; :>> outcome = VerdictKind::pass; :>> judgedAgainst = "d6d5556fbf24b6cd30a6669d40b1cd7eecbf6c70"; :>> judgedAt = "2026-09-08"; :>> judgedBy = "claudeOpus5"; }
    }

    verification briefBudgetsAreHeldRefineGate : Test { :>> id = "8892bb32-bfee-4b02-9a8b-58cb2cca13f5"; :>> title = "Sprint 607 refine gate (DoR)"; :>> createdAt = "2026-09-08"; :>> createdBy = "claudeOpus5"; :>> method = VerificationMethod::inspect; :>> procedureText = "READY, 2 pts: one function gains a budget loop and a ceiling clause, one fixture builder and one self-test are added, one skill section gains the enforcement note, and the page that failed is rewritten by a new builder. Chartered by D0355, the accepted Decision that made the checker the contract's enforcement - a budget the skill declares and the checker ignores is exactly the gap D0355 closed for the rest of the contract. The 450-word ceiling is NOT this sprint's to turn on: it is a process change and waits for the human's word on D0377 (D0337); the check reads that acceptance from the tree."; }
    // RAN: inspect: sprint 607 Refine text; estimatedPoints 2 and #CharteredBy d0355 present in the file; d0355 accepted (d0355AcceptR1, judgedBy wweatherholtz); dcBriefBudgetsAreHeld DoD re-read and amended before any result to name the synthetic fixtures
    part briefBudgetsAreHeldRefineGateR1 : TestResult { :>> id = "6b06578a-5dd2-40c8-8390-ac589e9a823d"; :>> outcome = VerdictKind::pass; :>> judgedAgainst = "d6d5556fbf24b6cd30a6669d40b1cd7eecbf6c70"; :>> judgedAt = "2026-09-08"; :>> judgedBy = "claudeOpus5"; }
    verification briefBudgetsAreHeldStandupGate : Test { :>> id = "1a56f944-ec96-42b4-86c7-7e56a156b99f"; :>> title = "Sprint 607 standup gate"; :>> createdAt = "2026-09-08"; :>> createdBy = "claudeOpus5"; :>> method = VerificationMethod::inspect; :>> procedureText = "ONE CHOICE: hold the three budgets whose section the markup can find (headline, ask, provenance) in the checker, and leave the rows the exec-summary suite already measures (why-now, rule, why-wins, change-mind) to it - a second measurer of the same field is a second truth. A second choice: the ceiling is gated on the decision file's status text rather than a flag, so the control turns on when the human's word lands and nothing else has to be edited. A third: the fixtures are synthetic and small, not the 1334-word published page - the DoD was amended before any result to say so, and the published page's refusal is recorded as the run's evidence instead."; }
    // RAN: inspect: sprint 607 Standup text; estimatedPoints 2 and #CharteredBy d0355 present in the file; d0355 accepted (d0355AcceptR1, judgedBy wweatherholtz); dcBriefBudgetsAreHeld DoD re-read and amended before any result to name the synthetic fixtures
    part briefBudgetsAreHeldStandupGateR1 : TestResult { :>> id = "df415756-340b-4616-ae6f-f6996d1e9c3c"; :>> outcome = VerdictKind::pass; :>> judgedAgainst = "d6d5556fbf24b6cd30a6669d40b1cd7eecbf6c70"; :>> judgedAt = "2026-09-08"; :>> judgedBy = "claudeOpus5"; }
    verification briefBudgetsAreHeldImplementGate : Test { :>> id = "9c16c8b3-87e1-41ba-958e-f6610e74e11c"; :>> title = "Sprint 607 implement gate"; :>> createdAt = "2026-09-08"; :>> createdBy = "claudeOpus5"; :>> method = VerificationMethod::test; :>> procedureText = "RAN: Edit tool on scripts/check_templates.py (BRIEF_BUDGETS, brief_page_ceiling, check_brief budget and ceiling clauses, _brief_fixture, self_test, --self-test dispatch); python scripts/check_templates.py --self-test (5 of 5 pass); python scripts/check_templates.py --brief on the published empty-queue page (3 violations, exit 1); scripts/exec_brief/build_2026_09_08_terse.py written and run over facts.json (tree d6d5556) - 447 reader words, headline 15, ask 47, provenance 42, --brief clean and clean under a forced 450 ceiling; page published to the standing artifact URL and .keel/decision-page.toml updated to ids d0376, d0377; build_2026_09_08_empty_queue.py deleted (its output fails the check it is superseded by); .engine/skills/asi-templates/SKILL.md section 2.1 and the deployed copy carry the enforcement note and the register; keel validate . (690 clean); keel guard --no-receipt ALL PASS."; }
    // RAN: inspect: sprint 607 Implement text; storyBriefBudgetsAreHeldDoDR1 pass recorded; check_templates --self-test 5 of 5; the terse page published to the standing URL and read as a rendered image (one label shortened after the read); dcDeclaredBudgetsNameTheirCheck added to the backlog for the retro finding; git status names check_templates.py, build_2026_09_08_terse.py, the deleted empty_queue builder, both asi-templates SKILL.md copies, backlog, issues, intake, decision 0377
    part briefBudgetsAreHeldImplementGateR1 : TestResult { :>> id = "3a77bc92-c015-4825-b4b7-446553de6b87"; :>> outcome = VerdictKind::pass; :>> judgedAgainst = "d6d5556fbf24b6cd30a6669d40b1cd7eecbf6c70"; :>> judgedAt = "2026-09-08"; :>> judgedBy = "claudeOpus5"; }
    verification briefBudgetsAreHeldReviewGate : Test { :>> id = "4faceea6-cb91-44c9-a918-a9ba0411a9fe"; :>> title = "Sprint 607 review gate — three passes per D0172"; :>> createdAt = "2026-09-08"; :>> createdBy = "claudeOpus5"; :>> method = VerificationMethod::inspect; :>> procedureText = "THREE QUESTIONS (D0172). Does the check now hold what the skill declares? For the three sections it can locate by markup, yes - a page over any of them exits 1 naming the count; the published page that had passed clean is the proof, refused at 26, 133 and 71. Can the ceiling be turned on without the human? No - brief_page_ceiling reads DecisionStatus::accepted from the 0377 decision file, and that status changes only through keel accept under D0337. What is NOT claimed: that the register itself is checked - caveman-lite is a writing rule in the skill, and no regex judges hedging; that the exec-summary suite's four remaining budgets are held here (they are its, not this check's); that the terse page is the right terseness - that is the human's judgment on D0377, and the page asks it."; }
    // RAN: inspect: sprint 607 Review text; storyBriefBudgetsAreHeldDoDR1 pass recorded; check_templates --self-test 5 of 5; the terse page published to the standing URL and read as a rendered image (one label shortened after the read); dcDeclaredBudgetsNameTheirCheck added to the backlog for the retro finding; git status names check_templates.py, build_2026_09_08_terse.py, the deleted empty_queue builder, both asi-templates SKILL.md copies, backlog, issues, intake, decision 0377
    part briefBudgetsAreHeldReviewGateR1 : TestResult { :>> id = "6e546ce1-a1d6-4e0b-bd15-157c1d8b75a6"; :>> outcome = VerdictKind::pass; :>> judgedAgainst = "d6d5556fbf24b6cd30a6669d40b1cd7eecbf6c70"; :>> judgedAt = "2026-09-08"; :>> judgedBy = "claudeOpus5"; }
    verification briefBudgetsAreHeldCloseOutGate : Test { :>> id = "5894d4b4-1f5e-4a25-816a-fe38acfa85eb"; :>> title = "Sprint 607 closeOut gate (autonomous, D0049)"; :>> createdAt = "2026-09-08"; :>> createdBy = "claudeOpus5"; :>> method = VerificationMethod::inspect; :>> procedureText = "CLOSED. The class of issue413 - a budget declared in a skill and held by nothing - is closed for the brief's headline, ask and provenance, and the page the human called too verbose is replaced by one at 447 words that the check accepts. D0376 and D0377 wait for their word on the published page."; }
    // RAN: inspect: sprint 607 CloseOut text; storyBriefBudgetsAreHeldDoDR1 pass recorded; check_templates --self-test 5 of 5; the terse page published to the standing URL and read as a rendered image (one label shortened after the read); dcDeclaredBudgetsNameTheirCheck added to the backlog for the retro finding; git status names check_templates.py, build_2026_09_08_terse.py, the deleted empty_queue builder, both asi-templates SKILL.md copies, backlog, issues, intake, decision 0377
    part briefBudgetsAreHeldCloseOutGateR1 : TestResult { :>> id = "c8ae2419-1ff5-4071-8211-dc17e0096b41"; :>> outcome = VerdictKind::pass; :>> judgedAgainst = "d6d5556fbf24b6cd30a6669d40b1cd7eecbf6c70"; :>> judgedAt = "2026-09-08"; :>> judgedBy = "claudeOpus5"; }
    verification briefBudgetsAreHeldRetroGate : Test { :>> id = "9cc73be3-2350-4d44-a447-aa48ac35869e"; :>> title = "Sprint 607 retro gate (autonomous, D0049)"; :>> createdAt = "2026-09-08"; :>> createdBy = "claudeOpus5"; :>> method = VerificationMethod::analyze; :>> procedureText = "AVOIDABLE-ISSUE SCAN HELD. One process finding: three pages went out under a contract whose budgets were prose, and the third drew the human's verdict before any check did - the same shape as issue397 the day before (a declared rule with no reader). The control that would have caught it earlier is a check-against-the-contract audit whenever a skill declares a number: every numeric budget in a skill's contract table names the check that holds it, or the table says none does. That is a recurring review, not a one-off, and it is recorded as a backlog item rather than a reminder (dcDeclaredBudgetsNameTheirCheck) so the frontier ranks it. A second, smaller: the recorder dropped a character during a footer edit and the page still built - check_brief does not parse the anchor; the human-facing check is the rendered page, read before publishing, which was done."; }
    // RAN: inspect: sprint 607 Retro text; storyBriefBudgetsAreHeldDoDR1 pass recorded; check_templates --self-test 5 of 5; the terse page published to the standing URL and read as a rendered image (one label shortened after the read); dcDeclaredBudgetsNameTheirCheck added to the backlog for the retro finding; git status names check_templates.py, build_2026_09_08_terse.py, the deleted empty_queue builder, both asi-templates SKILL.md copies, backlog, issues, intake, decision 0377
    part briefBudgetsAreHeldRetroGateR1 : TestResult { :>> id = "c4de5584-201b-42fc-acd2-963f4f051bd0"; :>> outcome = VerdictKind::pass; :>> judgedAgainst = "d6d5556fbf24b6cd30a6669d40b1cd7eecbf6c70"; :>> judgedAt = "2026-09-08"; :>> judgedBy = "claudeOpus5"; }
}
