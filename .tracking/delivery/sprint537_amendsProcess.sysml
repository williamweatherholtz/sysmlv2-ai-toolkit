// ProjectDeliveryS537 — Sprint 537: a Decision that names a process step reaches the definition, or the commit warns. EXECUTE. 2 pts.
package ProjectDeliveryS537 {
    private import EngineElement::*;
    private import EngineWork::*;
    private import EngineVerification::*;
    private import EngineRelationships::*;

    #CharteredBy dependency from amendsProcessStory to d0297;

    part amendsProcessStory : Story {
        :>> id = "0c66dbb7-fd5f-4009-8ce8-3a10481be743";
        :>> title = "Sprint 537: guard 59 decision-amends-process - identifier-anchored, warning-tier, with the shape that motivated it stated as a residual (2 pts)";
        :>> createdAt = "2026-09-04"; :>> createdBy = "claudeOpus5"; :>> kind = WorkKind::code; :>> priority = WorkPriority::p0; :>> owner = "claudeOpus5"; :>> estimatedPoints = 2;
    }

    action def DeliveryRunS537 {
        action storyAmendsProcess;
        verification storyAmendsProcessDoD : Test { :>> id = "95f0d3bf-4969-4297-b56e-9309c29868b0"; :>> method = VerificationMethod::test; :>> procedureText = "DELIVERED BACKLOG ITEMS: processAmendmentsReachTheDefinition (resolves issue298). PART A was already done: D0244 (71b789b, marked) carried D0243's amendment into knowledge-graph-memory.sysml as OPTIONAL comments on steps 1 and 2. PART B: guard decision-amends-process - staged Decisions whose prose names a Process, its file stem or a ProcessStep by whole identifier (camelCase or hyphenated only; a plain-word process name is prose) while that file is not staged -> one warning naming Decision, identifier, file and the two readings; legitimately empty between commits; anchored in the control map to ehz7 beside process-change. VERIFY: four unit tests incl. the armed residual (D0243's unnamed sentence is NOT caught) and the plain-word exclusion; a staged probe Decision naming kgInjection fired once and was removed; D0297 itself did not fire after the exclusion; 467 tests, clippy clean."; }
        // RAN: census over 296 Decisions (17 name a step identifier, 5 untouched files; 24 mention steps by number, 16 untouched, two thirds not amendments); cargo test --release 467/0 twice (one earlier run stopped at 397 with one failure I did not capture and could not reproduce); clippy 0; staged probe -> 1 warning naming kgInjection + knowledge-graph-memory.sysml; unstaged -> 0
        part storyAmendsProcessDoDR1 : TestResult { :>> id = "4a17ac00-2e23-4277-ac8e-e88da73e99a2"; :>> outcome = VerdictKind::pass; :>> judgedAgainst = "75941cc"; :>> judgedAt = "2026-09-04"; :>> judgedBy = "claudeOpus5"; }
    }

    verification amendsProcessRefineGate : Test { :>> id = "fcd54ad0-cbc7-4ce8-a2c6-a2d6a4e2099a"; :>> title = "Sprint 537 refine gate (DoR)"; :>> createdAt = "2026-09-04"; :>> createdBy = "claudeOpus5"; :>> method = VerificationMethod::inspect; :>> procedureText = "READY once the census was run: the DoD's own phrasing ('a Decision whose text amends a named process step') presumed the step is NAMED, and the motivating case does not name it. Measuring before designing turned a guess about the anchor into two numbers - identifiers 5 of 17, numbers 16 of 24 with most not amendments - and the tier and the residual followed from them."; }
    verification amendsProcessStandupGate : Test { :>> id = "7d0745fb-eb4c-4fc4-880f-bc94190bdb24"; :>> title = "Sprint 537 standup gate"; :>> createdAt = "2026-09-04"; :>> createdBy = "claudeOpus5"; :>> method = VerificationMethod::inspect; :>> procedureText = "ONE CHOICE: warning-tier, because a violation would have refused about half of the historical hits, which were citations, and D0176 taught what an over-strict gate trains its actor to do. Second: the residual is ARMED by a test that asserts the miss, so closing it later forces the documentation to change with it - a guard whose prose implies it catches the case that named it is the pass-at-zero hazard in words."; }
    verification amendsProcessImplementGate : Test { :>> id = "2b440dc8-a79e-477c-ab15-6d765d2c00bd"; :>> title = "Sprint 537 implement gate"; :>> createdAt = "2026-09-04"; :>> createdBy = "claudeOpus5"; :>> method = VerificationMethod::test; :>> procedureText = "RAN: the first commit carrying the guard warned on its own Decision - for the word `migration`, a process whose name and stem are one English word, in the phrase 'step 5 of the migration plan'. The exclusion (camelCase or hyphenated anchors only) came from that fire and has its own test. The scan-count test then demanded a LEGITIMATELY_EMPTY entry, correctly: the guard scans staged Decisions and is empty between commits."; }
    verification amendsProcessReviewGate : Test { :>> id = "424a1c58-9974-4c11-9b90-565b40cf0f5d"; :>> title = "Sprint 537 review gate — three passes per D0172"; :>> createdAt = "2026-09-04"; :>> createdBy = "claudeOpus5"; :>> method = VerificationMethod::inspect; :>> procedureText = "THREE PASSES. (1) WOULD IT HAVE CAUGHT D0243: no, and every surface says so - guard doc, guards.md row, D0297, and a test. It would have caught D0242, D0146 and D0092. (2) IS A WARNING A CONTROL: it is a detective control the commit author reads; the retro-backlog guard's history shows warnings ARE read when they name a file and an action, and this one does. (3) WHAT WOULD CLOSE THE RESIDUAL: an #Amends edge on Decisions - a schema fork D0297 declines to raise on one case."; }
    verification amendsProcessCloseOutGate : Test { :>> id = "2aaf7946-ebf2-4164-8d0d-3f943c145891"; :>> title = "Sprint 537 closeOut gate (autonomous, D0049)"; :>> createdAt = "2026-09-04"; :>> createdBy = "claudeOpus5"; :>> method = VerificationMethod::inspect; :>> procedureText = "CLOSED. issue298 resolves; guard count 59; guards.md and the control map carry the guard."; }
    verification amendsProcessRetroGate : Test { :>> id = "37569c18-62e8-4841-94a6-beea7bc416d1"; :>> title = "Sprint 537 retro gate (autonomous, D0049)"; :>> createdAt = "2026-09-04"; :>> createdBy = "claudeOpus5"; :>> method = VerificationMethod::analyze; :>> procedureText = "no new item - already tracked: the residual (the unnamed shape) is recorded in d0297 with its closing condition, and is not an item until the shape recurs. The unreproduced single test failure in one of three suite runs is noted in the RAN receipt; without a name it cannot be an Issue, and a flake seen once is a fact to watch, not a finding - if it returns, the run output is captured first and the Issue names the test."; }
}
