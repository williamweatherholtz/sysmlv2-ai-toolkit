// ProjectDeliveryS431 — Sprint 431: review sampling (D0200 OPTION A, all five clauses): honest split counts, judgeable delta cards, N+M sampling, the override-rate alarm, and escalation with teeth. EXECUTE. 3 pts.
package ProjectDeliveryS431 {
    private import EngineElement::*;
    private import EngineWork::*;
    private import EngineVerification::*;
    private import EngineRelationships::*;

    #CharteredBy dependency from reviewSamplingStory to d0200;

    part reviewSamplingStory : Story {
        :>> id = "f29dd261-cb8d-4076-a8b7-5afc522caf81";
        :>> title = "Sprint 431: the human gate becomes a gate (3 pts)";
        :>> createdAt = "2026-08-23"; :>> createdBy = "claudeFable5"; :>> kind = WorkKind::code; :>> priority = WorkPriority::p0; :>> owner = "claudeFable5"; :>> estimatedPoints = 3;
    }

    action def DeliveryRunS431 {
        action storyReviewSampling;
        verification storyReviewSamplingDoD : Test { :>> id = "eb92ac1a-f4bf-41b3-ba81-31d2072874d2"; :>> method = VerificationMethod::test; :>> procedureText = "DELIVERED: dcOversightRedesign (resolves issue228; delivers D0200 OPTION A, their deck-tap choice, the process-value panel's most convergent human-side recommendation). ALL FIVE CLAUSES: (1) SPLIT COUNTS - sitting-coverage reports readReviewed and batchAcknowledgedOnly as two numbers, never one (read back live: covered 107 = 43 read + 64 batch-only - the panel's 62-percent finding is now a permanent computed fact, with the classification basis stated: the machine token forward, the word batch for pre-D0200 history rather than laundering it into read). (2) JUDGEABLE DELTA CARDS - every sitting card renders the sprint's own DELIVERED text plus its pass/fail result census in a collapsible panel (open by default on deep-review cards): raw evidence, not narrative, per the deference research the panel cited. (3) N+M SAMPLING - per deck, 2 randomly-sampled (HEAD-seeded, so a reopened deck deals the same hand) + 1 risk-flagged (the sprint leaning hardest on guard/decision/schema surfaces) sittings are marked DEEP REVIEW; the rest offer an explicit Batch-acknowledge button recording the DISTINCT batch verdict (machine token, outcome pass, never counted as a read) with review-anyway still available. (4) OVERRIDE-RATE ALARM - sittingOverrideRateIndicator (computed, goal observe): fail-verdict share of READ reviews; live value 0.00 percent AT DECLARATION - the alarm state the HITL literature names, now on the dashboard instead of in a panel report. (5) ESCALATION WITH TEETH - the process-change guard refuses process-def commits while the DUE sitting queue's oldest item exceeds 14 days: the human's absence now changes system behavior (meaningful-human-control); delivery work and the review-recording writes that SHRINK the debt land freely, so no deadlock; fresh due sittings never block. VERIFIED: split counts and indicator read back live; deck greps show 1 risk-flagged + 2 random deep cards, 7 batch-ackable, delta panels with real censuses; full workspace suite 10/10 green; clippy pedantic+nursery clean after index-free sampling rewrite."; }
        part storyReviewSamplingDoDR1 : TestResult { :>> id = "1067ab22-a733-4a22-8642-b725f5e210b6"; :>> outcome = VerdictKind::pass; :>> judgedAgainst = "aa548b4231eb141f84ac0d89afeff885f2b933bb"; :>> judgedAt = "2026-08-23"; :>> judgedBy = "claudeFable5"; }
    }

    verification reviewSamplingRefineGate : Test { :>> id = "0d766582-198e-4add-bf12-ce38026a10ea"; :>> title = "Sprint 431 refine gate (DoR)"; :>> createdAt = "2026-08-23"; :>> createdBy = "claudeFable5"; :>> method = VerificationMethod::inspect; :>> procedureText = "DoR. Chartered by their D0200 OPTION A tap. All five clauses in scope; recommended parameters N=2, M=1 adopted as drafted. Out of scope (stated): retro-editing historical batch reviews - they are CLASSIFIED honestly, never rewritten. 3 points."; }
    part reviewSamplingRefineGateR1 : TestResult { :>> id = "75c3f245-0cbd-4b69-81d9-bd12fcb82b49"; :>> outcome = VerdictKind::pass; :>> judgedAgainst = "aa548b4231eb141f84ac0d89afeff885f2b933bb"; :>> judgedAt = "2026-08-23"; :>> judgedBy = "claudeFable5"; }
    verification reviewSamplingStandupGate : Test { :>> id = "22862377-4588-4288-a91d-5498f08ee9fd"; :>> title = "Sprint 431 standup gate"; :>> createdAt = "2026-08-23"; :>> createdBy = "claudeFable5"; :>> method = VerificationMethod::inspect; :>> procedureText = "Approach: the batch verdict is a machine token in the record's own text (the ceremony-guard convention family) because Test is frozen core and a schema field would need a CR for what a stated convention provides; sampling is seeded from HEAD so the ask is stable per tree; the throttle lives in the EXISTING process-change guard rather than a new one - the CHANGE route is already the gate the debt should hold. No blockers."; }
    part reviewSamplingStandupGateR1 : TestResult { :>> id = "7883d277-10c9-4fb7-8b43-a5373cd5a48c"; :>> outcome = VerdictKind::pass; :>> judgedAgainst = "aa548b4231eb141f84ac0d89afeff885f2b933bb"; :>> judgedAt = "2026-08-23"; :>> judgedBy = "claudeFable5"; }
    verification reviewSamplingImplementGate : Test { :>> id = "510f69d0-31aa-420c-b780-6647312d80fa"; :>> title = "Sprint 431 implement gate"; :>> createdAt = "2026-08-23"; :>> createdBy = "claudeFable5"; :>> method = VerificationMethod::test; :>> procedureText = "Verified by running: keel sitting-coverage - covered 107, readReviewed 43, batchAcknowledgedOnly 64, splitBasis stated; keel indicators - sittingOverrideRateIndicator live 0.00; regenerated deck - DEEP REVIEW x3 (1 risk-flagged, 2 random), Batch-acknowledge on the 7 sampled-out cards, delta panels rendering per-sprint pass/fail censuses; cargo test 10/10 result-ok; clippy clean; validate + all 47 guards green (the throttle arm is live but dormant - no due sitting is near 14 days)."; }
    part reviewSamplingImplementGateR1 : TestResult { :>> id = "256d4af3-8fb8-4eb3-b916-85746205b59a"; :>> outcome = VerdictKind::pass; :>> judgedAgainst = "aa548b4231eb141f84ac0d89afeff885f2b933bb"; :>> judgedAt = "2026-08-23"; :>> judgedBy = "claudeFable5"; }
    verification reviewSamplingReviewGate : Test { :>> id = "29379fe9-02bd-45df-b2b3-7211edf2af03"; :>> title = "Sprint 431 review gate — three passes per D0172"; :>> createdAt = "2026-08-23"; :>> createdBy = "claudeFable5"; :>> method = VerificationMethod::inspect; :>> procedureText = "PASS 1, CLAIMS: every number is a live read-back quoted in the story. PASS 2, BOUNDARY: the throttle was NOT negative-probed live (forcing it would need a 14-day-old due sitting planted into git history, which the impossible-evidence-date and claim-ancestry guards rightly make hard) - its arm is code-reviewed and its inputs (oversight_debt) are the same computation authority-queue displays; recorded as the residual for the control-evaluation sprint's scratch-repo pattern. PASS 3, OWN DIFF: the first sampling implementation indexed slices and clippy refused it wholesale - rewritten uid-keyed, which also made the risk/random labels unambiguous. WHAT A REVIEWER SHOULD ATTACK: the batch-classification heuristic for HISTORY ('batch' in the review text) could misclassify a hypothetical read review that used the word - the 64/43 split matches the known two-batch record exactly, and the basis is printed on the view so a challenge has its target."; }
    part reviewSamplingReviewGateR1 : TestResult { :>> id = "93ae9f6a-d91b-41f1-b115-677116e55a0b"; :>> outcome = VerdictKind::pass; :>> judgedAgainst = "aa548b4231eb141f84ac0d89afeff885f2b933bb"; :>> judgedAt = "2026-08-23"; :>> judgedBy = "claudeFable5"; }
    verification reviewSamplingCloseOutGate : Test { :>> id = "2a01ffd9-0144-4c97-adcb-578ed5ba6b0b"; :>> title = "Sprint 431 closeOut gate (autonomous, D0049)"; :>> createdAt = "2026-08-23"; :>> createdBy = "claudeFable5"; :>> method = VerificationMethod::inspect; :>> procedureText = "Autonomous closeOut (D0049). issue228 resolves - ALL FIVE panel issues (227-231) are now closed, plus both panel direction decisions applied (D0200 here, D0198 in sprint 430); the frontier holds dcAdvisoryInstrumentation, dcControlEvaluation (needs their per-run approval), dcHeterogeneousCritics (needs their second model); validate + guards green."; }
    part reviewSamplingCloseOutGateR1 : TestResult { :>> id = "7fa7d701-c18b-4bde-93e4-f8491dcbd422"; :>> outcome = VerdictKind::pass; :>> judgedAgainst = "aa548b4231eb141f84ac0d89afeff885f2b933bb"; :>> judgedAt = "2026-08-23"; :>> judgedBy = "claudeFable5"; }
    verification reviewSamplingRetroGate : Test { :>> id = "2de056df-596d-433a-aebf-e46deb1272ad"; :>> title = "Sprint 431 retro gate (autonomous, D0049)"; :>> createdAt = "2026-08-23"; :>> createdBy = "claudeFable5"; :>> method = VerificationMethod::analyze; :>> procedureText = "Autonomous retro (D0049). AVOIDABLE-ISSUE SCAN under rcRecurrence: none new - this sprint spends the panel's findings rather than generating them; the one deliberate debt (throttle un-probed live) is stated in the review gate with its closure path. WELL: the never-one-number discipline now covers the oversight loop itself, and the human's next deck opens with three cards asking for real judgment and seven honest acknowledgments - the exact shape the human-factors lens prescribed. Estimate 3 pts, delivered 3."; }
    part reviewSamplingRetroGateR1 : TestResult { :>> id = "4e25a687-17e3-4453-8e14-a36b83d4f895"; :>> outcome = VerdictKind::pass; :>> judgedAgainst = "aa548b4231eb141f84ac0d89afeff885f2b933bb"; :>> judgedAt = "2026-08-23"; :>> judgedBy = "claudeFable5"; }
}
