// ProjectDeliveryS256 — Sprint 256: declare the marker vocabulary + reject undeclared markers
// (issue077, D0133). Frozen-schema change under §2.5 sign-off. EXECUTE. 2 pts.
package ProjectDeliveryS256 {
    private import EngineElement::*;
    private import EngineWork::*;
    private import EngineVerification::*;
    private import EngineRelationships::*;

    #CharteredBy dependency from declaredMarkersStory to d0133;

    part declaredMarkersStory : Story {
        :>> id = "0d700001-0813-5001-9b3e-000000200001";
        :>> title = "Sprint 256: declare the 9 undeclared markers + marker-vocabulary hard guard (2 pts)";
        :>> createdAt = "2026-08-13"; :>> createdBy = "claudeOpus5"; :>> kind = WorkKind::code; :>> priority = WorkPriority::p0; :>> owner = "claudeOpus5"; :>> estimatedPoints = 2;
    }

    action def DeliveryRunS256 {
        action storyDeclaredMarkers;
        verification storyDeclaredMarkersDoD : Test { :>> id = "0d700002-0813-5002-9b3e-000000200002"; :>> method = VerificationMethod::test; :>> procedureText = "Delivers dcDeclaredMarkers (issue077/D0133). DEFECT: guards key on metadata markers that were never declared or type-checked. Complete scan of markers in REAL syntactic positions: #Verify 456, #CharteredBy 260, #Resolves 93, #DependsOn 44, #DerivedFrom 37, #ProspectiveChange 30, #Dispositions 21, #ProcessDefect 18, #Measures 12, #Supersede 11, #Informs 11, #JustifiedBy 8, #Capability 7, #View 5, #Covers 4 — against a declared set of only eight. NINE undeclared, including the two most load-bearing (#Verify, which tier-satisfaction/sr_verified_pct/verification-trace all key on; #DerivedFrom, which the HARD requirement-rootedness guard keys on). BUILT: (A) the nine declared in .engine/schema/core/relationships.sysml, each commented with what it links and which control consumes it; (B) new HARD guard `marker-vocabulary` (23 guards; 18 hard + 5 warning), with the declared set read from the SCHEMA rather than hardcoded so a downstream project is checked against its own vocabulary; (C) string literals stripped before scanning, because procedureText fields legitimately discuss markers (#Marker/#Kind/#Changes dependency) and without stripping those three prose examples alone fire nine false violations on a hard gate. HARD rather than warning-first because the check is exact set-membership, not a heuristic — the D0102 pattern exists for heuristics, and a warning would leave the silent-blinding window open, which is the whole harm. VERIFY (measured): with the nine declared, 989 markers scanned, 0 violations. NEGATIVE TEST — replacing one #DerivedFrom with the real-world typo #DerivdFrom produced a violation naming file, line and marker, exit 1; and in the same state `keel validate` still reported '277 tracking file(s) validated clean', proving the pre-change world accepted it silently while requirement-rootedness lost the edge. clippy clean; 156 tests incl. prose-ignored and misspelling-not-declared cases; validate + all 23 guards + check-engine green at 56d7e21."; }
        part storyDeclaredMarkersDoDR1 : TestResult { :>> id = "0d700003-0813-5003-9b3e-000000200003"; :>> outcome = VerdictKind::pass; :>> judgedAgainst = "56d7e21"; :>> judgedAt = "2026-08-13"; :>> judgedBy = "claudeOpus5"; }
    }

    verification dmRefineGate : Test { :>> id = "0d700004-0813-5004-9b3e-000000200004"; :>> title = "Sprint 256 refine gate (DoR)"; :>> createdAt = "2026-08-13"; :>> createdBy = "claudeOpus5"; :>> method = VerificationMethod::inspect; :>> procedureText = "DoR: unblocked by the human's §2.5 frozen-schema sign-off (declaredMarkersSchemaSignOff), which had held this at frontier #1 for two sprints — the correct behaviour per D0052 (surface a sign-off-blocked top item, proceed with the next needing none). Scope: declare + enforce. EXCLUDED with reason: moving marker validation into the parser/registry — a cleaner eventual home, but parser+registry changes for a check a text scan performs exactly today, and against D0112's direction of moving checks OUT of heavyweight layers; recorded as open in D0133. estimatedPoints=2. DoR met."; }
    part dmRefineGateR1 : TestResult { :>> id = "0d700005-0813-5005-9b3e-000000200005"; :>> outcome = VerdictKind::pass; :>> judgedAgainst = "56d7e21"; :>> judgedAt = "2026-08-13"; :>> judgedBy = "claudeOpus5"; }

    verification dmStandupGate : Test { :>> id = "0d700006-0813-5006-9b3e-000000200006"; :>> title = "Sprint 256 standup gate"; :>> createdAt = "2026-08-13"; :>> createdBy = "claudeOpus5"; :>> method = VerificationMethod::inspect; :>> procedureText = "Approach: enumerate the COMPLETE marker set from the corpus before declaring anything, having twice this sitting under-scoped a finding by reasoning from the instances I happened to notice — issue077 as originally filed listed five markers and missed #Verify, the most-used of all. The scan found nine, plus three prose-only false candidates that dictated the string-stripping design. No blockers."; }
    part dmStandupGateR1 : TestResult { :>> id = "0d700007-0813-5007-9b3e-000000200007"; :>> outcome = VerdictKind::pass; :>> judgedAgainst = "56d7e21"; :>> judgedAt = "2026-08-13"; :>> judgedBy = "claudeOpus5"; }

    verification dmImplementGate : Test { :>> id = "0d700008-0813-5008-9b3e-000000200008"; :>> title = "Sprint 256 implement gate"; :>> createdAt = "2026-08-13"; :>> createdBy = "claudeOpus5"; :>> method = VerificationMethod::test; :>> procedureText = "Implemented at 56d7e21. The negative test used the EXACT real-world typo (#DerivdFrom) rather than an invented one, and was run in a state where `keel validate` simultaneously reported all files clean — so the test demonstrates the silent-blinding directly rather than describing it. Also de-brittled the CLAUDE.md guard prose: the ordinal chain ('A SEVENTEENTH guard...') required renumbering on every guard addition and had already gone stale twice this sitting."; }
    part dmImplementGateR1 : TestResult { :>> id = "0d700009-0813-5009-9b3e-000000200009"; :>> outcome = VerdictKind::pass; :>> judgedAgainst = "56d7e21"; :>> judgedAt = "2026-08-13"; :>> judgedBy = "claudeOpus5"; }

    verification dmReviewGate : Test { :>> id = "0d70000a-0813-500a-9b3e-00000020000a"; :>> title = "Sprint 256 review gate"; :>> createdAt = "2026-08-13"; :>> createdBy = "claudeOpus5"; :>> method = VerificationMethod::inspect; :>> procedureText = "Reviewed. Markers were the one naming axis in the engine with NO referential integrity — an unresolved type reference fails loudly (check-engine), an unregistered actor fails loudly (actors guard), and a wrong marker failed silently while taking a control with it. That it was the axis the guards themselves depend on is the reason this ranked High. Correct judgement calls: HARD rather than warning-first, because exactness removes the noise argument; and reading the declared set from the schema rather than hardcoding it, so the control is portable to a downstream with its own vocabulary (D0129/nProcessPortability). Weakness accepted: the scan is text-based, so a marker written in an unusual syntactic position could be missed — acceptable because the enforced positions are the ones the parser itself recognises, and moving the check into the parser is recorded as open."; }
    part dmReviewGateR1 : TestResult { :>> id = "0d70000b-0813-500b-9b3e-00000020000b"; :>> outcome = VerdictKind::pass; :>> judgedAgainst = "56d7e21"; :>> judgedAt = "2026-08-13"; :>> judgedBy = "claudeOpus5"; }

    verification dmCloseOutGate : Test { :>> id = "0d70000c-0813-500c-9b3e-00000020000c"; :>> title = "Sprint 256 closeOut gate (autonomous, D0049)"; :>> createdAt = "2026-08-13"; :>> createdBy = "claudeOpus5"; :>> method = VerificationMethod::inspect; :>> procedureText = "Autonomous closeOut (D0049). dcDeclaredMarkers carries a passing DoD TestResult at 56d7e21; issue077 RESOLVES. validate + all 23 guards + check-engine green; 156 tests; clippy clean. D0133 is ACCEPTED (the §2.5 sign-off covered it). Frontier advances to keelInLoopGates — the Tier-1/Tier-2 escalation and the D0128 measurement, now the top item needing no sign-off."; }
    part dmCloseOutGateR1 : TestResult { :>> id = "0d70000d-0813-500d-9b3e-00000020000d"; :>> outcome = VerdictKind::pass; :>> judgedAgainst = "56d7e21"; :>> judgedAt = "2026-08-13"; :>> judgedBy = "claudeOpus5"; }

    verification dmRetroGate : Test { :>> id = "0d70000e-0813-500e-9b3e-00000020000e"; :>> title = "Sprint 256 retro gate (autonomous, D0049)"; :>> createdAt = "2026-08-13"; :>> createdBy = "claudeOpus5"; :>> method = VerificationMethod::analyze; :>> procedureText = "Autonomous retro (D0049) under D0131's retroTrack step. WELL: (1) the complete-corpus scan came FIRST and immediately corrected my own issue077, which had listed five markers and missed the most-used one — the third sprint running where measuring before designing changed the design, and the pattern is now reliable enough to treat as method rather than luck; (2) the prose-vs-syntax distinction was found by that same scan (three false candidates) rather than discovered as false positives after shipping a hard gate; (3) the negative test used the real typo in a state where validate simultaneously reported clean, demonstrating the harm instead of asserting it. AVOIDABLE-ISSUE 1: the CLAUDE.md guard prose used hardcoded ordinals ('A SEVENTEENTH guard...') which I had already had to renumber twice this sitting and which had gone stale both times — brittle documentation that guarantees drift. FIXED at the root by replacing the ordinal chain with stable phrasing; NO NEW ITEM because the fix removes the class rather than patching an instance, and the doc-sync guard already covers the general obligation. Estimate 2 pts, delivered."; }
    part dmRetroGateR1 : TestResult { :>> id = "0d70000f-0813-500f-9b3e-00000020000f"; :>> outcome = VerdictKind::pass; :>> judgedAgainst = "56d7e21"; :>> judgedAt = "2026-08-13"; :>> judgedBy = "claudeOpus5"; }
}
