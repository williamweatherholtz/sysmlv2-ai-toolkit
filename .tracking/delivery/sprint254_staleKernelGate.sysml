// ProjectDeliveryS254 — Sprint 254: retire the kernel per-file instance validator from the blocking
// commit path (issue081, D0132). Removing a gate INCREASED total enforcement. EXECUTE. 2 pts.
package ProjectDeliveryS254 {
    private import EngineElement::*;
    private import EngineWork::*;
    private import EngineVerification::*;
    private import EngineRelationships::*;

    #CharteredBy dependency from staleKernelGateStory to d0132;

    part staleKernelGateStory : Story {
        :>> id = "0d6d0001-0813-4d01-9b3e-0000001d0001";
        :>> title = "Sprint 254: kernel instance validator becomes opt-in; check-engine is the enforced gate (2 pts)";
        :>> createdAt = "2026-08-13"; :>> createdBy = "claudeOpus5"; :>> kind = WorkKind::code; :>> priority = WorkPriority::p0; :>> owner = "claudeOpus5"; :>> estimatedPoints = 2;
    }

    action def DeliveryRunS254 {
        action storyStaleKernelGate;
        verification storyStaleKernelGateDoD : Test { :>> id = "0d6d0002-0813-4d02-9b3e-0000001d0002"; :>> method = VerificationMethod::demo; :>> procedureText = "Delivers dcStaleKernelInstanceGate (issue081/D0132). DEFECT: validate_instances.py validates each .engine instance file IN ISOLATION, so cross-file references cannot resolve, and it FAILS 11 already-committed CORRECT decisions (0114, 0116-0125). Measured consequence: SKIP_VALIDATE=1 was used on EVERY .engine commit this sitting (8 times, sprints 247-253), and SKIP_VALIDATE=1 skips EVERY layer — so each bypass removed validate, all guards, check-engine and clippy for that commit. The gate was therefore worse than absent. CHANGE: validate_instances.py is OPT-IN behind KEEL_KERNEL_VALIDATE=1; `keel check-engine` (kernel-free, resolves references ACROSS files) is the enforced instance gate. Scope deliberately minimal — validate_schema.py and validate_workflows.py stay BLOCKING, being unproven-broken and rarely fired. VERIFY (both measured, neither assumed): NEGATIVE TEST — injecting `part d0131 : ThisTypeIsNotDeclaredAnywhere` made check-engine emit `ERROR: ...:11 — unresolved type reference` and exit 1; restoring the file gave exit 0, so the replacement gate genuinely blocks. REAL CRITERION — a commit staging .engine/decisions + .githooks + CLAUDE.md ran the hook to exit 0 with NO SKIP_VALIDATE, no JVM, and all 22 guards + check-engine executing; the sprint-254 commit itself (d6f9da5) then landed without a bypass, the first .engine commit this sitting to do so. clippy + cargo test + keel validate + guard green."; }
        part storyStaleKernelGateDoDR1 : TestResult { :>> id = "0d6d0003-0813-4d03-9b3e-0000001d0003"; :>> outcome = VerdictKind::pass; :>> judgedAgainst = "d6f9da5"; :>> judgedAt = "2026-08-13"; :>> judgedBy = "claudeOpus5"; }
    }

    verification skRefineGate : Test { :>> id = "0d6d0004-0813-4d04-9b3e-0000001d0004"; :>> title = "Sprint 254 refine gate (DoR)"; :>> createdAt = "2026-08-13"; :>> createdBy = "claudeOpus5"; :>> method = VerificationMethod::inspect; :>> procedureText = "DoR: taken by ORDER from the ranked frontier (D0052); issue081 is High and had recurred eight times in seven sprints, which is what the recurrence count is FOR. This changes what gates a commit, so it is a CHANGE (§3a) and D0132 is in scope by necessity. EXCLUDED with reason: making SKIP_VALIDATE layer-selective (a real improvement, but it treats the symptom and is a larger change to the escape hatch — recorded as a D0132 follow-on rather than bundled), and fixing validate_instances.py itself via two-pass registration (against the accepted D0112 JVM-retirement direction; option left open). estimatedPoints=2. DoR met."; }
    part skRefineGateR1 : TestResult { :>> id = "0d6d0005-0813-4d05-9b3e-0000001d0005"; :>> outcome = VerdictKind::pass; :>> judgedAgainst = "d6f9da5"; :>> judgedAt = "2026-08-13"; :>> judgedBy = "claudeOpus5"; }

    verification skStandupGate : Test { :>> id = "0d6d0006-0813-4d06-9b3e-0000001d0006"; :>> title = "Sprint 254 standup gate"; :>> createdAt = "2026-08-13"; :>> createdBy = "claudeOpus5"; :>> method = VerificationMethod::inspect; :>> procedureText = "Approach: PROVE the replacement gate before demoting the incumbent — inject a genuine unresolved reference and confirm check-engine both reports it and exits non-zero, because demoting a gate on the assumption that another one covers it is exactly how silent holes appear. Then prove the real criterion by running the hook on a staged .engine commit with no bypass. Keep the change minimal so the deep kernel oracle is not lost where it still works. No blockers."; }
    part skStandupGateR1 : TestResult { :>> id = "0d6d0007-0813-4d07-9b3e-0000001d0007"; :>> outcome = VerdictKind::pass; :>> judgedAgainst = "d6f9da5"; :>> judgedAt = "2026-08-13"; :>> judgedBy = "claudeOpus5"; }

    verification skImplementGate : Test { :>> id = "0d6d0008-0813-4d08-9b3e-0000001d0008"; :>> title = "Sprint 254 implement gate"; :>> createdAt = "2026-08-13"; :>> createdBy = "claudeOpus5"; :>> method = VerificationMethod::demo; :>> procedureText = "Implemented at d6f9da5. The commit is its own evidence: it staged .engine/decisions/0132 + .githooks/pre-commit + CLAUDE.md and landed with NO SKIP_VALIDATE, running the full Rust gate — the first .engine commit this sitting to do so. Eight consecutive prior .engine commits had required the bypass."; }
    part skImplementGateR1 : TestResult { :>> id = "0d6d0009-0813-4d09-9b3e-0000001d0009"; :>> outcome = VerdictKind::pass; :>> judgedAgainst = "d6f9da5"; :>> judgedAt = "2026-08-13"; :>> judgedBy = "claudeOpus5"; }

    verification skReviewGate : Test { :>> id = "0d6d000a-0813-4d0a-9b3e-0000001d000a"; :>> title = "Sprint 254 review gate"; :>> createdAt = "2026-08-13"; :>> createdBy = "claudeOpus5"; :>> method = VerificationMethod::inspect; :>> procedureText = "Reviewed. The result is counter-intuitive and worth stating plainly: REMOVING a gate increased total enforcement, because the only available bypass was all-or-nothing, so a gate that was routed around 100% of the time was also disabling four working layers each time. The generalisable lesson is that a gate's value is not what it checks but what it checks MINUS what its bypass destroys — and that a bypass counter is a first-class signal, not a nuisance. Correct restraint here: the fix was scoped to the one proven-broken validator rather than sweeping the kernel out of the hook entirely, and the tempting adjacent fix (layer-selective SKIP_VALIDATE) was recorded as a follow-on instead of smuggled in."; }
    part skReviewGateR1 : TestResult { :>> id = "0d6d000b-0813-4d0b-9b3e-0000001d000b"; :>> outcome = VerdictKind::pass; :>> judgedAgainst = "d6f9da5"; :>> judgedAt = "2026-08-13"; :>> judgedBy = "claudeOpus5"; }

    verification skCloseOutGate : Test { :>> id = "0d6d000c-0813-4d0c-9b3e-0000001d000c"; :>> title = "Sprint 254 closeOut gate (autonomous, D0049)"; :>> createdAt = "2026-08-13"; :>> createdBy = "claudeOpus5"; :>> method = VerificationMethod::inspect; :>> procedureText = "Autonomous closeOut (D0049). dcStaleKernelInstanceGate carries a passing DoD TestResult at d6f9da5; issue081 RESOLVES (open issues drop from 8 to 7). validate + all 22 guards + check-engine green; the hook runs bypass-free on .engine commits. D0132 is PROPOSED and joins D0131 awaiting the human. Frontier advances to dcDeclaredMarkers — which requires FROZEN-SCHEMA sign-off (§2.5) and therefore cannot be executed autonomously; per D0052 it is surfaced for the human while work proceeds with the next item needing none."; }
    part skCloseOutGateR1 : TestResult { :>> id = "0d6d000d-0813-4d0d-9b3e-0000001d000d"; :>> outcome = VerdictKind::pass; :>> judgedAgainst = "d6f9da5"; :>> judgedAt = "2026-08-13"; :>> judgedBy = "claudeOpus5"; }

    verification skRetroGate : Test { :>> id = "0d6d000e-0813-4d0e-9b3e-0000001d000e"; :>> title = "Sprint 254 retro gate (autonomous, D0049)"; :>> createdAt = "2026-08-13"; :>> createdBy = "claudeOpus5"; :>> method = VerificationMethod::analyze; :>> procedureText = "Autonomous retro (D0049) under D0131's retroTrack step. WELL: (1) the replacement gate was PROVEN by negative test before the incumbent was demoted — the one step that separates a considered demotion from a silent hole; (2) the bypass COUNT (8 in 7 sprints) did the arguing: a recurrence tally turned a nuisance into a High-severity, ranked, fixed item, which is precisely what recording recurrences is for; (3) scope held — one validator moved, the adjacent SKIP_VALIDATE improvement recorded rather than bundled. AVOIDABLE-ISSUE 1: my doc-sync edit silently did nothing (the replacement string did not match the file) and I only caught it because I grepped for the result afterwards. Had I trusted the 'changed/NO CHANGE' report of my own script, CLAUDE.md would have shipped stale while the commit message claimed it was synced. NO NEW ITEM — this is the same read-back-the-computed-answer principle already carried by dcVerificationTrace and now by the accepted response contract; recorded here as its SECOND observed occurrence (the first was the sprint-248 transform's false control total), so a third makes a pattern worth its own control. OBSERVATION (no item): the doc-sync GUARD passed on that commit because CLAUDE.md was staged — it checks that a doc file changed, not that the change was correct. That is an inherent limit of the heuristic and is already stated in D0113; noting it so the limit is not mistaken for coverage. Estimate 2 pts, delivered."; }
    part skRetroGateR1 : TestResult { :>> id = "0d6d000f-0813-4d0f-9b3e-0000001d000f"; :>> outcome = VerdictKind::pass; :>> judgedAgainst = "d6f9da5"; :>> judgedAt = "2026-08-13"; :>> judgedBy = "claudeOpus5"; }
}
