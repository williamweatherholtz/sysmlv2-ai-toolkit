// ProjectDeliveryS496 — Sprint 496: measure the finished-vs-open confusion, then ratchet the one real instance shut. EXECUTE. 2 pts.
package ProjectDeliveryS496 {
    private import EngineElement::*;
    private import EngineWork::*;
    private import EngineVerification::*;
    private import EngineRelationships::*;

    #CharteredBy dependency from sprintClosureStory to d0260;

    part sprintClosureStory : Story {
        :>> id = "93075090-3839-4680-9a3f-843cfed9389d";
        :>> title = "Sprint 496: guard 55 sprint-closure, and the correction of my own mis-report (2 pts)";
        :>> createdAt = "2026-08-30"; :>> createdBy = "claudeOpus5"; :>> kind = WorkKind::code; :>> priority = WorkPriority::p0; :>> owner = "claudeOpus5"; :>> estimatedPoints = 2;
    }

    action def DeliveryRunS496 {
        action storySprintClosure;
        verification storySprintClosureDoD : Test { :>> id = "ccfc4836-1a73-4ff2-bfa0-3c87a5f9cd5b"; :>> method = VerificationMethod::test; :>> procedureText = "DELIVERED: guard 55 sprint-closure (D0260) - for every delivery file except the highest-numbered, each task in its action def carries a TestResult; the newest sprint is exempt as in-progress. Armed by sprint_closure_actually_bites.rs (refuse case reproduces sprint483; allow case pins the in-progress exemption; a third proves stamping CLEARS it; a fourth asserts the live tree scans >400 clean so a mis-scoped guard cannot pass by seeing nothing). PLUS the correction: sprint 495's retro claimed the Critical was 'the same shape' as sprint 483 and it was not - the frontier was RIGHT to hold it open - corrected in place. VERIFY: guard 55 PASS 495 scanned 0 violations; 4/4 probes; clippy -D warnings clean; workspace suite 0 FAILED; keel version reports 55 guards.: DELIVERED BACKLOG ITEMS: <items>. <what done means, verified how>."; }
        // RAN: // RAN: keel guard sprint-closure PASS 495 scanned 0 violations; sprint_closure_actually_bites 4/4 (refuse, allow, clears, live-tree-non-vacuous); clippy -D warnings clean; workspace suite 0 FAILED; keel version 55 guards
        part storySprintClosureDoDR1 : TestResult { :>> id = "4ff183d1-6d0d-4466-97d4-32ff16064d0a"; :>> outcome = VerdictKind::pass; :>> judgedAgainst = "aea7dcc"; :>> judgedAt = "2026-08-30"; :>> judgedBy = "claudeOpus5"; }
    }

    verification sprintClosureRefineGate : Test { :>> id = "2a1edb0b-c1b2-49ff-9b3b-d4a2c70f6d69"; :>> title = "Sprint 496 refine gate (DoR)"; :>> createdAt = "2026-08-30"; :>> createdBy = "claudeOpus5"; :>> method = VerificationMethod::inspect; :>> procedureText = "READY: the human's question named two candidate causes and both were MEASURED before any control was designed - 496 sprint files scanned, the dropped gate's actual subject read from its removal, and the Critical's timeline read from git. A control designed before that measurement would have been fitted to my impression rather than the defect."; }
    verification sprintClosureStandupGate : Test { :>> id = "919f422a-ea3c-4c0a-86c3-aeddf22caa2d"; :>> title = "Sprint 496 standup gate"; :>> createdAt = "2026-08-30"; :>> createdBy = "claudeOpus5"; :>> method = VerificationMethod::inspect; :>> procedureText = "No blocker. One design tension resolved explicitly: the naive form of this guard blocks every commit during an open sprint, which is issue272 exactly - preventing an illegitimate state by forbidding a legitimate one. The exemption (highest sprint number) makes it objective rather than a judgment call, and the refuse/allow probe pair pins both sides so a later edit cannot quietly widen or narrow it."; }
    verification sprintClosureImplementGate : Test { :>> id = "2dccba9a-c1f4-4ad3-bf91-6ae29c74e571"; :>> title = "Sprint 496 implement gate"; :>> createdAt = "2026-08-30"; :>> createdBy = "claudeOpus5"; :>> method = VerificationMethod::test; :>> procedureText = "RAN: keel guard sprint-closure -> PASS, 495 scanned, 0 violations (the ratchet starts clean, as a ratchet must). cargo test --test sprint_closure_actually_bites -> 4/4. cargo clippy --workspace --all-targets -D warnings -> clean (one missing-backticks error fixed, not suppressed). cargo test --workspace --release -> 0 FAILED. keel version -> 55 guards (46 hard-blocking, 9 warning-only). THE ASSERTION THAT COULD FAIL was the live-tree probe: had the guard been mis-scoped it would have scanned near zero and passed vacuously, so the probe asserts >400 scanned as well as zero violations."; }
    verification sprintClosureReviewGate : Test { :>> id = "6922fba0-d2aa-45ec-8f32-f97da264973c"; :>> title = "Sprint 496 review gate — three passes per D0172"; :>> createdAt = "2026-08-30"; :>> createdBy = "claudeOpus5"; :>> method = VerificationMethod::inspect; :>> procedureText = "THREE PASSES. (1) IS IT A RATCHET OR A BURDEN: the rule is already observed 496 of 496 times, so adoption costs nobody anything - the strongest available justification for a control, and the one that distinguishes this from process-for-its-own-sake. (2) CAN IT LOCK OUT LEGITIMATE WORK: no - the in-progress exemption is asserted by a dedicated allow-case probe, the specific failure mode that made issue272 into issue273. (3) DOES IT OVERCLAIM: the Decision names what it does NOT fix - a task stamped with a WRONG result is untouched and belongs to the attestation surface (D0232). A guard read as proof of honest evidence would be worse than none."; }
    verification sprintClosureCloseOutGate : Test { :>> id = "d3ceb2db-e940-4a48-81f2-560e3f0f7dfe"; :>> title = "Sprint 496 closeOut gate (autonomous, D0049)"; :>> createdAt = "2026-08-30"; :>> createdBy = "claudeOpus5"; :>> method = VerificationMethod::inspect; :>> procedureText = "CLOSED. 55 guards, zero violations at adoption. The frontier's 'ready' now means what it says for closed sprints: an unstamped task cannot survive the opening of the next sprint."; }
    verification sprintClosureRetroGate : Test { :>> id = "e0dcc54e-21dc-4d1a-8de0-a4e4b0fe38f9"; :>> title = "Sprint 496 retro gate (autonomous, D0049)"; :>> createdAt = "2026-08-30"; :>> createdBy = "claudeOpus5"; :>> method = VerificationMethod::analyze; :>> procedureText = "FINDING, and it is about my reporting rather than the engine: the measurement contradicted my own narrative from the previous turn. I had reported two instances of finished-work-read-as-open; there was one, in 496 sprints, and the second was the model correctly holding work open while I described it as a bookkeeping artifact. THE HAZARD IS DIRECTIONAL: narrating a correct refusal as a false positive builds pressure to relax the definition of done toward 'the code landed', which is the precise move that turned issue272's fix into issue273's Critical. No new control filed for it - a wording gate over my own retros is the D0232 class that has now failed four times and does not calibrate. What is filed instead is the correction itself, in the record, where a successor reads it."; }
}
