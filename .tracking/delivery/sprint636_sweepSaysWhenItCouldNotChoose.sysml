// ProjectDeliveryS636 — Sprint 636: Sprint 636: a knob sweep on recall_bench.py ends with a verdict derived from the measured numbers - DISCRIMINATED naming the spread, or COULD NOT CHOOSE naming the statistic that never moved and whether any case's outcome changed at all (dcSweepSaysWhenItCouldNotChoose, issue405, D0415). EXECUTE: a Sensor's mechanism gains a reporting mode; no guard, hook or process changes. 2 pts.. EXECUTE. 2 pts.
package ProjectDeliveryS636 {
    private import EngineElement::*;
    private import EngineWork::*;
    private import EngineVerification::*;
    private import EngineRelationships::*;

    #CharteredBy dependency from sweepSaysWhenItCouldNotChooseStory to d0415;

    part sweepSaysWhenItCouldNotChooseStory : Story {
        :>> id = "b97bd43d-4c17-4fb7-9282-9c98e5b2551b";
        :>> title = "Sprint 636: a knob sweep on recall_bench.py ends with a verdict derived from the measured numbers - DISCRIMINATED naming the spread, or COULD NOT CHOOSE naming the statistic that never moved and whether any case's outcome changed at all (dcSweepSaysWhenItCouldNotChoose, issue405, D0415). EXECUTE: a Sensor's mechanism gains a reporting mode; no guard, hook or process changes. 2 pts. (2 pts)";
        :>> createdAt = "2026-09-09"; :>> createdBy = "claudeOpus5"; :>> kind = WorkKind::code; :>> priority = WorkPriority::p0; :>> owner = "claudeOpus5"; :>> estimatedPoints = 2;
    }

    action def DeliveryRunS636 {
        action storySweepSaysWhenItCouldNotChoose;
        verification storySweepSaysWhenItCouldNotChooseDoD : Test { :>> id = "46ec1e3f-853a-4c30-a946-2156a3c42d5a"; :>> method = VerificationMethod::test; :>> procedureText = "DELIVERED (dcSweepSaysWhenItCouldNotChoose, resolves issue405 through that item): recall_bench.py takes --sweep KNOB=v1,v2,... (KEEL_RECALL_ prefix optional), runs the chosen arm once per value with the knob in the recall subprocess's environment, prints per-value hits / median position / top-3 / mean rows / latency and ends with one verdict line computed by the pure sweep_verdict from those numbers and the per-case outcome vector; --probe runs that function on its known cases and a sweep refuses to start if one fails. PROBED (D0388) before any tree was read: known-positive D0364's two-hop numbers (0 -> 15/50 md 8, 1.25 -> 22/50 md 5) read DISCRIMINATED naming hits 15..22; known-negative issue405's default-arm numbers (49/50 md 3 at three values, identical per case) read COULD NOT CHOOSE and say this set contains no case the knob applies to; equal totals with one shifted case read COULD NOT CHOOSE naming 1 case and NOT the no-case clause - python .engine/tools/recall_bench.py --probe -> all 6 cases hold. LIVE on tree ae58328 with the script uncommitted: --sweep DOM_HOP2=0.4,0.7,1.0 on the default arm (issue405's own knob and arm) -> 46/50 md 3 top-3 29/46 at every value, verdict COULD NOT CHOOSE ... no case's outcome changed at any value - this set contains no case the knob applies to; --cases 12 --sweep UNREAD_KNOB=1,2 -> the same clause; --hops 2 --sweep DOMINANCE=0,1.25 -> 19/50 md 5 top-3 0/19 then 24/50 md 5 top-3 6/24, verdict DISCRIMINATED, hits moved 19..24; the plain default run after the refactor -> 46/50, md 3, top-3 29/46, p = 0.000 on 44 discordant pairs, which equals the sweep's DOMINANCE=1.25 row. The same first sweep on the default arm read DISCRIMINATED with median position 2..3 (0 -> md 2 top-3 33/46, 1.25 -> md 3 top-3 29/46): recorded as issue430 with resolver dcDominanceRechosenUnderItsOwnRule, not acted on here. D0415 records the verdict rule (auto-accepted, non-fork); the knowledge-graph-memory skill's step-7 row names the sweep."; }
        // RAN: python .engine/tools/recall_bench.py --probe -> all 6 cases hold; --sweep DOM_HOP2=0.4,0.7,1.0 (default arm) -> COULD NOT CHOOSE, no case's outcome changed; --hops 2 --sweep DOMINANCE=0,1.25 -> DISCRIMINATED hits 19..24
        part storySweepSaysWhenItCouldNotChooseDoDR1 : TestResult { :>> id = "bb9a8dba-9a89-4309-8c46-b80343cfa3ba"; :>> outcome = VerdictKind::pass; :>> judgedAgainst = "ae583285ccaf3ae0d56250bda6489d89d13fed2f"; :>> judgedAt = "2026-09-09"; :>> judgedBy = "claudeOpus5"; }
    }

    verification sweepSaysWhenItCouldNotChooseRefineGate : Test { :>> id = "19c0b088-f40b-4df0-b0c1-edefbee616b2"; :>> title = "Sprint 636 refine gate (DoR)"; :>> createdAt = "2026-09-09"; :>> createdBy = "claudeOpus5"; :>> method = VerificationMethod::inspect; :>> procedureText = "Definition of Ready: dcSweepSaysWhenItCouldNotChoose at the head of keel whats-next . after ae58328; its DoD names the property (a sweep that could not discriminate says so), the DO (--sweep, per-value numbers, a verdict line derived from the numbers) and the VERIFY pair (a knob the arm cannot see -> COULD NOT CHOOSE; the two-hop arm -> DISCRIMINATED with the spread); one bench script and its doc row, no fork; 2 points."; }
    // RAN: keel whats-next . after ae58328 -> dcSweepSaysWhenItCouldNotChoose at the head; DoD read at .tracking/backlog.sysml:887-888; 2 points
    part sweepSaysWhenItCouldNotChooseRefineGateR1 : TestResult { :>> id = "723c5169-ba9e-4b33-ae18-d3514e87a160"; :>> outcome = VerdictKind::pass; :>> judgedAgainst = "ae583285ccaf3ae0d56250bda6489d89d13fed2f"; :>> judgedAt = "2026-09-09"; :>> judgedBy = "claudeOpus5"; }
    verification sweepSaysWhenItCouldNotChooseStandupGate : Test { :>> id = "66f231fd-e94b-4c7f-ae35-291cfb7165d1"; :>> title = "Sprint 636 standup gate"; :>> createdAt = "2026-09-09"; :>> createdBy = "claudeOpus5"; :>> method = VerificationMethod::inspect; :>> procedureText = "No blocker. One design point settled at the probe: COULD NOT CHOOSE has two derived clauses, because 'this set contains no case the knob applies to' is a claim about the set and can only be stated when no case's outcome moved at any value; equal totals over shifted cases is the other clause and names the cases, so the DoD's sentence is never asserted where it is false."; }
    // RAN: no blocker; the two COULD NOT CHOOSE clauses settled at the probe (python .engine/tools/recall_bench.py --probe -> all 6 cases hold)
    part sweepSaysWhenItCouldNotChooseStandupGateR1 : TestResult { :>> id = "f5d3ef2d-9286-4d7d-a0d8-c76029233c45"; :>> outcome = VerdictKind::pass; :>> judgedAgainst = "ae583285ccaf3ae0d56250bda6489d89d13fed2f"; :>> judgedAt = "2026-09-09"; :>> judgedBy = "claudeOpus5"; }
    verification sweepSaysWhenItCouldNotChooseImplementGate : Test { :>> id = "4e769509-60a2-4eb2-9371-d55f190f1c05"; :>> title = "Sprint 636 implement gate"; :>> createdAt = "2026-09-09"; :>> createdBy = "claudeOpus5"; :>> method = VerificationMethod::test; :>> procedureText = "recall_bench.py rewritten with the Write tool (its body carries a Windows path and regexes, D0309): main split into build_cases, run_arm (returns the statistics the summary prints plus the per-case outcome vector) and print_summary, with sweep_stats, sweep_verdict, parse_sweep and probe added; the plain run's output is unchanged line for line except the D0364 two-hop docstring paragraph gained its successor on the sweep. Six live runs at about 1.4 s per recall call: 50 cases per value, 2-3 values per sweep. The skill row patched through textpatch (docsync636.py) and keel sync-claude regenerated the .claude copy."; }
    // RAN: python .engine/tools/recall_bench.py --probe -> all 6 cases hold; --sweep DOM_HOP2=0.4,0.7,1.0 -> COULD NOT CHOOSE (no case the knob applies to); --hops 2 --sweep DOMINANCE=0,1.25 -> DISCRIMINATED hits 19..24; plain run 46/50 md 3 = the sweep's 1.25 row; keel sync-claude .
    part sweepSaysWhenItCouldNotChooseImplementGateR1 : TestResult { :>> id = "dc36bcd4-6bde-42eb-a522-18dfb7a6e822"; :>> outcome = VerdictKind::pass; :>> judgedAgainst = "ae583285ccaf3ae0d56250bda6489d89d13fed2f"; :>> judgedAt = "2026-09-09"; :>> judgedBy = "claudeOpus5"; }
    verification sweepSaysWhenItCouldNotChooseReviewGate : Test { :>> id = "0ae48cfd-3614-4bde-a401-d012204be93e"; :>> title = "Sprint 636 review gate — three passes per D0172"; :>> createdAt = "2026-09-09"; :>> createdBy = "claudeOpus5"; :>> method = VerificationMethod::inspect; :>> procedureText = "Three passes per D0172: (1) the verdict is probed on the two sides that matter and on the case that separates the two COULD NOT CHOOSE clauses; (2) the live runs cover the DoD's VERIFY pair on issue405's own knob and arm, plus a knob nothing reads; (3) the plain run's summary numbers equal the sweep's row at the default setting, so the refactor moved nothing."; }
    // RAN: three passes: probe pair + clause-separating case; live VERIFY pair on issue405's knob and arm plus an unread knob (--cases 12 --sweep UNREAD_KNOB=1,2); plain summary equals the sweep row at the default
    part sweepSaysWhenItCouldNotChooseReviewGateR1 : TestResult { :>> id = "45ff6adc-cb0a-46a2-9702-cbc94aef80fc"; :>> outcome = VerdictKind::pass; :>> judgedAgainst = "ae583285ccaf3ae0d56250bda6489d89d13fed2f"; :>> judgedAt = "2026-09-09"; :>> judgedBy = "claudeOpus5"; }
    verification sweepSaysWhenItCouldNotChooseCloseOutGate : Test { :>> id = "bd207ecb-8445-4b27-bab2-750da920a39c"; :>> title = "Sprint 636 closeOut gate (autonomous, D0049)"; :>> createdAt = "2026-09-09"; :>> createdBy = "claudeOpus5"; :>> method = VerificationMethod::inspect; :>> procedureText = "keel validate . clean, keel check-engine . clean, keel gate --fast clean; dcSweepSaysWhenItCouldNotChooseDoD stamped with the probe and the live verdict lines named; issue430 recorded and triaged to dcDominanceRechosenUnderItsOwnRule."; }
    // RAN: keel validate . && keel check-engine . && keel gate --fast . clean; dcSweepSaysWhenItCouldNotChooseDoD stamped; issue430 -> dcDominanceRechosenUnderItsOwnRule
    part sweepSaysWhenItCouldNotChooseCloseOutGateR1 : TestResult { :>> id = "b0503cbe-8ded-4885-9ce4-89e3fd775c56"; :>> outcome = VerdictKind::pass; :>> judgedAgainst = "ae583285ccaf3ae0d56250bda6489d89d13fed2f"; :>> judgedAt = "2026-09-09"; :>> judgedBy = "claudeOpus5"; }
    verification sweepSaysWhenItCouldNotChooseRetroGate : Test { :>> id = "f0a328a9-28ea-4f24-92f4-f945edbdb255"; :>> title = "Sprint 636 retro gate (autonomous, D0049)"; :>> createdAt = "2026-09-09"; :>> createdBy = "claudeOpus5"; :>> method = VerificationMethod::analyze; :>> procedureText = "Avoidable-issue scan: the sweep's first live run on the default arm did not reproduce issue405's neutrality - the tree has grown two days past sprint 593 and the bonus now touches the one-hop set - so the DoD's VERIFY was met on issue405's other knob, DOM_HOP2, which the arm still cannot see. The finding that fell out of that is issue430 (the setting in force fails the rule that chose it), already tracked with its resolver dcDominanceRechosenUnderItsOwnRule. Observed and NOT concluded: the plain default run reads 46/50 against 49/50 two days ago at both knob values, so the drop is the tree's and not the knob's; which additions moved it is not measured here. No new item beyond issue430."; }
    // RAN: retro recorded in the sprint file; issue430 is the one finding, already tracked with its resolver
    part sweepSaysWhenItCouldNotChooseRetroGateR1 : TestResult { :>> id = "fdfc7926-2c8a-4b81-9e4f-fe27905d95b0"; :>> outcome = VerdictKind::pass; :>> judgedAgainst = "ae583285ccaf3ae0d56250bda6489d89d13fed2f"; :>> judgedAt = "2026-09-09"; :>> judgedBy = "claudeOpus5"; }
}
