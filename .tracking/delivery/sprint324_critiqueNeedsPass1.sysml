// ProjectDeliveryS324 — Sprint 324: critique backfill pass 1 — five human-authored Needs. EXECUTE. 3 pts.
package ProjectDeliveryS324 {
    private import EngineElement::*;
    private import EngineWork::*;
    private import EngineVerification::*;
    private import EngineRelationships::*;

    #CharteredBy dependency from critPass1Story to d0080;

    part critPass1Story : Story {
        :>> id = "0d8003f0-0814-63f0-9b3e-0000003003f0";
        :>> title = "Sprint 324: critique pass 1 — 5 Needs x Core-3, 14 fail / 1 pass (3 pts)";
        :>> createdAt = "2026-08-17"; :>> createdBy = "claudeOpus5"; :>> kind = WorkKind::modeling; :>> priority = WorkPriority::p0; :>> owner = "claudeOpus5"; :>> estimatedPoints = 3;
    }

    action def DeliveryRunS324 {
        action storyCritPass1;
        verification storyCritPass1DoD : Test { :>> id = "0d8003f1-0814-63f1-9b3e-0000003003f1"; :>> method = VerificationMethod::analyze; :>> procedureText = "First pass of the element-critique backfill, five elements with Core-3 lenses each, targets chosen for INDEPENDENCE: critique-policy.toml requires judgedBy != the element's author, so the five are all wweatherholtz-authored Needs (nProcessPortability, nAiGovernanceInLoop, nReleaseDiscipline, nServeApproveBeforeExecute, nServeBoundedContext). MEASURED FIRST — of 154 uncovered elements, 67 are authored by someone other than claudeOpus5 and are critiquable by me; 87 are my own and are BLOCKED on a different critic, which is a real blocker rather than an approval one. 14 of 15 lenses FAIL, and the findings are substantive rather than procedural: nProcessPortability asserts 'enforcement travels with it' which no file transfer can deliver (guards are compiled into the binary, and unit.toml already documents the gap); nReleaseDiscipline's justifying clause is now FALSE (it cites a never-run Deploy workflow that has since run three times); nServeBoundedContext is contradicted by the primary way this engine is actually used — this very multi-sprint session is the diffuse long-running context it warns against, and it has been the productive mode. READ BACK from the computed view: Need coverage 3 -> 8 of 39. validate 352 clean; 34 guards ALL PASS."; }
        part storyCritPass1DoDR1 : TestResult { :>> id = "0d8003f2-0814-63f2-9b3e-0000003003f2"; :>> outcome = VerdictKind::pass; :>> judgedAgainst = "763b016"; :>> judgedAt = "2026-08-17"; :>> judgedBy = "claudeOpus5"; }
    }

    verification c1RefineGate : Test { :>> id = "0d8003f3-0814-63f3-9b3e-0000003003f3"; :>> title = "Sprint 324 refine gate (DoR)"; :>> createdAt = "2026-08-17"; :>> createdBy = "claudeOpus5"; :>> method = VerificationMethod::inspect; :>> procedureText = "DoR. Five elements per pass, one sprint per pass, critiques authored directly into critiques.sysml — the batch size the human set after an earlier oversized pass, kept because it is a QUALITY constraint and their instruction not to be stopped for approval overrode only the go/no-go pause, not the batch size. Needs first because they root the satisfaction tier: a defective Need propagates into every requirement derived from it, so critiquing requirements before their Needs would judge the derivation against a target nobody had examined. estimatedPoints=3."; }
    part c1RefineGateR1 : TestResult { :>> id = "0d8003f4-0814-63f4-9b3e-0000003003f4"; :>> outcome = VerdictKind::pass; :>> judgedAgainst = "763b016"; :>> judgedAt = "2026-08-17"; :>> judgedBy = "claudeOpus5"; }

    verification c1StandupGate : Test { :>> id = "0d8003f5-0814-63f5-9b3e-0000003003f5"; :>> title = "Sprint 324 standup gate"; :>> createdAt = "2026-08-17"; :>> createdBy = "claudeOpus5"; :>> method = VerificationMethod::inspect; :>> procedureText = "Approach: measure the independence split BEFORE picking targets, so no effort goes into critiques the policy will not count; read each Need's full statement rather than its title; generate ids from a CSPRNG rather than hand-minting them, which is sprint 320's recorded lesson. No blockers."; }
    part c1StandupGateR1 : TestResult { :>> id = "0d8003f6-0814-63f6-9b3e-0000003003f6"; :>> outcome = VerdictKind::pass; :>> judgedAgainst = "763b016"; :>> judgedAt = "2026-08-17"; :>> judgedBy = "claudeOpus5"; }

    verification c1ImplementGate : Test { :>> id = "0d8003f7-0814-63f7-9b3e-0000003003f7"; :>> title = "Sprint 324 implement gate"; :>> createdAt = "2026-08-17"; :>> createdBy = "claudeOpus5"; :>> method = VerificationMethod::analyze; :>> procedureText = "ONE LENS PASSED AND THE REASON IS RECORDED, because a pass is a claim too: nReleaseDiscipline's testability passes NARROWLY — its artifact clauses are independently checkable and `keel version` already reports the reconciliation — while its cadence clause ('per-milestone/on-demand') is unfalsifiable, since any interval including never satisfies on-demand. Recorded as a pass because that clause is honestly a scope exclusion rather than a requirement; reading it as a constraint would be reading testability into words that do not carry it. TWO RECURRING DEFECT SHAPES across the five Needs, both of which the engine's own downstream work already compensated for: SOLUTION-BOUND statements (nAiGovernanceInLoop names an MCP surface that was never built, while the concern it stands for is served by the output style, orient, and the hooks), and MISSING BOUNDS supplied downstream (nServeBoundedContext states no unit or threshold, so its requirements chose their own — meaning the Need cannot adjudicate a dispute about whether a context is too wide)."; }
    part c1ImplementGateR1 : TestResult { :>> id = "0d8003f8-0814-63f8-9b3e-0000003003f8"; :>> outcome = VerdictKind::pass; :>> judgedAgainst = "763b016"; :>> judgedAt = "2026-08-17"; :>> judgedBy = "claudeOpus5"; }

    verification c1ReviewGate : Test { :>> id = "0d8003f9-0814-63f9-9b3e-0000003003f9"; :>> title = "Sprint 324 review gate"; :>> createdAt = "2026-08-17"; :>> createdBy = "claudeOpus5"; :>> method = VerificationMethod::inspect; :>> procedureText = "Reviewed. NO ISSUES WERE RAISED FOR THE 14 FAILING CRITIQUES, deliberately: a failing critique IS a recorded finding, carrying its lens, its judge, its date and a #Verify edge to the element it judges. Duplicating each as an Issue would record one finding in two places, which is the dual truth invariant 1 forbids, and it would put 14 items on a frontier where the only permitted actor is the Needs' owner. They are the owner's to act on — every one of these five Needs is wweatherholtz's, and D0108 bars me from narrowing any of them. SELF-CHECK ON RIGOR: the critique-rigor diagnostic exists to flag affirming-only critics, and a 14-of-15 fail rate invites the opposite suspicion — that I found fault to look thorough. The defence is that each finding names a specific clause and a specific consequence, three of them cite the engine's own artifacts contradicting the Need (unit.toml's warning, the three shipped releases, D0151), and one lens passed where the evidence supported it."; }
    part c1ReviewGateR1 : TestResult { :>> id = "0d8003fa-0814-63fa-9b3e-0000003003fa"; :>> outcome = VerdictKind::pass; :>> judgedAgainst = "763b016"; :>> judgedAt = "2026-08-17"; :>> judgedBy = "claudeOpus5"; }

    verification c1CloseOutGate : Test { :>> id = "0d8003fb-0814-63fb-9b3e-0000003003fb"; :>> title = "Sprint 324 closeOut gate (autonomous, D0049)"; :>> createdAt = "2026-08-17"; :>> createdBy = "claudeOpus5"; :>> method = VerificationMethod::inspect; :>> procedureText = "Autonomous closeOut (D0049). Need coverage 3 -> 8 of 39; 62 critiquable elements remain (15 Needs, 25 SystemRequirements, 22 Decisions) plus 87 blocked on an independent critic. Zero open issues; ready frontier empty; D0159 queued for acceptance. validate 352 clean; check-engine clean; 34 guards ALL PASS; no code changed."; }
    part c1CloseOutGateR1 : TestResult { :>> id = "0d8003fc-0814-63fc-9b3e-0000003003fc"; :>> outcome = VerdictKind::pass; :>> judgedAgainst = "763b016"; :>> judgedAt = "2026-08-17"; :>> judgedBy = "claudeOpus5"; }

    verification c1RetroGate : Test { :>> id = "0d8003fd-0814-63fd-9b3e-0000003003fd"; :>> title = "Sprint 324 retro gate (autonomous, D0049)"; :>> createdAt = "2026-08-17"; :>> createdBy = "claudeOpus5"; :>> method = VerificationMethod::analyze; :>> procedureText = "Autonomous retro (D0049) under D0131's retroTrack. WELL: (1) the independence split was measured before any critique was written, so no effort went into work the policy would discard — and it also produced the honest number for what I am NOT permitted to do (87 elements); (2) ids came from a CSPRNG, applying sprint 320's lesson instead of restating it; (3) the one passing lens carries its reasoning, so a reader can disagree with the pass rather than only with the fails. AVOIDABLE-ISSUE: a bash heredoc broke on quoting for the fourth time this session, and the fix was the one already recorded — write the script to a file and run the file. The pattern is now specific enough to state as a rule: any generated text containing apostrophes, backticks or nested quotes goes through a FILE, never a heredoc, because the failure is a shell parse error that says nothing about which character caused it. NO NEW ITEM: it costs one wasted call and is instantly diagnosable. Estimate 3 pts, delivered."; }
    part c1RetroGateR1 : TestResult { :>> id = "0d8003fe-0814-63fe-9b3e-0000003003fe"; :>> outcome = VerdictKind::pass; :>> judgedAgainst = "763b016"; :>> judgedAt = "2026-08-17"; :>> judgedBy = "claudeOpus5"; }
}
