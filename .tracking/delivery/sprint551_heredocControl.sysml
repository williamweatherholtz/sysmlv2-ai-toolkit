// ProjectDeliveryS551 — Sprint 551: the heredoc defect gets a control, and the retro process gets a control over its own blind spot. EXECUTE. 3 pts.
package ProjectDeliveryS551 {
    private import EngineElement::*;
    private import EngineWork::*;
    private import EngineVerification::*;
    private import EngineRelationships::*;

    #CharteredBy dependency from heredocControlStory to d0309;

    part heredocControlStory : Story {
        :>> id = "770788c8-bcfe-4397-8c63-978fdae4d2b7";
        :>> title = "Sprint 551: the heredoc defect gets a control, and the retro process gets a control over its own blind spot (3 pts)";
        :>> createdAt = "2026-09-05"; :>> createdBy = "claudeOpus5"; :>> kind = WorkKind::code; :>> priority = WorkPriority::p0; :>> owner = "claudeOpus5"; :>> estimatedPoints = 3;
    }

    action def DeliveryRunS551 {
        action storyHeredocControl;
        verification storyHeredocControlDoD : Test { :>> id = "552967f7-dd78-441e-9d4e-e56de7d31896"; :>> method = VerificationMethod::test; :>> procedureText = "DELIVERED BACKLOG ITEMS: dcPreBashSeesHeredocSource (resolves issue372, and the recurring heredoc class). DONE, in two single-clause Decisions: D0309 - keel hook pre-bash DENIES a Bash command whose heredoc body carries a backslash, in every profile, naming the tag, the line and the Write-tool remedy, because the harness collapses backslash pairs before bash runs (measured with cat <<'EOF'); prose heredocs and backslashes outside a heredoc pass. D0310 - guard 62 recurrence-escalates: an open item named by two or more retros as the already-tracked home is a violation unless it is in the next three ready items or blocked on a proposed Decision; superseded items are not open; the frontier is computed only when a candidate exists. VERIFY: detector unit test (source named, prose passes, outside passes, <<- form); live hook denies the exact Python-with-escapes shape and is silent on a commit message; the deny fired on its author one minute after being built; recurrence guard - first run named three (one superseded, fixed; one the heredoc item, delivered here; one dcVerificationByAuthority, pulled to the front and now exempt as being worked); integration probe in hook_and_push_controls_actually_fire; issue372 records the process failure; CLAUDE.md sections 5 and 6 name the rule; suite and clippy in the RAN line."; }
        // RAN: cargo test --release --no-fail-fast 489 passed 0 failed (completed before this line); clippy 0; live pre-bash deny on the Python-with-escapes shape, silent on a commit-message heredoc; the deny fired on its author within a minute; recurrence-escalates first run 3 -> 0 after supersession + ranked-frontier fixes; guard time lazy
        part storyHeredocControlDoDR1 : TestResult { :>> id = "8ec7fe6f-49e3-4505-a865-765c67f6b947"; :>> outcome = VerdictKind::pass; :>> judgedAgainst = "6702c38"; :>> judgedAt = "2026-09-05"; :>> judgedBy = "claudeOpus5"; }
    }

    verification heredocControlRefineGate : Test { :>> id = "84bb1907-795f-4a1e-808b-a3329b1db02d"; :>> title = "Sprint 551 refine gate (DoR)"; :>> createdAt = "2026-09-05"; :>> createdBy = "claudeOpus5"; :>> method = VerificationMethod::inspect; :>> procedureText = "READY the moment the human asked the question, because the answer was already in the tree: the item existed, the retros named it, and nothing computed that naming it twice meant the defect had recurred. The measurement that made it buildable was one line of shell: a backslash pair collapses to one inside a quoted heredoc."; }
    verification heredocControlStandupGate : Test { :>> id = "7b796ad8-484c-40dd-8c9b-7b6c67cf8b80"; :>> title = "Sprint 551 standup gate"; :>> createdAt = "2026-09-05"; :>> createdBy = "claudeOpus5"; :>> method = VerificationMethod::inspect; :>> procedureText = "THREE CHOICES stated plainly. (1) Deny, not advise: the advisory, the memory and the Issue were three reminders and eight recurrences past them; D0047 was written for exactly this. (2) Two Decisions, not one: under D0303 C a layered change is one Decision per clause, and this is the first day the rule binds - so the deny and the escalation guard are D0309 and D0310. (3) The escalation guard exempts the front of the frontier and fork-blocked items, because those are the two honest states a recurring item can be in; everything else is deferral by silence, which is what happened."; }
    verification heredocControlImplementGate : Test { :>> id = "6a25cf2a-a603-4ceb-9d78-38a723d2436c"; :>> title = "Sprint 551 implement gate"; :>> createdAt = "2026-09-05"; :>> createdBy = "claudeOpus5"; :>> method = VerificationMethod::test; :>> procedureText = "RAN: probe the mechanism first (cat <<'EOF' with backslash forms); detector + deny; the deny fired on my own census script; recurrence guard's first run over-counted a superseded item and mis-read the frontier (the simple unranked orient, not the ranked one) - both fixed; the guard then cost six seconds per gate until the frontier became lazy; keystone lock demanded the Decisions; clippy items on both."; }
    verification heredocControlReviewGate : Test { :>> id = "766ebcb0-2e82-4af0-8313-5fb747a45f11"; :>> title = "Sprint 551 review gate — three passes per D0172"; :>> createdAt = "2026-09-05"; :>> createdBy = "claudeOpus5"; :>> method = VerificationMethod::inspect; :>> procedureText = "THREE PASSES. (1) CAN THE DENY BE ROUTED AROUND: yes - printf, echo -e, a here-string; the deny covers the shape that has actually failed eight times and the fire-ledger records every deny, so the next shape shows up as a count. (2) IS THE ESCALATION GUARD GAMEABLE: a retro can avoid naming the item - then retro-backlog's fourth shape fails it for naming nothing; naming a different item each time is the remaining hole, and it is the reviewer's to read. (3) COST: recurrence-escalates runs orient only when a candidate exists; today there is one (dcVerificationByAuthority, exempt at the front), so the gate pays ~5s until it is worked - which is the point."; }
    verification heredocControlCloseOutGate : Test { :>> id = "44a09bf7-917a-4201-b9a0-3b666b89b806"; :>> title = "Sprint 551 closeOut gate (autonomous, D0049)"; :>> createdAt = "2026-09-05"; :>> createdBy = "claudeOpus5"; :>> method = VerificationMethod::inspect; :>> procedureText = "CLOSED. issue372 resolves; guard count 62; dcVerificationByAuthority is next."; }
    verification heredocControlRetroGate : Test { :>> id = "f1801818-7b63-4607-898d-10520232f16d"; :>> title = "Sprint 551 retro gate (autonomous, D0049)"; :>> createdAt = "2026-09-05"; :>> createdBy = "claudeOpus5"; :>> method = VerificationMethod::analyze; :>> procedureText = "no new item - already tracked: the remaining bypass shapes (printf, here-strings) are counted by the fire-ledger and are not a finding until one fires; dcVerificationByAuthority is at the front by the guard's own demand. The lesson is the human's, verbatim: are we not flagging issues in sprint retros - we were, and flagging without escalation is how a tracked defect recurs eight times; the guard that reads the count is what was missing."; }
}
