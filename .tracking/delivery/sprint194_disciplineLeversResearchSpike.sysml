// ProjectDeliveryS194 — Sprint 194: disciplineLeversResearchSpike (RESEARCH). Research how to get better
// AI-agent discipline (the human's frontend / claude -p / better-skill ideas). DOGFOODS the research-spike
// routing (issue055) — chartered to the proposed D0109 (a research spike -> a proposed decision). EXECUTE. 1 pt. AUTONOMOUS (D0049).
package ProjectDeliveryS194 {
    private import EngineElement::*;
    private import EngineWork::*;
    private import EngineVerification::*;
    private import EngineRelationships::*;

    #CharteredBy dependency from discLeversStory to d0109;

    part discLeversStory : Story {
        :>> id = "63940516-2c7d-4e8f-c194-51627384c001";
        :>> title = "Sprint 194: disciplineLeversResearchSpike (1 pt) - research better agent discipline (frontend/claude-p/skill) -> D0109";
        :>> createdAt = "2026-07-06"; :>> createdBy = "wweatherholtz"; :>> kind = WorkKind::research; :>> priority = WorkPriority::p2; :>> owner = "claudeOpus"; :>> estimatedPoints = 1;
    }

    action def DeliveryRunS194 {
        action storyDiscLevers;
        verification storyDiscLeversDoD : Test { :>> id = "63940516-2c7d-4e8f-c194-51627384c002"; :>> method = VerificationMethod::analyze; :>> procedureText = "Research spike on 'how to get better AI-agent discipline' (the human's directive), routed as a chartered research spike (issue055) rather than freeform chat. FINDINGS (docs/proposals/2026-07-06-ai-discipline-levers.md): the drift problem is REAL (evidenced this self-build); `claude -p` is the WRONG lever for prompt overhead (same system prompt; SDK is the only prompt-owning path, enterprise-auth-constrained); discipline lives in the ACTION SPACE not instructions (strong-typing insight — a skill is a linter, typed tools/process-launcher/schema-I/O are the compiler); lever hierarchy hard->soft = constrain-action-space > short-context > validated-I/O+repair > approve-gates > rigorous-skill; a better input skill is necessary-NOT-sufficient (engine-triage already exists + D0106 emits Parsed: and was still violated); a frontend uniquely CAN close D0106's conversational residual (issue059) at the interaction boundary; build it as `keel serve` maturation, not a new AI IDE. RECOMMENDED DIRECTION recorded as D0109 (proposed): action-space constraints at keel's boundary (process-launcher + validated I/O + short context), NOT a general frontend / claude -p / skill-alone. VERIFY: proposal artifact authored; D0109 proposed + kernel-validated; keel validate + guard all (15) green. Open forks (build order, harness) left to the human."; }
        part storyDiscLeversDoDR1 : TestResult { :>> id = "63940516-2c7d-4e8f-c194-51627384c003"; :>> outcome = VerdictKind::pass; :>> judgedAgainst = "37931c2"; :>> judgedAt = "2026-07-06"; :>> judgedBy = "claudeOpus"; }
    }

    verification discLeversRefineGate : Test { :>> id = "63940516-2c7d-4e8f-c194-51627384c004"; :>> title = "Sprint 194 refine gate (DoR)"; :>> createdAt = "2026-07-06"; :>> createdBy = "claudeOpus"; :>> method = VerificationMethod::inspect; :>> procedureText = "DoR: human directed 'research how to get better discipline'. Substantial analysis -> a chartered research spike (issue055/D0106), NOT freeform chat. estimatedPoints=1. #CharteredBy d0109 (proposed). DoR met."; }
    part discLeversRefineGateR1 : TestResult { :>> id = "63940516-2c7d-4e8f-c194-51627384c005"; :>> outcome = VerdictKind::pass; :>> judgedAgainst = "37931c2"; :>> judgedAt = "2026-07-06"; :>> judgedBy = "claudeOpus"; }
    verification discLeversStandupGate : Test { :>> id = "63940516-2c7d-4e8f-c194-51627384c006"; :>> title = "Sprint 194 standup gate"; :>> createdAt = "2026-07-06"; :>> createdBy = "claudeOpus"; :>> method = VerificationMethod::inspect; :>> procedureText = "Approach: synthesize the lever research into a proposal artifact + a proposed D0109 (the recommended direction); charter the spike to D0109 (dogfood issue055 routing). No code. No blockers."; }
    part discLeversStandupGateR1 : TestResult { :>> id = "63940516-2c7d-4e8f-c194-51627384c007"; :>> outcome = VerdictKind::pass; :>> judgedAgainst = "37931c2"; :>> judgedAt = "2026-07-06"; :>> judgedBy = "claudeOpus"; }
    verification discLeversImplementGate : Test { :>> id = "63940516-2c7d-4e8f-c194-51627384c008"; :>> title = "Sprint 194 implement gate"; :>> createdAt = "2026-07-06"; :>> createdBy = "claudeOpus"; :>> method = VerificationMethod::analyze; :>> procedureText = "Proposal artifact + D0109 (proposed) authored. kernel validate_instances PASS (D0109); keel validate + guard all (15) green."; }
    part discLeversImplementGateR1 : TestResult { :>> id = "63940516-2c7d-4e8f-c194-51627384c009"; :>> outcome = VerdictKind::pass; :>> judgedAgainst = "37931c2"; :>> judgedAt = "2026-07-06"; :>> judgedBy = "claudeOpus"; }
    verification discLeversReviewGate : Test { :>> id = "63940516-2c7d-4e8f-c194-51627384c00a"; :>> title = "Sprint 194 review gate"; :>> createdAt = "2026-07-06"; :>> createdBy = "claudeOpus"; :>> method = VerificationMethod::inspect; :>> procedureText = "Reviewed. The research itself was routed through the discipline it studied — a chartered research spike (issue055), not a freeform chat dump — which is the point. Findings are honest (corrects the claude -p premise; affirms the strong-typing insight; ranks a 'better skill' as the weakest lever). D0109 stays PROPOSED (the human decides the direction + open forks). Clean."; }
    part discLeversReviewGateR1 : TestResult { :>> id = "63940516-2c7d-4e8f-c194-51627384c00b"; :>> outcome = VerdictKind::pass; :>> judgedAgainst = "37931c2"; :>> judgedAt = "2026-07-06"; :>> judgedBy = "claudeOpus"; }
    verification discLeversCloseOutGate : Test { :>> id = "63940516-2c7d-4e8f-c194-51627384c00c"; :>> title = "Sprint 194 closeOut gate (autonomous, D0049)"; :>> createdAt = "2026-07-06"; :>> createdBy = "claudeOpus"; :>> method = VerificationMethod::inspect; :>> procedureText = "Autonomous closeOut (D0049): DoD pass; the discipline research is captured as a tracked artifact + a proposed direction (D0109). keel validate + guard all (15) green. Self-evidencing (D0051). Awaits the human's D0109 decision + fork choices."; }
    part discLeversCloseOutGateR1 : TestResult { :>> id = "63940516-2c7d-4e8f-c194-51627384c00d"; :>> outcome = VerdictKind::pass; :>> judgedAgainst = "37931c2"; :>> judgedAt = "2026-07-06"; :>> judgedBy = "claudeOpus"; }
    verification discLeversRetroGate : Test { :>> id = "63940516-2c7d-4e8f-c194-51627384c00e"; :>> title = "Sprint 194 retro gate (autonomous, D0049)"; :>> createdAt = "2026-07-06"; :>> createdBy = "claudeOpus"; :>> method = VerificationMethod::analyze; :>> procedureText = "Autonomous retro (D0049). WELL: dogfooded the research-spike routing (issue055) on a real research directive — the research on discipline was ITSELF done with discipline (tracked spike + proposal + proposed decision), not a freeform chat dump; and it honestly corrected the human's claude -p premise + ranked their 'better skill' idea as the weakest lever. AVOIDABLE-ISSUE SCAN: none. LESSON: when asked to 'research X', route it to a chartered spike -> a proposal + a proposed decision; that IS the discipline the human is asking for. Estimate 1 pt held. Follow-on: the human decides D0109 (accept/revise) + the build-order/harness forks; if accepted, the work becomes keel serve increments (also closing issue061 via the business-architecture skill)."; }
    part discLeversRetroGateR1 : TestResult { :>> id = "63940516-2c7d-4e8f-c194-51627384c00f"; :>> outcome = VerdictKind::pass; :>> judgedAgainst = "37931c2"; :>> judgedAt = "2026-07-06"; :>> judgedBy = "claudeOpus"; }
}
