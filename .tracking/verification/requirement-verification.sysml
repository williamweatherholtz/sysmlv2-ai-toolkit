// =====================================================================
// ProjectRequirementVerification — OBJECTIVE verification of the system requirements (D0079 C / D0082).
// Each `verification srNNVerify : Test` records the reproducible evidence that the requirement holds,
// #Verify-linked to it; the passing TestResult makes srNNVerify a done task, so `sysmlv2 coverage`
// reports the requirement VERIFIED (tier, D0082). The 14 Needs become verified TRANSITIVELY via their
// satisfy'd requirement. EXCEPTION: sr11FastStart is a measured GAP (orient ~13.6s vs <500ms) — no
// passing verification is authored; it is tracked as an Issue (see issues.sysml) per D0079 (never
// fake a pass). Methods: test = automated check; inspect/analyze = repo evidence (self-evidencing, D0051).
// All judged against HEAD 0941e97 on 2026-06-21 by claudeOpus.
// =====================================================================
package ProjectRequirementVerification {
    private import EngineElement::*;
    private import EngineVerification::*;
    private import EngineRelationships::*;

    verification sr01Verify : Test { :>> id = "7a1c0001-0001-4e01-9a01-516273840001"; :>> title = "Verify sr01TypedItems"; :>> createdAt = "2026-06-21"; :>> createdBy = "claudeOpus"; :>> method = VerificationMethod::test; :>> procedureText = "Every tracked element has an immutable UUID id, a metaclass, and typed attribute fields: demonstrated by kernel validate_schema (14/14, schema/core type vocabulary) + the parser test suite (cargo test -p sysmlv2-parser, part/requirement/verification with id+attrs) + rust `sysmlv2 validate` (84 files clean). Re-run: those three commands green."; }
    part sr01VerifyR1 : TestResult { :>> id = "7a1c0001-0001-4e01-9a01-5162738400a1"; :>> outcome = VerdictKind::pass; :>> judgedAgainst = "0941e97"; :>> judgedAt = "2026-06-21"; :>> judgedBy = "claudeOpus"; }
    #Verify dependency from sr01Verify to sr01TypedItems;

    verification sr02Verify : Test { :>> id = "7a1c0002-0002-4e02-9a02-516273840002"; :>> title = "Verify sr02DecisionRecord"; :>> createdAt = "2026-06-21"; :>> createdBy = "claudeOpus"; :>> method = VerificationMethod::inspect; :>> procedureText = "Decision items with rationale + typed #Supersede edges to cancelled Needs: 81 Decision files in .engine/decisions/ each carry context/decision/rationale/consequences; supersede edges are authored (e.g. scope-cut Decisions). validate_instances 92/92 green. Inspect .engine/decisions/ + the supersede edges."; }
    part sr02VerifyR1 : TestResult { :>> id = "7a1c0002-0002-4e02-9a02-5162738400a2"; :>> outcome = VerdictKind::pass; :>> judgedAgainst = "0941e97"; :>> judgedAt = "2026-06-21"; :>> judgedBy = "claudeOpus"; }
    #Verify dependency from sr02Verify to sr02DecisionRecord;

    verification sr03Verify : Test { :>> id = "7a1c0003-0003-4e03-9a03-516273840003"; :>> title = "Verify sr03AppendResults"; :>> createdAt = "2026-06-21"; :>> createdBy = "claudeOpus"; :>> method = VerificationMethod::test; :>> procedureText = "Each verification execution is a distinct TestResult with outcome+judgedAgainst+judgedBy, never mutated: the write API (`sysmlv2 append-result`/`append-gate-result`) enforces append-only N+1 UUID generation, covered by the write.rs test suite (cargo test -p sysmlv2-cli write). Re-run: cargo test green; inspect any task's R1..Rn result chain."; }
    part sr03VerifyR1 : TestResult { :>> id = "7a1c0003-0003-4e03-9a03-5162738400a3"; :>> outcome = VerdictKind::pass; :>> judgedAgainst = "0941e97"; :>> judgedAt = "2026-06-21"; :>> judgedBy = "claudeOpus"; }
    #Verify dependency from sr03Verify to sr03AppendResults;

    verification sr04Verify : Test { :>> id = "7a1c0004-0004-4e04-9a04-516273840004"; :>> title = "Verify sr04ComputedViews"; :>> createdAt = "2026-06-21"; :>> createdBy = "claudeOpus"; :>> method = VerificationMethod::test; :>> procedureText = "Orientation/coverage/suspicion are COMPUTED from facts+git, with no authored status/coverage/suspicion fields: `sysmlv2 orient`/`coverage`/`suspect` produce these views, and a grep confirms ZERO authored `:>> done/ready/coverageState/suspicion =` fields in .tracking/ (only Decision.status, which is authored + legitimate). Re-run: the three subcommands + the grep."; }
    part sr04VerifyR1 : TestResult { :>> id = "7a1c0004-0004-4e04-9a04-5162738400a4"; :>> outcome = VerdictKind::pass; :>> judgedAgainst = "0941e97"; :>> judgedAt = "2026-06-21"; :>> judgedBy = "claudeOpus"; }
    #Verify dependency from sr04Verify to sr04ComputedViews;

    verification sr05Verify : Test { :>> id = "7a1c0005-0005-4e05-9a05-516273840005"; :>> title = "Verify sr05GitNative"; :>> createdAt = "2026-06-21"; :>> createdBy = "claudeOpus"; :>> method = VerificationMethod::inspect; :>> procedureText = "All authored items/edges are .sysml text committed to git, and commit SHAs are the causal clock for suspicion: the repo is a git repo, every item is a .sysml file, and orient/suspect compute happened-before via `git merge-base --is-ancestor` over judgedAgainst SHAs (orient.rs). Inspect: git log; orient.rs git ancestry usage."; }
    part sr05VerifyR1 : TestResult { :>> id = "7a1c0005-0005-4e05-9a05-5162738400a5"; :>> outcome = VerdictKind::pass; :>> judgedAgainst = "0941e97"; :>> judgedAt = "2026-06-21"; :>> judgedBy = "claudeOpus"; }
    #Verify dependency from sr05Verify to sr05GitNative;

    verification sr06Verify : Test { :>> id = "7a1c0006-0006-4e06-9a06-516273840006"; :>> title = "Verify sr06ProcessModel"; :>> createdAt = "2026-06-21"; :>> createdBy = "claudeOpus"; :>> method = VerificationMethod::inspect; :>> procedureText = "Workflows, phase sequences, gate criteria, and skill registries are .sysml in .engine/, readable/executable by agents without in-context embedding: .engine/processes/*.sysml (8 process-defs), .engine/skills/skills-registry.sysml, .engine/views/ — all parse (validate_instances 92/92). Inspect .engine/."; }
    part sr06VerifyR1 : TestResult { :>> id = "7a1c0006-0006-4e06-9a06-5162738400a6"; :>> outcome = VerdictKind::pass; :>> judgedAgainst = "0941e97"; :>> judgedAt = "2026-06-21"; :>> judgedBy = "claudeOpus"; }
    #Verify dependency from sr06Verify to sr06ProcessModel;

    verification sr07Verify : Test { :>> id = "7a1c0007-0007-4e07-9a07-516273840007"; :>> title = "Verify sr07AgentLoop"; :>> createdAt = "2026-06-21"; :>> createdBy = "claudeOpus"; :>> method = VerificationMethod::inspect; :>> procedureText = "A discipline guide + validator toolchain let an AI agent orient->execute->validate->record->commit autonomously: CLAUDE.md (the discipline), .githooks/pre-commit (rust validate + 9 forward guards), and the `sysmlv2` CLI provide the loop. (The requirement names the retired validate_all.py; the Rust authority D0048 superseded it — capability preserved.) Inspect CLAUDE.md + .githooks/pre-commit; this session's 70+ autonomous sprints are the demonstration."; }
    part sr07VerifyR1 : TestResult { :>> id = "7a1c0007-0007-4e07-9a07-5162738400a7"; :>> outcome = VerdictKind::pass; :>> judgedAgainst = "0941e97"; :>> judgedAt = "2026-06-21"; :>> judgedBy = "claudeOpus"; }
    // R2 (A1 re-verify at HEAD): the deliverable source drifted since R1; the reverify gate (cargo test --workspace --release + clippy -D warnings, target/reverify) passed GREEN at edd7b75, and the agent loop (CLAUDE.md + pre-commit + keel CLI) is in active use this sitting. Claim holds; refreshed.
    part sr07VerifyR2 : TestResult { :>> id = "7a1c0007-0007-4e07-9a07-5162738400c7"; :>> outcome = VerdictKind::pass; :>> judgedAgainst = "edd7b75"; :>> judgedAt = "2026-06-25"; :>> judgedBy = "claudeOpus"; }
    #Verify dependency from sr07Verify to sr07AgentLoop;

    verification sr08Verify : Test { :>> id = "7a1c0008-0008-4e08-9a08-516273840008"; :>> title = "Verify sr08TraceQuery"; :>> createdAt = "2026-06-21"; :>> createdBy = "claudeOpus"; :>> method = VerificationMethod::test; :>> procedureText = "A query traces a Need forward to its satisfying SystemRequirements from satisfy edges in text: `sysmlv2 trace-need n01AtomicItems .` returns the satisfy-edge trace JSON (confirmed live). Re-run: `sysmlv2 trace-need <need>`."; }
    part sr08VerifyR1 : TestResult { :>> id = "7a1c0008-0008-4e08-9a08-5162738400a8"; :>> outcome = VerdictKind::pass; :>> judgedAgainst = "0941e97"; :>> judgedAt = "2026-06-21"; :>> judgedBy = "claudeOpus"; }
    #Verify dependency from sr08Verify to sr08TraceQuery;

    verification sr09Verify : Test { :>> id = "7a1c0009-0009-4e09-9a09-516273840009"; :>> title = "Verify sr09SelfBuild"; :>> createdAt = "2026-06-21"; :>> createdBy = "claudeOpus"; :>> method = VerificationMethod::analyze; :>> procedureText = "The system tracks its own construction using its own process+schema, so .tracking/ IS the primary process-correctness evidence: 200+ done tasks across 70+ sprints in .tracking/delivery/, each with ceremony gates + DoD TestResults, all under the engine's own schema. Analyze: `sysmlv2 orient` done count + .tracking/delivery/."; }
    part sr09VerifyR1 : TestResult { :>> id = "7a1c0009-0009-4e09-9a09-5162738400a9"; :>> outcome = VerdictKind::pass; :>> judgedAgainst = "0941e97"; :>> judgedAt = "2026-06-21"; :>> judgedBy = "claudeOpus"; }
    #Verify dependency from sr09Verify to sr09SelfBuild;

    verification sr10Verify : Test { :>> id = "7a1c0010-0010-4e10-9a10-516273840010"; :>> title = "Verify sr10RustCli"; :>> createdAt = "2026-06-21"; :>> createdBy = "claudeOpus"; :>> method = VerificationMethod::test; :>> procedureText = "A Rust CLI binary performs parse/validate/orient/trace-need without JVM/conda/Jupyter: target/release/sysmlv2 runs all of these natively (used throughout this session, no kernel); cargo test -p sysmlv2-cli green. Re-run: `sysmlv2 validate|orient|trace-need` with no conda env active."; }
    part sr10VerifyR1 : TestResult { :>> id = "7a1c0010-0010-4e10-9a10-5162738400b0"; :>> outcome = VerdictKind::pass; :>> judgedAgainst = "0941e97"; :>> judgedAt = "2026-06-21"; :>> judgedBy = "claudeOpus"; }
    // R2 (A1 re-verify at HEAD): the reverify gate passed GREEN at edd7b75 (cargo test --workspace --release + clippy); the Rust CLI (parse/validate/orient, no JVM) is in active use this sitting. Claim holds; refreshed.
    part sr10VerifyR2 : TestResult { :>> id = "7a1c0010-0010-4e10-9a10-5162738400c0"; :>> outcome = VerdictKind::pass; :>> judgedAgainst = "edd7b75"; :>> judgedAt = "2026-06-25"; :>> judgedBy = "claudeOpus"; }
    #Verify dependency from sr10Verify to sr10RustCli;

    // sr11FastStart: target revised by D0083 (parse/validate < 500ms + full orient-with-suspicion
    // < 1.5s) after orientPerf (Sprint 74) cut orient 13.6s -> ~0.85s. Now VERIFIED against the
    // realistic bars; n11FastStart verifies transitively.
    verification sr11Verify : Test { :>> id = "7a1c0011-0011-4e11-9a11-516273840011"; :>> title = "Verify sr11FastStart (D0083 revised bars)"; :>> createdAt = "2026-06-21"; :>> createdBy = "claudeOpus"; :>> method = VerificationMethod::test; :>> procedureText = "FastStart, D0083 two-bar target: parse/validate < 500ms AND full orient (with git-temporal suspicion) < 1.5s. MEASURED live (5+ runs, cold, this developer laptop / Windows): `sysmlv2 validate .` ~100-117ms (< 500ms); `sysmlv2 orient .` ~0.85-1.0s (< 1.5s) after orientPerf's batched git. Both bars met. Re-run: time `sysmlv2 validate .` and `sysmlv2 orient .`."; }
    part sr11VerifyR1 : TestResult { :>> id = "7a1c0011-0011-4e11-9a11-5162738400b1"; :>> outcome = VerdictKind::pass; :>> judgedAgainst = "324ab15"; :>> judgedAt = "2026-06-21"; :>> judgedBy = "claudeOpus"; }
    // R2 (D0084): re-verify after element-content suspicion flagged sr11Verify stale — sr11's statement
    // was amended (D0083) AFTER R1's commit (324ab15). Re-judged at 96584de where the statement is
    // stable and matches this evidence. Demonstrates the re-verify-on-change loop end to end.
    part sr11VerifyR2 : TestResult { :>> id = "7a1c0011-0011-4e11-9a11-5162738400b2"; :>> outcome = VerdictKind::pass; :>> judgedAgainst = "96584de"; :>> judgedAt = "2026-06-21"; :>> judgedBy = "claudeOpus"; }
    // R3 (B1 charterDebtGateCoverage re-verify at HEAD): the source drifted since R2, leaving sr11/n11 the
    // last charter-debt (uncovered) pair. Re-measured at HEAD (D0083 two-bar target): keel validate ~88-118ms
    // (< 500ms) AND keel orient ~0.86-1.12s (< 1.5s) over 4 runs (subprocess-timed, incl. spawn overhead).
    // Both bars met; FastStart holds. Re-run: time `keel validate .` + `keel orient .`.
    part sr11VerifyR3 : TestResult { :>> id = "7a1c0011-0011-4e11-9a11-5162738400c1"; :>> outcome = VerdictKind::pass; :>> judgedAgainst = "a342cac"; :>> judgedAt = "2026-06-25"; :>> judgedBy = "claudeOpus"; }
    #Verify dependency from sr11Verify to sr11FastStart;

    verification sr12Verify : Test { :>> id = "7a1c0012-0012-4e12-9a12-516273840012"; :>> title = "Verify sr12DenyWarnings"; :>> createdAt = "2026-06-21"; :>> createdBy = "claudeOpus"; :>> method = VerificationMethod::test; :>> procedureText = "The crates compile under #![deny(warnings, clippy::all, pedantic, nursery)] with no unwrap/expect/index-without-bounds in src/ outside tests: `cargo clippy --workspace --all-targets` is green at HEAD (the lints are declared in main.rs/lib.rs and enforced in pre-commit). Re-run: cargo clippy --workspace --all-targets -- -D warnings."; }
    part sr12VerifyR1 : TestResult { :>> id = "7a1c0012-0012-4e12-9a12-5162738400b2"; :>> outcome = VerdictKind::pass; :>> judgedAgainst = "0941e97"; :>> judgedAt = "2026-06-21"; :>> judgedBy = "claudeOpus"; }
    // R2 (A1 re-verify at HEAD): the reverify gate ran `cargo clippy --workspace --all-targets -- -D warnings` GREEN at edd7b75 — the #![deny(warnings, pedantic, nursery)] lint floor holds. Refreshed.
    part sr12VerifyR2 : TestResult { :>> id = "7a1c0012-0012-4e12-9a12-5162738400c2"; :>> outcome = VerdictKind::pass; :>> judgedAgainst = "edd7b75"; :>> judgedAt = "2026-06-25"; :>> judgedBy = "claudeOpus"; }
    #Verify dependency from sr12Verify to sr12DenyWarnings;

    verification sr13Verify : Test { :>> id = "7a1c0013-0013-4e13-9a13-516273840013"; :>> title = "Verify sr13SpecPin"; :>> createdAt = "2026-06-21"; :>> createdBy = "claudeOpus"; :>> method = VerificationMethod::inspect; :>> procedureText = "build.rs embeds the canonical SysML v2 spec URL + pinned grammar SHA as compile-time constants and verifies the fetched manifest's SHA-256 (fail on divergence; SYSML_V2_SPEC_OFFLINE=1 skips): sysmlv2-parser/build.rs defines SYSML_V2_SPEC_URL + SYSML_V2_GRAMMAR_SHA + sha256_hex check (inspected). Inspect sysmlv2-parser/build.rs."; }
    part sr13VerifyR1 : TestResult { :>> id = "7a1c0013-0013-4e13-9a13-5162738400b3"; :>> outcome = VerdictKind::pass; :>> judgedAgainst = "0941e97"; :>> judgedAt = "2026-06-21"; :>> judgedBy = "claudeOpus"; }
    // R2 (A1 re-verify at HEAD): the reverify gate (cargo test --workspace --release) built GREEN at edd7b75 — build.rs still embeds + checks the pinned SysML v2 spec SHA (inspected; unchanged). Refreshed.
    part sr13VerifyR2 : TestResult { :>> id = "7a1c0013-0013-4e13-9a13-5162738400c3"; :>> outcome = VerdictKind::pass; :>> judgedAgainst = "edd7b75"; :>> judgedAt = "2026-06-25"; :>> judgedBy = "claudeOpus"; }
    #Verify dependency from sr13Verify to sr13SpecPin;

    verification sr14Verify : Test { :>> id = "7a1c0014-0014-4e14-9a14-516273840014"; :>> title = "Verify sr14TddBdd"; :>> createdAt = "2026-06-21"; :>> createdBy = "claudeOpus"; :>> method = VerificationMethod::test; :>> procedureText = "Parser/semantic behavior is covered by cucumber-rs BDD + proptest property tests, and CI enforces cargo test + clippy green: the BDD feature files + proptest strategies exist in the crates and `cargo test --workspace` passes (28 + 31 + scenario suites). Re-run: cargo test --workspace."; }
    part sr14VerifyR1 : TestResult { :>> id = "7a1c0014-0014-4e14-9a14-5162738400b4"; :>> outcome = VerdictKind::pass; :>> judgedAgainst = "0941e97"; :>> judgedAt = "2026-06-21"; :>> judgedBy = "claudeOpus"; }
    #Verify dependency from sr14Verify to sr14TddBdd;

    // serve console SR verification (serve redesign). sr17 (directed-only) is MET by Sprint 150; sr15/
    // sr16/sr18/sr19 remain unverified (unbuilt) — honest burndown gaps (D0098), no fake passes.
    verification sr15Verify : Test { :>> id = "7a1c0015-0015-4e15-9a15-516273840015"; :>> title = "Verify sr15ServeIntrospect"; :>> createdAt = "2026-06-24"; :>> createdBy = "claudeOpus"; :>> method = VerificationMethod::test; :>> procedureText = "Live introspection with recency: (1) current state computed live — the orient tab + the D0098 burndown block; (2) decisions newest-first with full context — the Decisions tab sorts newest-first (dNNNN desc) + the item modal shows every authored attr (context/decision/rationale/consequences); (3) git-derived recent-activity timeline — NEW `keel recent` (git log of the latest commits touching .tracking/.engine + the element files each changed, newest first) surfaced as the console Recent tab via GET /api/recent. VERIFIED (live): `keel recent .` = 25 commits; GET /api/recent = 25 commits; console / has the Recent tab; clippy + keel validate + guard all (12) green. Re-run: `keel recent .`; curl /api/recent; grep console.html for the Recent tab."; }
    part sr15VerifyR1 : TestResult { :>> id = "7a1c0015-0015-4e15-9a15-5162738400b5"; :>> outcome = VerdictKind::pass; :>> judgedAgainst = "744ffe4"; :>> judgedAt = "2026-06-24"; :>> judgedBy = "claudeOpus"; }
    #Verify dependency from sr15Verify to sr15ServeIntrospect;
    verification sr16Verify : Test { :>> id = "7a1c0016-0016-4e16-9a16-516273840016"; :>> title = "Verify sr16ServeCritiqueLoop"; :>> createdAt = "2026-06-24"; :>> createdBy = "claudeOpus"; :>> method = VerificationMethod::test; :>> procedureText = "The critique loop closes in-console: (1) a directed Critique records each finding as a severity-carrying Issue linked to the element (the element-critique skill via the bridge); (2) a >=Medium finding requires a typed human disposition (Findings tab / Act-Accept-risk-Dismiss -> /api/disposition, D0092); (3) ACT ATTACHES A RESOLVER — POST /api/resolver creates a `<finding>Fix` action in the backlog (NextWork) + a #Resolves edge (write::add_task + append_resolves_edge), verified LIVE: POST {finding:issue046} -> {ok:true,resolver:issue046Fix} wrote the action + edge (then reverted); the implementation is then done by the process-aware agent/human and (4) RE-VERIFIED by re-running Critique on the element; (5) an unresolved/failed critique induces suspicion until resolved (critique_suspect, D0086). Re-run: POST /api/resolver on a finding -> resolver action + #Resolves edge appear; re-Critique clears suspicion when clean."; }
    part sr16VerifyR1 : TestResult { :>> id = "7a1c0016-0016-4e16-9a16-5162738400b6"; :>> outcome = VerdictKind::pass; :>> judgedAgainst = "21c7c7c"; :>> judgedAt = "2026-06-24"; :>> judgedBy = "claudeOpus"; }
    #Verify dependency from sr16Verify to sr16ServeCritiqueLoop;
    verification sr17Verify : Test { :>> id = "7a1c0017-0017-4e17-9a17-516273840017"; :>> title = "Verify sr17ServeDirectedNoChat"; :>> createdAt = "2026-06-24"; :>> createdBy = "claudeOpus"; :>> method = VerificationMethod::inspect; :>> procedureText = "The console provides NO free-form AI chat surface and every AI action is directed at a named element + records an artifact: the Agent tab + the free action/target runner + runAgent were removed from console.html (grep 'agent,Agent' / 'Run agent' / 'Investigate' = 0); the only AI action is the modal Critique on a named element (records Issues via the element-critique skill). Defense-in-depth: GET /api/agent/stream rejects any action != critique with a clear message (verified live: action=investigate -> 'only the critique action is supported'). Re-run: grep console.html; curl '/api/agent/stream?action=investigate&target=x' -> error event."; }
    part sr17VerifyR1 : TestResult { :>> id = "7a1c0017-0017-4e17-9a17-5162738400b7"; :>> outcome = VerdictKind::pass; :>> judgedAgainst = "67273fa"; :>> judgedAt = "2026-06-24"; :>> judgedBy = "claudeOpus"; }
    #Verify dependency from sr17Verify to sr17ServeDirectedNoChat;
    verification sr18Verify : Test { :>> id = "7a1c0018-0018-4e18-9a18-516273840018"; :>> title = "Verify sr18ServeSectionCritique"; :>> createdAt = "2026-06-24"; :>> createdBy = "claudeOpus"; :>> method = VerificationMethod::test; :>> procedureText = "The console renders a BOUNDED SECTION and records section-scoped critique against its elements: (1) NEW `view::section_json` + GET /api/section?view=NAME|element=NAME returns {seed,kind,count,items[],edges[]} — a declared view's element set OR an element + its 1-hop typed-edge neighbourhood (induced subgraph: only edges with both endpoints in-section). VERIFIED LIVE: ?element=sr18ServeSectionCritique -> 2 items (sr18 + its satisfy-neighbour n17ServeGranularWhitebox) + the induced satisfy edge; ?view=issues -> 48 items; no-seed/unknown-element -> 400 with a clear error. (2) SECTION-SCOPED critique: AgentReq gains an optional `section` seed; build_agent_prompt names the bounded neighbourhood (section_member_names) so the AI judges the target IN its local context (whole-model views are too coarse), still recording findings against the section's elements via the sr16 critique path. (3) console Section tab: pick a view or element -> render the bounded section (items + edges as itemLinks) -> 'Critique in section' runs the section-scoped critique. Unit tests: element_neighbourhood (element + 1-hop, both directions, stops at 1 hop), section_subgraph_json (induced edges only), parse_section_seed, build_agent_prompt (scoped only with members). clippy -D warnings + cargo test (60 lib) + keel validate + guard all (12) green. Re-run: curl '/api/section?element=<x>'; cargo test -p keel-cli section."; }
    part sr18VerifyR1 : TestResult { :>> id = "7a1c0018-0018-4e18-9a18-5162738400b8"; :>> outcome = VerdictKind::pass; :>> judgedAgainst = "665aa4d"; :>> judgedAt = "2026-06-24"; :>> judgedBy = "claudeOpus"; }
    #Verify dependency from sr18Verify to sr18ServeSectionCritique;
    verification sr19Verify : Test { :>> id = "7a1c0019-0019-4e19-9a19-516273840019"; :>> title = "Verify sr19ServeWhiteboxBoundary"; :>> createdAt = "2026-06-24"; :>> createdBy = "claudeOpus"; :>> method = VerificationMethod::demo; :>> procedureText = "White-box + black-box critique over a defined system boundary (per D0100: boundaries from existing structure not clustering; interconnects are typed edges not ports; no schema change). (1) BOUNDARY = a Need-slice — NEW view::need_slice = Need + satisfying SRs + their allocated Components + verifying Tests, a recursive System-of-Interest; view::cut_edges = the interfaces (edges with exactly one endpoint inside). (2) WHITE-BOX: critique a boundary's internal elements (reuses sr18 section critique + existing CritiqueLens; the console Boundary tab's per-element 'Critique element'). (3) BLACK-BOX: NEW build_blackbox_prompt critiques the cut edges for necessity/minimality/completeness; AgentReq.boundary routes it; findings = Issues referencing each interface (D0100, no port). (4) `keel boundary <need>` + `keel boundary-sweep` (the tier-satisfaction first sweep target, D0098) + GET /api/boundary + /api/boundary-sweep + console Boundary tab (white-box internals, black-box interfaces, sweep table). VERIFIED LIVE: `keel boundary n17ServeGranularWhitebox` -> 4 internal + 4 interfaces (derivedfrom/charteredby cut edges); `keel boundary-sweep` -> 17 Needs with internal/coupling/decomposed/srs_verified; non-Need seed -> clear 400; /api/boundary + /api/boundary-sweep serve. Unit tests: need_slice, cut_edges, boundary_emit_json, build_blackbox_prompt. clippy -D warnings + cargo test (64 lib) + keel validate (169) + guard all (12) green. Re-run: `keel boundary <need>`; `keel boundary-sweep`; cargo test -p keel-cli boundary."; }
    part sr19VerifyR1 : TestResult { :>> id = "7a1c0019-0019-4e19-9a19-5162738400b9"; :>> outcome = VerdictKind::pass; :>> judgedAgainst = "0fd9d32"; :>> judgedAt = "2026-06-24"; :>> judgedBy = "claudeOpus"; }
    #Verify dependency from sr19Verify to sr19ServeWhiteboxBoundary;
}
