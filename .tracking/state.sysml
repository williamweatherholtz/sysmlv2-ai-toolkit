// =====================================================================
// state.sysml — RETIRED by D0045 (2026-06-16).
// The StateCursor hand-maintained pointer is gone. Orient now computes
// sprint ceremony status directly from delivery file TestResults.
// File retained as a tombstone so git history references are traceable.
// =====================================================================
package ProjectState {
    // no parts — StateCursor retired
}
