// Per-actor issues records for claudeOpus5 (issue210/srDcPerActorWriteTargets): new records
// route here so concurrent contributors never conflict at a shared append anchor.
package IssuesClaudeOpus5 {
    private import EngineElement::*;
    private import EngineWork::*;
    private import EngineVerification::*;
    private import EngineRelationships::*;

    part issue292 : Issue {
        :>> id = "cea7937f-97e0-4482-8a06-4cbfddb8aa79";
        :>> title = "the shipped reference decision copy is parsed as instance data, importing 235 foreign attestations and 236 unresolvable evidence SHAs";
        :>> createdAt = "2026-08-27";
        :>> createdBy = "claudeOpus5";
        :>> description = "keel init remaps the engine's 236 decisions to .engine/reference/decisions/ and Sprint 104's record states they are NOT scanned as instance - the rust views scan .engine/decisions. That was never true: collect_sysml (lib.rs:75) has no exclusions, so the reference copy has always been parsed and registered into the downstream project's model. Sprint 104 implemented the PATH remap and not the scanning boundary it declared. Measured in a fresh init fixture: the downstream model contains 235 TestResults judged by wweatherholtz - keel's human, not a stakeholder of that project - and 236 judgedAgainst SHAs that do not resolve in that repository (sampled e146621: 'Not a valid object name'). So every downstream project's verification surface is inflated with another project's human attestations, and its evidence chain contains 236 references that D0129 requires to resolve and which cannot. D0237 fixed the symptom this surfaced (the package collision on the first recorded decision) and deliberately did not fix this. Note the constraint on any fix: .engine/rules/rules.sysml carries 10 real #JustifiedBy edges to dNNNN targets, so the reference copy cannot simply be dropped from the walk - the edges would dangle. Aggravating, and the reason this shipped: both gates covering init (sprint 104's live check and sprint 115's init smoke test) assert init-then-validate and never record a fact, which is the one state in which every defect in this class is invisible.";
        :>> discoveredInField = true;
        :>> severity = Severity::High;
    }
    #Resolves dependency from scopeReferenceCopyOutOfTheInstanceModel to issue292;

    part issue293 : Issue {
        :>> id = "42488fde-9b75-44e7-b5e4-c83032b5fed4";
        :>> title = "keel activate/deactivate rewrites activation.toml and loses charteredBy plus non-switchable processes";
        :>> createdAt = "2026-08-27";
        :>> createdBy = "claudeOpus5";
        :>> description = "Found because the KEYSTONE LOCK refused a commit, which is the control working exactly as designed: I ran `keel deactivate knowledge-graph-memory` and `keel activate knowledge-graph-memory` to verify a kill switch, believed I had restored the file, and the pre-commit gate reported a locked-file change with no co-committed Decision. The diff showed two losses from one round trip. (1) `charteredBy = 'd0226'` was DELETED along with its explanatory comment - that is the D0225 charter reference, and the comment it removed says a set without a charter is a collection of switches nobody can account for. (2) `decision-authoring` was dropped from `active`, because it is reported `[always]` (asserts no guard, nothing to switch off) and the writer emits only switchable processes. The second is a semantic change, not untidiness: an ABSENT section means everything is active (D0138/D0164), but a PRESENT list naming 10 of 11 processes means the 11th is INACTIVE - so silently omitting a process from a list that exists can deactivate it. Both losses are in a file under the keystone lock, so any legitimate use of `keel activate` now either loses these facts or requires a signed Decision to re-add them, which is a write path fighting its own control. Nothing detected either loss; the lock detected the FILE changing.";
        :>> discoveredInField = true;
        :>> severity = Severity::High;
    }
    #Resolves dependency from activateDoesNotLoseFacts to issue293;

    part issue294 : Issue {
        :>> id = "08e84944-fdf2-467b-8575-cd7456e119dc";
        :>> title = "four-letter domain words never seed recall: they are dropped for length before frequency is consulted";
        :>> createdAt = "2026-08-28";
        :>> createdBy = "claudeOpus5";
        :>> description = "A prompt token shorter than five characters is dropped for LENGTH before its corpus frequency is ever consulted (prompt_tokens), so four-letter DOMAIN words never seed recall: gate, hook, land, push, view. Five-letter hooks seeds and four-letter hook does not, which is arbitrary from the reader side and cannot be predicted by anyone using it. The five-character floor exists because a four-character floor admits been, does, made, that and this, and the English function-word list was sized against the longer floor. Found because a unit test asserted that gate would be dropped as TOO COMMON and it was instead dropped as TOO SHORT - the test premise was wrong, not the code, and nothing else would have surfaced it. Severity Medium rather than High: the identifier path and longer synonyms still work, so this narrows recall rather than breaking it, and the eight-case comparison gives a way to measure any fix instead of guessing.";
        :>> discoveredInField = true;
        :>> severity = Severity::Medium;
    }
    #Resolves dependency from shortDomainWordsCanSeed to issue294;

    part issue295 : Issue {
        :>> id = "a97e2219-d1db-4a5e-b771-cc25bcecdd33";
        :>> title = "recall never indexes body text, and its ranker is alphabetical in 43 of 50 cases";
        :>> createdAt = "2026-08-28";
        :>> createdBy = "claudeOpus5";
        :>> description = "Found by an adversarial panel (IR-fundamentals lens), confirmed against the code. seeds_for matches an item's name, its title and an Alias term - nothing else - so the five body fields the same module reads for DISPLAY (decision, description, rationale, actionText, consequences) are invisible to RETRIEVAL. Demonstrated: a prompt about provenance and defaulted dates contributed ZERO seeds for `provenance`, the most informative word in it, because it appears in dozens of bodies and in no name or title. Second defect, structural: agreement is the primary sort key but reaches max 1 in 43 of 50 bench cases, so the key is constant and ranking degenerates to (hops, name) - alphabetical - which is precisely the failure the agreement comment says it was introduced to fix. MAX_PROMPT_WORDS caps votes at three and the rarity ceiling removes the mid-frequency words most likely to co-occur, so the vote can rarely happen. BM25 measured on the SAME fields scores 37/50 (74%) hit@20 versus the shipped 24/50 (48%); the field ceiling is 44/50. SQLite FTS5 provides bm25() as its default ranking function, so rejecting BM25 while proposing SQLite was incoherent. The lexical layer is not exhausted, it is barely attempted.";
        :>> discoveredInField = true;
        :>> severity = Severity::High;
    }
    #Resolves dependency from recallIndexesBodiesAndRanksProperly to issue295;

    part issue296 : Issue {
        :>> id = "a5088939-bd58-4cba-8321-462d35171f70";
        :>> title = "the recall benchmark's control was a strawman, precision was never measured, and the 14-point gap is not significant";
        :>> createdAt = "2026-08-28";
        :>> createdBy = "claudeOpus5";
        :>> description = "Found independently by two panel lenses and confirmed by re-running the harness. The control matches name and title only while queries are drawn from BODY_FIELDS, so it was structurally denied the field the queries came from; with bodies included the same rarest-word control scores 50/50 and real git grep 14/15 - both themselves leakage, since queries are verbatim body words. The harness cannot discriminate in either direction, so the 48%-vs-34% result carries no information and should not have been used to ship anything. Worse for a PUSH feature: precision was never measured at all, and sampling 17 realistic prompts put it near 9% - one of eleven pushes topical. The 2x2 is 13 both / 11 KG-only / 4 grep-only / 22 neither, giving McNemar exact p = 0.119 and a net advantage of 7 cases rather than 24. And the harness carries a dead statistic (`both`, always false, never printed), which is evidence it went unreviewed while being the sole evidence for a proposal to delete the subsystem.";
        :>> discoveredInField = true;
        :>> severity = Severity::High;
    }
    #Resolves dependency from recallBenchmarkCanDiscriminate to issue296;

    part issue297 : Issue {
        :>> id = "99351a32-1e98-4479-8cdb-fb0e676ad5b9";
        :>> title = "three surfaces still assert a confidence gate that has not existed since it was removed, including a passing DoD";
        :>> createdAt = "2026-08-28";
        :>> createdBy = "claudeOpus5";
        :>> description = "confident() discards all four parameters and returns seed_count > 0, so the only silenced prompts are those with no informative token - already rejected upstream by prompt_tokens. The gate is gone; its prose is not. The main.rs doc comment still lists kill switch 3 as 'a LOW-confidence prompt is not injected at all'; the PASSING kgPromptPathInjects DoD still reads 'Injection is gated on a CONFIDENCE verdict - silence beats noise'; and the printed HIGH/LOW label is unreachable at LOW whenever any row is shown, so it carries no information while reading as though it does - the panel observed 'confidence HIGH' stamped on a payload 14 of whose 17 rows were off-topic. This is the fourth instance this session of prose asserting a property the code lacks, and the first where I wrote both the prose and the code within two commits. Same class, also in my own comments: the ceiling described as '~60' when it computes to 68, `gate` counted as 5,736 on one line and 5,806 on another, and the ceiling credited with dropping `gate` when the length rule drops it first.";
        :>> discoveredInField = true;
        :>> severity = Severity::Medium;
    }
    #Resolves dependency from retireTheConfidenceProse to issue297;

    part issue298 : Issue {
        :>> id = "eaf25067-5cbe-4026-806d-7199dad74d6c";
        :>> title = "D0243 changed an accepted process's meaning with no marker and without editing the process definition";
        :>> createdAt = "2026-08-28";
        :>> createdBy = "claudeOpus5";
        :>> description = "Found by the source-fidelity panel lens and confirmed: D0243 carries ZERO #ProspectiveChange/#SafetyChange markers where its sibling D0242 carries two, and .engine/processes/knowledge-graph-memory.sysml mentions neither Decision. Yet D0243 declared '.knowledge/ an optional refinement rather than a prerequisite' and rejected 'require a curated subject vocabulary, AS THE SOURCE PROCESS'S STEPS 1-2 IMPLY' - i.e. it changed what two accepted, human-owned steps mean. The keystone lock did not fire because the guarded artifact was never edited: the amendment was made AROUND the control rather than through it. D0161 had already written the rule broken here - 'A design may amend a process; it may not quietly disagree with one.' The substance of D0243 is sound and measured; the governance is not, and a guard that only notices edits cannot notice a disagreement.";
        :>> discoveredInField = true;
        :>> severity = Severity::High;
    }
    #Resolves dependency from processAmendmentsReachTheDefinition to issue298;

    part issue299 : Issue {
        :>> id = "4ed10cb4-e5ab-45ce-8cdd-3f4931ddb75a";
        :>> title = "identifier seeding fails on three of six natural spellings, and it is the one path measured to work";
        :>> createdAt = "2026-08-28";
        :>> createdBy = "claudeOpus5";
        :>> description = "Confirmed by the panel and reconfirmed directly: `d0242`, `issue294` and `what does D0242 say` seed correctly, while `issue 294`, `D-0242` and `decision 242` push nothing at all - is_identifier_token requires the digit run to abut the prefix with no separator. Both the cost-benefit and IR lenses independently named identifier lookup as the feature's genuine value (`keel why d0133` returns the decision, its acceptance Test, its TestResult and file paths - precise and provenance-carrying, which grep does not give), and the cost-benefit lens recommends making it the ONLY injection trigger. Under that recommendation this brittleness becomes the system's whole failure rate rather than a corner case.";
        :>> discoveredInField = true;
        :>> severity = Severity::Medium;
    }
    #Resolves dependency from identifierMatchingAcceptsNaturalSpellings to issue299;

    part issue300 : Issue {
        :>> id = "7eabeb2d-2325-4276-94e7-d1acffa3961d";
        :>> title = "The intake write path accepts 12 of the schema's 15 ImplicationKind members";
        :>> createdAt = "2026-08-28";
        :>> createdBy = "claudeOpus5";
        :>> description = "Found 2026-08-28 while triaging st023. schema/core/intake.sysml:39-59 declares 15 ImplicationKind members. keel-cli/src/intake_write.rs:57 hardcodes a 12-element allowlist that omits verifiedRequirement, designChange and implementationChange - the three members the schema comments call out as deliberately RENAMED or added, and which .engine/processes/intake.sysml:36 and both copies of the intake SKILL.md instruct the triager to use. A real story of mine was refused today for using designChange, which is the correct member for it. THE HARM IS THE ONE THE PROCESS EXISTS TO PREVENT: intake.sysml says a kind the vocabulary cannot express is a CHANGE to the vocabulary and never a forced fit, so a triager following the skill hits a refusal and the path of least resistance is to force-fit into architecture or bug - a wrong triage, which the skill states is worse than an absent one because it routes real direction to the wrong place and looks handled. THIS IS THE issue119/issue120 CLASS, EXACTLY. That pair was resolved by building schema.rs so the binary reads its vocabulary from the schema instead of restating it: KNOWN_EDGES mirrored EdgeKind, ENGINE_MARKERS mirrored the metadata defs, RISK_ORDER mirrored the severity enum. IMPLICATIONS is a fourth constant of the same kind that was written after the fix and did not use it. FIX: read ImplicationKind from schema/core/intake.sysml through schema.rs, as the other three vocabularies already are, so the allowlist cannot drift again; a downstream project that extends the enum then works without a binary change. CONTROL: the schema-vocabulary guard should assert that every vocabulary the binary validates against is schema-sourced, so a fifth hardcoded list is a red gate rather than a discovery.";
        :>> discoveredInField = false;
        :>> severity = Severity::High;
    }
    #Resolves dependency from dcIntakeHasAWritePath to issue300;

    part issue301 : Issue {
        :>> id = "1d8bfa7a-ed75-4621-97c0-26d9f901c859";
        :>> title = "The unit manifest carries machine-absolute path keys, and publishing it to a shared library would break every other machine";
        :>> createdAt = "2026-08-28";
        :>> createdBy = "claudeOpus5";
        :>> description = "Found 2026-08-28 while committing the intake-vocabulary fix. .engine/contracts/installed-units.toml records per-file content hashes keyed by path, and four keys under the decision-channel unit are MACHINE-ABSOLUTE: file.C:__SL__Users__SL__WilliamWeatherholtz__SL__claude_code__SL__sysmlv2-ai-toolkit__SL__.github__SL__scripts__SL__record_decision.sh and three siblings. Every other key in the file is repository-relative (file.processes__SL__intake.sysml). WHY THIS IS NOW URGENT RATHER THAN LATENT: D0250 makes the library a git REPOSITORY that other machines clone. A committed manifest naming this machine's home directory was previously an ugliness confined to one tree; published to a library that a second machine pulls, the keys resolve to nothing there, so the three-way merge that D0183 relies on compares against files it cannot find. The defect is in the one file whose entire purpose is portability. FIX: keys are repository-relative always; a unit-extras entry outside the project root is either rejected at export or recorded relative to a declared anchor, never absolutised. VERIFY: a unit exported on one machine and imported on another reconciles by hash with no path rewriting; a manifest containing an absolute key fails a check rather than being silently tolerated.";
        :>> discoveredInField = false;
        :>> severity = Severity::High;
    }
    #Resolves dependency from storyLibraryManifestIntegrity to issue301;

    part issue302 : Issue {
        :>> id = "b54cc34a-5c24-4ed6-8df5-2b329b9582e7";
        :>> title = "Unit versions bump with no content change, so every update decision reads as noise";
        :>> createdAt = "2026-08-28";
        :>> createdBy = "claudeOpus5";
        :>> description = "Found 2026-08-28 while committing. The intake unit in .engine/contracts/installed-units.toml went version 42 -> 43 during a session in which none of its three recorded file hashes changed, and the file churns in essentially every recent commit. A version that moves without content moving is a FALSE UPDATE SIGNAL. WHY IT MATTERS MORE UNDER D0250: import --update decides on version, and srActivatedUnitVersionIsPinned makes a project's recorded unit version the thing that does not move until an explicit update. Once the library is a repository other machines pull, a project deciding whether to take an update reads a number that changes for reasons unrelated to content - so the honest answer to should I update becomes unavailable exactly where it starts to matter. This also interacts with the no-op churn: a manifest rewritten every commit makes the diff useless as a review surface for what actually moved. FIX: the version advances only when at least one recorded file hash changes; a re-stamp that finds identical hashes leaves the version alone. VERIFY: re-running the stamping path twice with no edits leaves installed-units.toml byte-identical; a single file edit advances exactly that unit's version and no other.";
        :>> discoveredInField = false;
        :>> severity = Severity::Medium;
    }
    #Resolves dependency from storyLibraryManifestIntegrity to issue302;

    part issue303 : Issue {
        :>> id = "5c15d85a-35ca-41dc-a133-f5f9e99ffba7";
        :>> title = "Eight of nine controls are classified unprobeable by a VIEW's constraints, and read as unverifiable";
        :>> createdAt = "2026-08-29";
        :>> createdBy = "claudeOpus5";
        :>> description = "Found 2026-08-29 while answering a demand for REAL assurance. keel controls reports 9 declared controls: 1 ARMED, 8 not-machine-checkable, with uncoveredHazards [] and hazardsWithADisarmedControl [] - a clean bill of health resting on ONE probe. Each reason in control-arming.toml is individually careful, and the AGGREGATE is the issue240 failure at a higher level: truthful on the question asked, misleading on the question a reader has. THE SHARED ERROR: not-machine-checkable BY A READ-ONLY VIEW was generalised into not checkable at all. keel controls must not spawn processes, write files or make network calls, so it genuinely cannot establish most of these. A TEST may do all three. The arming question was answered against the constraints of the surface that happened to ask it, not against whether the property is verifiable. PROVEN ON THE FIRST ONE TRIED: ctlWriteLock was classified nothing to probe on the reasoning that no configuration can disarm it. That rules out being DISARMED and says nothing about whether the lock SERIALISES - and issue184/issue185 record four concurrent writers landing two issues with all four exiting 0, a day on which the same reasoning was equally true. A 30-line integration test with six real concurrent processes now proves it: all six land, all six exit 0, six distinct ids. The control is genuinely armed, and now demonstrably so rather than assumed. REMAINING, each needing its own probe rather than a reclassification: ctlPrePushBehind (a two-clone fixture can attempt a push - audit-history already built one), ctlReverify (run it against a fixture), ctlPreWriteTiers (invoke the hook, assert it denies), ctlFireLedger, ctlAuditHistory, ctlBranchProtection, ctlReleaseGateJob. FIX: a third arming state - proven-by-test, distinct from both checkable-by-view and not-checkable - plus a probe per control that admits one. The control-arming contract gains provenBy naming the test, so a reader can re-derive rather than trust the reason text.";
        :>> discoveredInField = false;
        :>> severity = Severity::High;
    }
    // RE-POINTED 2026-08-29 (D0255). It pointed at sprint 485, whose DoD said it resolved issue303
    // 'in part' - and resolution is COMPUTED from resolver completion, which has no partial state, so
    // a passing DoD closed an issue whose own closeOut gate said it stays open. The prose asserted a
    // nuance the computation cannot see. The resolver is now the OPEN task that actually finishes it.
    #Resolves dependency from dcProveTheRemainingControls to issue303;

    part issue304 : Issue {
        :>> id = "a3f95a97-c977-483f-b288-fda52817697f";
        :>> title = "The control map has never been reconciled against the enforcement the binary implements";
        :>> createdAt = "2026-08-29";
        :>> createdBy = "claudeOpus5";
        :>> description = "Found 2026-08-29 (D0254 clause C). The control map declared NINE controls. The launcher's dirty-tree refusal - implemented in launcher::prepare, load-bearing for every Need about bounded process launching, and now proven by test - was not among them; a grep for launch, dirty or singleWriter across .tracking/architecture/control-map.sysml returned nothing. It was found by asking about one mechanism, not by any check. THE CLASS, distinct from the two already named: declared-but-never-fired (D0217) is visible to a reader who looks, and declared-and-unprobeable (D0253) is visible as a classification, but IMPLEMENTED-BUT-UNDECLARED is visible to nobody. keel controls computes the hazard/control diff over DECLARED controls and DECLARED hazards, so an undeclared control cannot appear as a gap, and neither can a hazard only that control covers. Worse, the measure improves as the map gets less complete: fewer declared controls with no gaps reads better than more declared controls with gaps. That is the issue088/issue240 shape again - truthful about the question asked, misleading about the question a reader has. NOT ESTIMATED HERE, deliberately: the map has ten entries and the binary has 53 guards, six hook events, a write lock, a launcher, a push gate and a release gate. Putting a guessed number of missing controls in the record would be the habit this whole line of work has been correcting. FIX: reconcile the map against the binary's actual enforcement surface, one mechanism at a time, and make the reconciliation itself a check so the map cannot silently fall behind the code again - the doc-sync shape applied to controls rather than prose.";
        :>> discoveredInField = false;
        :>> severity = Severity::High;
    }
    // RE-POINTED 2026-08-29 (D0255), same cause as issue303 above: sprint 486 declared ONE control
    // and said 'in part'. Sprint 487 reconciles the map against control-events.toml and lands the
    // standing check, which is what actually resolves it.
    #Resolves dependency from storyControlMapReconciled to issue304;

    part issue305 : Issue {
        :>> id = "86fb8720-b9d7-4720-ab17-e94e7d6fd7ed";
        :>> title = "A DoD saying it resolves an issue IN PART closes it outright, because resolution has no partial state";
        :>> createdAt = "2026-08-29";
        :>> createdBy = "claudeOpus5";
        :>> description = "Found 2026-08-29 by reading back the model after two sprints I authored myself. Resolution is COMPUTED from a resolver's completion (D0077): a #Resolves edge plus a passing resolver DoD closes the issue. There is no partial state. I wrote 'RESOLVES issue303 in part' and 'RESOLVES issue304 in part' into two sprint DoDs, and both issues computed as CLOSED the moment those DoDs passed - while each sprint's own closeOut gate said in plain words that the issue STAYS OPEN. Two surfaces of the same model, one computed and one prose, disagreeing, with the computed one winning silently and the prose one being the true statement. THE SHAPE, and it is the recurring one: prose asserting a nuance the computation cannot see. The engine's own rule is that resolution is computed and never a prose RESOLVED note - this is the mirror image, a prose NOT-YET-RESOLVED note that the computation cannot honour. It is also self-serving in the dangerous direction: the issue count went DOWN while the work did not get done, and nothing flagged it. FIX, two parts. (1) An issue's resolver must be an item whose completion actually resolves it; 'in part' is not expressible, so the honest options are to SPLIT the issue or to point the edge at the item that finishes it - both done here for issue303 and issue304. (2) A CONTROL, because this will recur every time a large issue is chipped at: flag a DoD whose text claims partial resolution ('resolves ... in part', 'partially resolves', 'in part') while carrying a #Resolves edge, since that combination is always either a mis-pointed edge or an issue that needs splitting.";
        :>> discoveredInField = false;
        :>> severity = Severity::High;
    }
    #Resolves dependency from storyControlMapReconciled to issue305;

    part issue306 : Issue {
        :>> id = "b7c19dc5-be2c-4ab7-b8c1-c846ed18a4c0";
        :>> title = "The pre-push hook refused every fresh project's bootstrap push of main";
        :>> createdAt = "2026-08-29";
        :>> createdBy = "claudeOpus5";
        :>> description = "Found 2026-08-29 by the ctlPrePushBehind arming probe - a two-clone fixture attempting a REAL push through the REAL .githooks/pre-push - on its first run. The hook fetches origin main to verify behind-ness, and 'git fetch origin main' FAILS when the remote has no main yet; the fail-loud clause (K2) then refuses. So the BOOTSTRAP push - creating main on an empty remote, the first thing every keel init project does after git init and adding a remote - was refused, with a message directing the user to keel land, which would hit the same wall. The hook conflated 'cannot reach the remote' with 'the remote has no main YET'. THE ASYMMETRY THAT CAUSED IT: ref DELETION was already skipped (local_sha all zeros, one line above) while ref CREATION was not (remote_sha all zeros) - half of 'deleting or creating refs is not a behind-ness question' was implemented and the comment claimed both. IN-FIELD because every downstream project hits it: the self-build never did, since main existed on its remote before the hook was installed - the same reason it survived unnoticed. FIX (shipped with this issue, D0256 co-committed per the keystone lock): skip when remote_sha is all zeros, exactly as deletion is skipped. THE SECOND LESSON from the same probe: a PLAIN behind push never reaches this hook at all - git's own client-side fast-forward check refuses it first - so the hook's actual added value is the push git would ACCEPT: a FORCED one. The probe now pushes --force, testing what the control is FOR (the D0129 history-rewrite class) rather than a case git already catches. The arming contract's old claim that this 'can only be established by attempting a push, which a read-only view must not do' was true of the view and false of a test.";
        :>> discoveredInField = true;
        :>> severity = Severity::High;
    }
    // Re-pointed at filing time: the FIX ships with sprint 488, so the resolver is the story that
    // completes now - not the long-running probe task, which would hold a fixed defect open (the
    // inverse of the issue305 trap, where prose held a closed one open).
    #Resolves dependency from storyFourMoreControlsProven to issue306;

    part issue307 : Issue {
        :>> id = "bdee3068-393b-40d7-91f2-8f4ed566e017";
        :>> title = "guard 53 passes a traversal key: relative-with-dotdot escapes the project exactly as an absolute key does";
        :>> createdAt = "2026-08-29";
        :>> createdBy = "claudeOpus5";
        :>> description = "Found 2026-08-29 by the control-propriety panel (pf02, lens classCoverage), by mutating the guard's motivating defect: the class is 'a manifest key that resolves outside the receiving project', and manifest-key-portability checks only the ABSOLUTE members (drive letter, leading slash, tilde). A relative key with traversal segments - file...__SL__..__SL__elsewhere decodes to ../../elsewhere - escapes the project root identically and PASSES. Demonstrated against the predicate by hand. This is the mutation-testing question doing exactly what the research said it would: the guard killed the specimen and three shape-variants, and the fourth variant class slipped. FIX: the same predicate also flags any decoded key containing a '..' path segment; arming re-proven by injection.";
        :>> discoveredInField = false;
        :>> severity = Severity::High;
    }
    #Resolves dependency from storyProprietyRound1 to issue307;

    part issue308 : Issue {
        :>> id = "4ac6c679-4a3e-4b93-844e-4034fa9024c1";
        :>> title = "provenBy is a receipt-shaped testimony: nothing verifies the named test file exists";
        :>> createdAt = "2026-08-29";
        :>> createdBy = "claudeOpus5";
        :>> description = "Found 2026-08-29 by the control-propriety panel (pf33, lens changeRobustness), by construction: no check exists to fail. provenBy = 'a/test/that/never/existed.rs' passes every gate, and so does a stale pointer after a rename. A dangling provenBy is WORSE than none - it is a receipt-shaped testimony sitting in the very contract (control-arming.toml, D0253) that exists to separate receipts from testimonies. The keystone lock authenticates the ACT of writing it, not the CONTENT. FIX: control-map-reconciled (guard 54) additionally resolves every provenBy path in control-arming.toml against the tree; a missing file is a violation naming the entry. The qualitative half - whether the named test actually EXERCISES that control - remains judgment (pf35) and stays with the panel.";
        :>> discoveredInField = false;
        :>> severity = Severity::High;
    }
    #Resolves dependency from storyProprietyRound1 to issue308;

    part issue309 : Issue {
        :>> id = "fb3b9bcd-de99-463e-9205-92423dd4cad1";
        :>> title = "Root extras imported into .engine: the dot heuristic fit the specimen and misplaced everything else";
        :>> createdAt = "2026-08-29";
        :>> createdBy = "claudeOpus5";
        :>> description = "Found 2026-08-29 by the kickoff DEMO, live: importing the exec-summary unit landed templates/ and tests/ under the receiving project's .engine/ - inert, in the wrong place, while reporting '5 file(s) from upstream'. restore_dst inferred repo-residence from a LEADING DOT, which fit the only extras that existed when it was written (.github/workflows, the decision-channel unit) and misplaced every dotless root extra. The pf02 overfit class, verbatim: the rule killed the specimen and none of its variants. FIX: residence travels WITH the bundle - export writes the unit's declared extras (repo-relative) into unit.toml, and restore_dst_with restores a declared extra where it lived; the dot rule stays as the fallback so pre-extras bundles import exactly as before. Both import loops thread the same list (two loops with one rule between them being the recorded cause of the LAST placement defect). CONTROL: a unit test pins declared-extra-at-root, engine-file-under-.engine, dot-fallback, and no-declaration-old-behaviour. Proven live: re-published, re-imported, extras restored at the demo project's root.";
        :>> discoveredInField = true;
        :>> severity = Severity::High;
    }
    #Resolves dependency from storyKickoffReady to issue309;

    part issue310 : Issue {
        :>> id = "cf924c95-0287-4152-ba14-484678d2ee02";
        :>> title = "Regenerate-from-model writers silently drop what the engine's view cannot represent";
        :>> createdAt = "2026-08-30";
        :>> createdBy = "claudeOpus5";
        :>> description = "Generalised from issue293's retro (sprint497). keel activate regenerated activation.toml from a template plus two computed lists, so it deleted every fact the engine's view could not represent: comments, the charteredBy reference, and the whole category of non-switchable [always] processes. NOTHING DETECTED IT - the keystone lock caught the FILE changing, and only because that file happens to be locked. A write path whose only audit is the control guarding its output is unaudited for every output that is not locked. THE CLASS: any command that rebuilds a human-editable file from the engine's model of it. sync-claude is the next candidate and already claims the correct shape (it merges user entries in settings.json rather than overwriting) - claimed, not currently proven by a test that a hand-added user entry survives a regeneration. SCOPE: enumerate the writers that regenerate a human-editable file, and hold each one's preservation claim with a round-trip test of the sprint497 shape (write, regenerate, assert byte-identical apart from the intended change).";
        :>> discoveredInField = false;
        :>> severity = Severity::Medium;
    }
    #Resolves dependency from activateDoesNotLoseFacts to issue310;

    part issue311 : Issue {
        :>> id = "ae5000ae-cc76-4b89-b268-60c3332c5873";
        :>> title = "The release process tags AFTER recording, so the tag and the recorded commit disagree by construction";
        :>> createdAt = "2026-08-30";
        :>> createdBy = "claudeOpus5";
        :>> description = "Found by the rigor audit (2026-08-30) reading the release-recorded warning that had been standing since v0.3.1 shipped. The Release item recorded c4e306c (the content commit) while tag v0.3.1 points at c4d5dbf (the commit that RECORDED the release). Neither was a typo: the release process records the Release item, commits, and THEN tags HEAD - so the tag necessarily lands one commit after the commit the record names, for every release. The instance is corrected (the record now names the tagged commit, which is what users actually run); the PROCESS defect is this issue. Fix direction: tag the commit the record NAMES, not HEAD - or record the release and tag that same commit, so the two cannot diverge. Whichever is chosen must be held by a test that a release's recorded commit resolves to its own tag, since the guard that caught this is warning-tier and stood unread for days behind 61 undischargeable warnings (D0261).";
        :>> discoveredInField = false;
        :>> severity = Severity::Medium;
    }
    #Resolves dependency from dcNoOpInvarianceControl to issue311;

    part issue312 : Issue {
        :>> id = "7937936b-24d5-417b-98ee-686f98669997";
        :>> title = "decision-scaffolding has no way to say 'the change landed WITH the Decision', so self-executing decisions warn forever";
        :>> createdAt = "2026-08-30";
        :>> createdBy = "claudeOpus5";
        :>> description = "Found by the rigor audit. The guard warns when an accepted #ProspectiveChange Decision has no inbound tracked-item edge, on the premise that it 'promises process change but charters no work'. For a decision whose change IS the commit - d0211 froze the enforcement surface, d0247 reclassified STPA, d0248 cut six clauses, d0257 shipped the propriety process and its skill, all landing in the same commit as the Decision - there is no future work to charter and never will be. The premise is right for promises and wrong for self-executing changes, so those four warn permanently: the SAME defect as the legacy-actor lines this audit just collapsed (D0261), regenerating itself in another channel. The fix is the shape this codebase already reached twice - THREE buckets, not two (issue173, quoted in keel hardening: the two-bucket version made a judgment look identical to a missing guard). A decision needs a way to declare 'self-executing, the change is in this commit', reviewable and disagreeable, exactly like process-enforcement.toml's declaredUnenforceable. NOT FIXED HERE, deliberately: the guard is under the keystone lock and adding a bucket is a weakening unless the declaration is itself checkable, which needs a Decision and a design - hardening it today would either lock out legitimate self-executing decisions or add an unchecked escape hatch. What IS fixed here: the three decisions that genuinely promised unbuilt mechanisms (d0201 Option B device HMAC, d0252 migration rollback, d0249 ungrounded-ratio trigger) now carry tracked work.";
        :>> discoveredInField = false;
        :>> severity = Severity::Medium;
    }
    #Resolves dependency from dcUngroundedRatioTriggers to issue312;

    part issue313 : Issue {
        :>> id = "b5381977-0f45-42fd-93cf-16c70b9b04bd";
        :>> title = "A fresh keel project cannot make its first commit at a deep path: reference-decision filenames blow Windows MAX_PATH";
        :>> createdAt = "2026-08-30";
        :>> createdBy = "claudeOpus5";
        :>> description = "FOUND BY RECONNAISSANCE for the federation test platform, before any suite existed. keel init at a 150-character directory produces .engine/reference/decisions/0137-a-release-is-verified-by-running-the-published-asset.sysml at 249 characters; git add -A then fails with 'unable to index file ... fatal: adding files failed' and the project cannot make its FIRST COMMIT. Discriminated against the alternative explanation: the SAME scaffold at C:/kt1 stages 484 files with exit 0, so this is path length, not a corrupt scaffold. Windows MAX_PATH is 260 and git refuses without core.longpaths=true, which keel init does not set. 150 characters of parent path is not exotic - a user under C:/Users/<name>/Documents/Projects/<client>/<project>/ is most of the way there before keel adds 100 of its own. THE SHAPE OF THE FIX IS A CHOICE, not obvious: set core.longpaths in the project keel init creates (only helps if keel owns the git init), shorten reference filenames on copy (changes a stable path downstream readers may cite), or DETECT the margin at init and refuse loudly rather than let the failure surface as an opaque git error later. Refusing loudly is the honest floor: a project that cannot commit is not initialised, whatever else succeeded.";
        :>> discoveredInField = false;
        :>> severity = Severity::High;
    }
    #Resolves dependency from dcNoOpInvarianceControl to issue313;

    part issue314 : Issue {
        :>> id = "39a31cb5-85c4-461f-9972-582a56813240";
        :>> title = "keel migrate silently reverts a project's adoption choices: engine resync overwrites project-owned contracts";
        :>> createdAt = "2026-08-30";
        :>> createdBy = "claudeOpus5";
        :>> description = "FOUND BY THE FEDERATION SUITE (F9), which exists because the propriety panel returned UNSOUND on the design for testing a project only at birth (pf42). step_engine_resync copies every shipped engine file over the project's copy, and .engine/contracts/ is shipped - so keel migrate overwrote activation.toml, adoption-profile.toml, engine-version.toml, installed-units.toml, github-actors.toml and parser-coverage-baseline.toml with the engine's defaults. DEMONSTRATED on a real project: deactivate render, commit, migrate - and render was ACTIVE again. THE DIRECTION THAT MATTERS MORE is the other one: where the engine's default has FEWER active processes than the project, migrate silently DISARMS controls the project had on, with no Decision anywhere - the unsigned control-weakening the keystone lock and audit-adherence exist to catch, arriving through a path neither of them watches. github-actors.toml is worse still: it declares WHO MAY DECIDE on the decision channel. FIXED: is_project_owned_contract - the engine ships a default so a fresh init has one, and resync ADDS it if absent but never overwrites it. The rule is 'a keel COMMAND writes this file'. Held by F9, which now asserts the deactivation survives the upgrade. THIS DESCRIPTION WAS REPAIRED (2026-08-30): its first version was written with backticks inside a double-quoted shell argument, so the shell EXECUTED them and substituted their stdout into the record - and also ran deactivate against this repository, whose activation.toml was restored from git. Third occurrence of a documented trap; routed to issue315.";
        :>> discoveredInField = false;
        :>> severity = Severity::High;
    }
    #Resolves dependency from dcNoOpInvarianceControl to issue314;

    part issue315 : Issue {
        :>> id = "b7350b86-7701-4ead-bfb9-156c2bb29ac4";
        :>> title = "A documented trap fired a third time because its fix was applied to the instance, not the class";
        :>> createdAt = "2026-08-30";
        :>> createdBy = "claudeOpus5";
        :>> description = "THIRD OCCURRENCE of a trap that already has a fix. Prose passed to a write command as a double-quoted shell argument has its backticks EXECUTED by the shell, and the command's stdout is substituted into the governance record in place of the author's words. D0224 fixed this for `record decision` by adding --from FILE after it happened twice. `record issue` was left on the argument path, and on 2026-08-30 it fired again while recording issue314: the shell ran `keel deactivate render` and `keel migrate`, substituted their output into the description, AND modified this repository's keystone-locked activation.toml, which had to be restored from git. The record was repaired by hand and says so. THE LESSON IS NOT 'be careful with backticks'. That is manual vigilance, which D0047 rejects as a control, and my own memory already carries the warning verbatim - it did not help. The lesson is that D0224 fixed the INSTANCE (decisions) and not the CLASS (every write path that takes prose as an argument). FIXED HERE: `record issue --description-from FILE`, mirroring the decision path, with the argument form still accepted for one-liners and its usage text naming the hazard. STILL OPEN as the class: any other write path taking prose by argument. The honest closure is a check that no write command accepts a long prose field by argument alone - which needs an inventory of write paths, so it is named here rather than claimed.";
        :>> discoveredInField = false;
        :>> severity = Severity::High;
    }
    #Resolves dependency from dcNoOpInvarianceControl to issue315;

    part issue316 : Issue {
        :>> id = "7ae8dd2e-20aa-4029-9213-a8e767b9423d";
        :>> title = "reprocess-candidates cannot finish, so the antiquated-data question has never been answered on this project";
        :>> createdAt = "2026-08-30";
        :>> createdBy = "claudeOpus5";
        :>> description = "FOUND BY THE VINTAGE PANEL (pf55), by measurement rather than inspection: keel reprocess-candidates does not finish. Timed twice - 240 seconds, exit 124, zero bytes of output - because it walks all 501 delivery stories and runs several git subprocesses PER STORY (govern.rs:362 all_delivery_stories, then govern_resolve -> git grep + git log per item). WHY IT MATTERS MORE THAN A SLOW COMMAND: this is the lens that answers 'which items were authored under a process version a SAFETY change later superseded' - that is, exactly the antiquated-data question. Because it never completes, that answer has never been computed on this project. The per-item lens (governing-version) works and is correct, but it is only usable by someone who ALREADY suspects a particular item, which D0261's own retro named as the shape of a metric that is not a control. THE FIX IS NOT A DESIGN CHANGE - the derivation is sound on four of five propriety lenses. It is a batched traversal: one git log --name-only pass building a commit -> touched-definition map and a decision -> intro-commit map, then an in-memory lookup per item, instead of a subprocess per item. VERIFY BOTH WAYS: the batched result must be IDENTICAL to the per-item result on a sample of items where the slow path can still be run to completion, and the whole-corpus run must finish - a fast lens that quietly answers differently is worse than a slow correct one.";
        :>> discoveredInField = false;
        :>> severity = Severity::High;
    }
    #Resolves dependency from dcNoOpInvarianceControl to issue316;

    part issue317 : Issue {
        :>> id = "2c850de4-e479-4139-beaa-3ab746009abc";
        :>> title = "governing-version answers DELIVERY for every item type it does not cover, instead of unknown";
        :>> createdAt = "2026-08-30";
        :>> createdBy = "claudeOpus5";
        :>> description = "FOUND BY THE VINTAGE PANEL (pf52). governing_def_for falls back UNCONDITIONALLY to .engine/workflows/delivery.sysml when an item has no #CharteredBy edge (govern.rs:19 and :39), and reprocess-candidates iterates only all_delivery_stories (govern.rs:362). CONSEQUENCE: asking for the vintage of a Need, SystemRequirement, Issue, Test, Statement, Decision or critique does not return 'unknown' - it returns DELIVERY, confidently and wrongly. A Need is governed by the Business workflow, not Delivery. A lens that answers the wrong question fluently is worse than one that refuses, because nobody checks a fluent answer. MEASURED SCOPE: 447 of 501 delivery stories carry a #CharteredBy edge, so derivation has real input for that ONE item type. No other item type in the corpus carries one. The human's intuition - that antiquated data carries no indication of what process authored it - is CORRECT for every item type except Story. FIX DIRECTION, and the choice matters: either (a) resolve per item KIND, with a declared kind-to-workflow map so a Need resolves to Business, or (b) return UNKNOWN when no charter edge exists, which is honest and immediately less useful. (a) is better only if the map is declared and checkable rather than another hardcoded constant restating something the model already knows - the issue300 class. Whichever is chosen, the unconditional Delivery fallback must go: it manufactures an answer.";
        :>> discoveredInField = false;
        :>> severity = Severity::High;
    }
    // Re-pointed 2026-08-30: issue316 was filed against the nearest AVAILABLE resolver because
    // `record issue` requires one, which is the very antipattern the github-intake process warns
    // about (an issue routed to a resolver that will not resolve it looks handled and is not).
    #Resolves dependency from dcBatchedGovernanceIndex to issue317;

    part issue318 : Issue {
        :>> id = "219bc82c-091c-4777-ba90-1434843bbabd";
        :>> title = "keel land reports success on a push whose CI it never looked at";
        :>> createdAt = "2026-08-30";
        :>> createdBy = "claudeOpus5";
        :>> description = "CI was red for seven hours across five pushes and nothing noticed. The human noticed. WHY EVERY SIGNAL SAID FINE. The local gate is thorough - validate, 56 guards, check-engine, rules --enforce, clippy - and it passed every time, because the three failing cases were ENVIRONMENT-dependent and this machine has a configured library, a global git identity and an authenticated gh. `keel land` reports 'landed' on a successful PUSH, which is where its knowledge stops. Green locally, push succeeded, command said landed, CI red. THE GAP IS PRECISE: land makes a claim about a GIT OPERATION while reading as a claim about the tree's standing. A contributor who runs land and sees 'landed' has been told the thing worked. FIX DIRECTION, and it is a real design choice rather than an obvious patch. (a) land POLLS the resulting run and reports its verdict - accurate, but turns a fast command into a two-minute one and needs a network path that may not exist. (b) land reports the run URL and the PREVIOUS run's verdict, cheap and immediate but tells you about the last push rather than this one. (c) land records the pushed SHA as awaiting CI and the NEXT keel invocation reports any awaited SHA whose run has since failed - cheap, asynchronous, and it surfaces the failure at the start of the next session, which is when someone can act. (c) is the shape that fits how this project is actually used, and it needs no new network call in the hot path. WHATEVER IS CHOSEN MUST NOT BE A REMINDER. D0047 rejects manual vigilance as a control, and my own working memory already carried 'check gh run after EVERY push' verbatim - it did not help for seven hours. The check has to be mechanical and it has to fire where someone will read it.";
        :>> discoveredInField = false;
        :>> severity = Severity::High;
    }
    #Resolves dependency from dcBatchedGovernanceIndex to issue318;

    part issue319 : Issue {
        :>> id = "675a3b5d-97f9-473b-801c-70bf9481dc12";
        :>> title = "An unrecognised flag becomes the ROOT, so a typo reports every guard green over a phantom directory";
        :>> createdAt = "2026-08-31";
        :>> createdBy = "claudeOpus5";
        :>> description = "INGESTED FROM GITHUB as GH#14 (st058), reported from field use. `keel guard --read` treated the unrecognised flag as the ROOT argument, gated a directory that does not exist, found no files, and reported every guard PASS with 0 scanned. TWO DEFECTS COMPOUNDING, which is why it is worse than either alone: silent argument mis-parsing, and pass-at-zero. Together they produce a GREEN RUN OVER NOTHING - output indistinguishable from a clean tree, on a command whose entire job is to tell you whether the tree is clean. REPRODUCED before fixing, on a fresh strict-profile project: every guard PASS, 0 scanned. NOT AN ISOLATED TYPO: the identical shape appeared hours earlier while building github-ingest, where the trailing value of --at was taken as the root and the command failed with an opaque filesystem error. Two independent instances of 'an argument that is not a path becomes the path' in one day is a class, not an accident - so the fix is a shared refusal applied to guard, validate and check-engine rather than a patch where it was noticed. FIXED: refuse_flag_as_path names the offending argument and states why refusing beats answering. Held by unknown_flag_is_refused.rs, which asserts BOTH that the three commands refuse with no verdict line AND that an ordinary root still scans the corpus - a refusal that broke real usage would have traded one vacuous pass for another.";
        :>> discoveredInField = false;
        :>> severity = Severity::High;
    }
    #Resolves dependency from dcUnknownFlagIsRefused to issue319;

    part issue320 : Issue {
        :>> id = "46806a42-912a-4810-b6f0-3d4e54d928c2";
        :>> title = "Every issue id I cited in prose today was off by one, because I piped the command that told me through tail -1";
        :>> createdAt = "2026-08-31";
        :>> createdBy = "claudeOpus5";
        :>> description = "EVERY ISSUE ID I CITED IN PROSE TODAY, from the migrate-adoption defect onward, was off by one. Six distinct defects, cited in Decisions D0263/D0265/D0266/D0268, in CLAUDE.md, in four source files, in two sprint records and in a propriety round: 33 wrong references in total, corrected here. ROOT CAUSE, PROVEN NOT GUESSED: `keel record issue` prints the allocated id on its FIRST line - 'recorded issue320 -> ...' - and even prints the resolver edge to author. I piped every one of those calls through `| tail -1`, which showed only the closing 'run keel validate to confirm' line and discarded the id. I then wrote down the number I ASSUMED had been allocated. The command told me the truth every time and I truncated it away. THIS IS THE THIRD TIME TODAY that output truncation caused a defect: `| head -4` killed a migration mid-apply and left a half-written tree; `| tail -1` hid an id fourteen times; and the same reflex hid the ingest count earlier. The pattern is piping a command's output through a truncating filter and then reporting on what I did not read. WHAT CAUGHT IT, AND WHAT DID NOT. `edge-endpoints` caught it the moment a TYPED EDGE named a non-existent issue320 - that guard works exactly as designed. Nothing caught the 33 PROSE citations, because a reference inside a description string is not an edge. So the model's typed structure is verified and its prose is not, and prose is where most cross-references actually live. CONTROL GAP, stated as the honest finding rather than a resolution to be careful: a guard could check that every `issueNNN` / `dNNNN` token appearing in authored prose resolves to a declared item. It would have caught all 33 immediately. It is not built here because the false-positive surface needs thought - prose legitimately discusses ids that were superseded or that belong to another project - and shipping a noisy guard would repeat the D0261 mistake of adding lines nobody can act on.";
        :>> discoveredInField = false;
        :>> severity = Severity::High;
    }
    #Resolves dependency from dcUnknownFlagIsRefused to issue320;

    part issue321 : Issue {
        :>> id = "7e18cd4f-8544-4640-a0d0-53398ef50bd6";
        :>> title = "The CLI has 111 dispatch arms and ~30 of them are the same act: compute a lens and print it";
        :>> createdAt = "2026-09-01";
        :>> createdBy = "claudeOpus5";
        :>> description = "INGESTED FROM THE HUMAN (st063), on the summary page: 'remove cruft from CLI. tons of commands, when a smaller subset should do, and parentheticals embedded in descriptions. tighten it up - what core functional hooks do we need in the CLI? a lot of these seem to be variations of an idea cemented as separate cli hooks. and critique all descriptions to trim them down to the real root of what is being done and what a user needs to know to run it.' MEASURED, and they are right about the scale. 111 dispatch arms in main.rs. About 30 of those are READ-ONLY LENSES - assumptions, attestation-coverage, authority-queue, concern-coverage, contentions, controls, coverage, critique-coverage, dispositions, hardening, indicators, intake, open-issues, orphans, outstanding, question-coverage, recent, reprocess-candidates, rootedness, sitting-coverage, suspect, tier-satisfaction, verification, why, workflows and more. Every one of them is the same act: compute a view of the model and print it. Each got its own top-level verb. THE DUPLICATION IS DEEPER THAN THE COMMAND LIST. 16 of the 32 declared VIEWPOINTS also have a dedicated top-level command of the same name - so a lens is declared in one mechanism and implemented in another. And the two are only half-connected: `keel view orphans` FAILS with 'view file not found' while `keel orphans` works. Two mechanisms for one idea, neither complete. DONE IN THIS PASS, because it breaks nothing: 55 help rows carried a decision-id parenthetical - (D0195), (issue171/D0169) - which is provenance for a maintainer, not something a user needs in order to run the command. All 55 stripped; the citations remain in the source doc comments, where someone looking for the reason will actually look. NOT DONE, and this is the part that needs a decision rather than initiative: collapsing ~30 verbs into one router is a BREAKING change to a surface other things call by name. Measured cost: 118 references across .engine skills and processes invoke these commands directly, and guard 39 (tool-reference) fails a process that names a tool it did not receive. So the migration is real work with a real failure mode, not a rename. THE SHAPE I WOULD PROPOSE, for their call: one `keel show <lens>` routing to the existing implementations, with all current names kept as aliases for a deprecation window so nothing breaks on the day it lands; then the alias list shrinks as the 118 call sites move. That collapses the visible surface from 111 arms to roughly twenty verbs - orient/status/whats-next, show, gate, record, audit, github, library, process, init/migrate/sync/land, serve/render/report/deck, actor/enroll, hook - without removing a single capability.";
        :>> discoveredInField = false;
        :>> severity = Severity::Medium;
    }
    // Re-pointed: record issue auto-triaged this onto a task that is already DONE. The honest
    // resolver is the consolidation task, which the human has not yet authorised - so the issue
    // carries the analysis and waits, rather than looking handled.
    #Resolves dependency from dcCliSurfaceConsolidation to issue321;

    part issue322 : Issue {
        :>> id = "af25e075-18f6-4678-bae2-2b2aadcb6e2c";
        :>> title = "The prose-by-argument trap fired a fourth time, because the fix was applied per-command not per-class";
        :>> createdAt = "2026-09-01";
        :>> createdBy = "claudeOpus5";
        :>> description = "FOURTH OCCURRENCE of the same trap, and the reason it recurred is precisely diagnosable: the fix was applied per-command instead of per-class. D0224 added `--from FILE` to `record decision` after shell backticks in a double-quoted argument were EXECUTED into a governance record twice. issue315 recorded the third occurrence, in `record issue --description`, which also ran `keel deactivate` against this repository; that one was fixed with `--description-from FILE`. `add-task --dod` was the remaining prose-by-argument path and nobody looked, so today it ate `keel show <lens>` out of a task's Definition of Done, leaving the sentence 'one routing to the existing implementations' - a DoD that reads as finished prose and is missing the thing it specifies. WHAT MAKES THIS DIFFERENT FROM CARELESSNESS: after the third occurrence I wrote the rule into CLAUDE.md, into the skill, and into a Decision. All three said never pass prose as a double-quoted shell argument. The instruction was present, correct, and prominent - and the command I needed had no file-taking flag, so following the rule was impossible for that call. A rule that cannot be obeyed on some path is not a control on that path. FIXED: `add-task --dod-from FILE`, with the usage text naming the hazard on the inline form. That is now every write path that takes prose. THE REMAINING GAP, stated rather than claimed closed: nothing CHECKS that a write path taking a long prose field offers a file alternative. A fifth such path added tomorrow would reopen this. That check is cheap in principle - enumerate the write commands, assert each prose flag has a `-from` sibling - and it is not built here because the honest resolver is the CLI consolidation work (issue321), which will change what the write paths are.";
        :>> discoveredInField = false;
        :>> severity = Severity::High;
    }
    #Resolves dependency from dcCliSurfaceConsolidation to issue322;

    part issue323 : Issue {
        :>> id = "dae5054f-9128-40e5-98de-3ed72a35b88c";
        :>> title = "Re-publishing an imported unit re-mints its identity and resets it to v1, so the drift report affirms there is no update";
        :>> createdAt = "2026-09-01";
        :>> createdBy = "claudeOpus5";
        :>> description = "FOUND while publishing an improvement to the exec-summary skill, and it defeats the drift report shipped one day earlier. WHAT HAPPENED, step by step and all verified on disk. This project imported `exec-summary` from the library; the import wrote an install record keyed by the LIBRARY's unit id a2428932. The skill was then improved and re-published. Export looked the unit id up in THIS project's .engine/contracts/unit-ids.toml, found a DIFFERENT id - a55244a1 - and wrote that into the library's unit.toml, replacing the original identity. Because install_record(a55244a1) finds nothing (the record is filed under a2428932), next_unit_version fell to its None arm and wrote version = 1. SO THE PUBLISHED UNIT CHANGED CONTENT, CHANGED IDENTITY, AND KEPT ITS VERSION NUMBER. The library's SKILL.md is now 151 lines carrying the new sufficiency rule; unit.toml still says version = 1. WHY THIS IS WORSE THAN A NUMBERING BUG. Every consuming project compares versions to decide whether it is behind - that is exactly what `keel status`'s drift section does, shipped yesterday against srDriftIsReportedPerUnit. A project holding the old v1 sees 'v1 available, v1 installed, nothing behind' while the content differs entirely. The report does not merely miss the update; it AFFIRMS that there is none. And the identity change means even a corrected version number would not help: the unit a project installed no longer exists under that id. TWO DEFECTS, and they should not be conflated. (1) A unit's identity is re-minted on export from a project that IMPORTED it, instead of being carried from the install record. (2) The version resets when the id lookup misses, silently, because None means 'new unit' and a missed lookup is indistinguishable from one. FIX DIRECTION. Export must prefer the id in the INSTALL RECORD over a locally minted one - a unit's identity belongs to the unit, not to the project that happens to be exporting it - and a version lookup that misses on a process the project demonstrably has installed should REFUSE rather than restart at 1. Whatever is chosen must be held by a round trip: import a unit, change one file, publish, and assert the identity is unchanged AND the version incremented. That test would have failed today.";
        :>> discoveredInField = false;
        :>> severity = Severity::High;
    }
    // MIS-TRIAGED ON ARRIVAL and corrected here: this pointed at dcCliSurfaceConsolidation, which is
    // the resolver of the two issues recorded immediately before it and has nothing to do with unit
    // identity. The `issues` guard passed anyway, because it checks that a #Resolves edge EXISTS
    // (guards.rs:970-986) and never that the resolver can resolve it — so a false triage reads as
    // triaged. issue322 above points at the same task DELIBERATELY and says so in its own text; that
    // is what a correct one looks like, and the difference is not visible to any control today.
    #Resolves dependency from dcUnitIdentityIsCarriedNotMinted to issue323;

    part issue324 : Issue {
        :>> id = "9cdbc5c6-28d9-41fb-a5d9-80fa8e7960f4";
        :>> title = "Migrate's dirty-tree refusal and D0251's skew refusal form a circular lock, sprung by a file the engine wrote itself";
        :>> createdAt = "2026-09-01";
        :>> createdBy = "claudeOpus5";
        :>> description = "REPORTED BY A PEER SESSION working in another keel project (their issue021), and VERIFIED HERE IN SOURCE before recording rather than taken on their word. Three individually-correct controls compose into a lock with no non-bypassing exit, and the file that springs it is written BY THE ENGINE. THE CYCLE, each leg read at file:line. (1) `keel migrate` refuses on a dirty tree - migrate.rs:652-656, and the check at migrate.rs:670-687 runs `git status --porcelain -- .tracking .engine`, which reports UNTRACKED files, so a brand-new file trips it. (2) Committing that file to clean the tree fails - the pre-commit hook runs `keel validate`, and validate REFUSES under engine-version skew because a gate surface must not return a verdict from an engine the project did not pin (main.rs:226-230, D0251). (3) Skew clears by running the pinned binary or by `keel migrate` - main.rs:188. A project whose only available binary is the newer one has exactly one exit, and it is leg (1). WHY IT IS THE ENGINE'S OWN DOING. The uncommitted file in the reported case was `.tracking/obligations/red-yield-<short>.sysml`, auto-written by `record_obligation` (write.rs:471-481) when the Stop hook's second red pass yielded, under D0176/K7. That function's own doc comment reasons about deadlock - 'one Issue per file so recording can never deadlock on the very file being repaired' - and the reasoning is correct at the FILE level and blind at the TREE level: a new untracked file in a tree that cannot be committed is exactly as blocking as an edit to the file under repair. And the trigger correlates with the hazard: an obligation is recorded precisely when a project is already unhealthy, which is also when it is most likely to be behind its pin. NOT REPRODUCIBLE IN THIS REPO, and that is why it went unseen. check_preconditions returns Refusal::SelfBuild for any tree holding keel-cli/Cargo.toml (migrate.rs:664-666), so migrate never runs here at all. This class of defect can only be found downstream, which makes the peer's report the evidence and not a nuisance. WHAT THE HUMAN ACTUALLY DID: `git stash push -u -- <path>` then migrate then `git stash pop` - the escape migrate's own message names. It works and bypasses nothing. The outcome worth preventing is the contributor who reaches for `--no-verify` instead, which disables every other check in the hook to get past one. FIX DIRECTION, and the two rejected alternatives are the argument for the chosen one. (a) Have the obligation recorder STAGE its own file: does not help - staged is still uncommitted, and `git status --porcelain` reports it either way. (b) Degrade pre-commit validate to a warning under pure skew: weakens a gate to work around a different gate, which is how a control gets hollowed out one exception at a time. (c) Let migrate proceed when every uncommitted path under .tracking/ is an engine-authored obligation record: this is the only shape that breaks the cycle WITHOUT weakening anything, and it is defensible on migrate's own stated rationale - the refusal exists because 'a half-migrated tree mixed with uncommitted edits cannot be told apart afterwards', and a brand-new additive file in a dedicated directory CAN be told apart. It must stay narrow: the carve-out is `.tracking/obligations/` only, untracked-or-added only, and migrate must NAME the files it tolerated so the exemption is visible rather than silent.";
        :>> discoveredInField = false;
        :>> severity = Severity::High;
    }
    #Resolves dependency from dcObligationDoesNotLockTheTree to issue324;

    part issue325 : Issue {
        :>> id = "aed57d5d-fa22-46eb-96e6-ca64393d708a";
        :>> title = "add-task wrote DoD prose into a SysML literal unsanitized, so a quoted phrase left the backlog unparseable";
        :>> createdAt = "2026-09-01";
        :>> createdBy = "claudeOpus5";
        :>> description = "FOUND BY HITTING IT, one command after recording issue322 about this exact class. `add-task --dod-from` interpolated its prose RAW into a SysML string literal (write.rs:1193) while every other prose write path in the same file bound sanitize_field. My DoD contained the phrase THE REMEDY IS NOT (quote)fill in the placeholder(quote), the inner double quote closed the literal, and .tracking/backlog.sysml stopped parsing at 418:398. WHAT MADE IT WORSE THAN A MALFORMED FIELD. The tree was UNPARSEABLE, so the next command could not read the model to do anything at all - including to report the problem. `keel record issue` failed with 'cannot read the model to check the resolver', which is the write API refusing correctly and for the wrong-looking reason: the resolver was fine, the corpus was broken by the previous write. A write path that can render the model unreadable takes every other control down with it, because they all parse before they check. THE SAME SHAPE AS issue322, ONE DAY LATER AND FROM THE SAME CAUSE. issue322 recorded that the prose-by-argument trap fired a fourth time because the fix had been applied PER-COMMAND rather than per-class, and its remedy was `add-task --dod-from FILE`. That flag was added THIS MORNING - by me - and it was wired to read a file without routing the result through the sanitizer the other write paths use. So the fix for a per-command defect was itself applied per-command. The rule I wrote in issue322's own text ('a fix applied per-command leaves the next path open') described what I was about to do. FIXED AT THE WRITE PATH, and SWEPT rather than patched: before changing the line I grepped every interpolation into a SysML literal in write.rs. record_issue_locked binds `let s = sanitize_field` and uses it on title, date, author, description, severity and resolver; record_decision does the same for its six fields; record_obligation binds `esc`; the notes, view-attribute and claim paths all call it. add_task_locked was the only one that did not. That is now closed and the count is zero. RESIDUAL, stated: nothing CHECKS that a new interpolation routes through the sanitizer. A fifth prose field added tomorrow could skip it exactly as this one did, and the only signal would be a corrupted tree. The honest control would be a lint or a type that makes an unsanitized value unusable in a literal - not built here, and named so it is not mistaken for closed.";
        :>> discoveredInField = false;
        :>> severity = Severity::High;
    }
    #Resolves dependency from dcDodProseCannotBreakTheModel to issue325;

    part issue326 : Issue {
        :>> id = "8df99ffa-9adc-4556-b797-c5a7506dd12e";
        :>> title = "decision-channel ships two CI workflows as extras that build the keel crate, so every consumer importing it acquires two permanently red workflows";
        :>> createdAt = "2026-09-01";
        :>> createdBy = "claudeOpus5";
        :>> description = "REPORTED BY A PEER SESSION that imported decision-channel v6 into a non-engine project (their issue022), and VERIFIED HERE before recording rather than taken on their word. The unit ships two CI workflows as declared extras, and NEITHER can run anywhere but the engine's own repository. VERIFIED AT file:line. `.engine/contracts/unit-extras.toml [decision-channel] files` declares all four extras, including .github/workflows/decision-issue.yml and .github/workflows/decision-record.yml; the library's decision-channel unit ships exactly those four files alongside the process, skill and registry. Both workflows run `cargo build --release -p keel-cli --bin keel` - decision-issue.yml:27 and decision-record.yml:49. A consuming project has no Cargo.toml and no keel-cli crate, so the build step cannot succeed. The peer additionally reports both returned startup_failure on their very next push, which is their observation and not one I can reproduce from here; the build-step defect stands independently of it. SO EVERY CONSUMER THAT IMPORTS decision-channel ACQUIRES TWO PERMANENTLY RED WORKFLOWS. That is not merely noise. A project whose Actions tab is red by default trains its maintainers to ignore red, which is the same failure that let this repo's own CI stay red for seven hours across five pushes (issue318). Shipping a red workflow is shipping a disabled alarm. SAME FAMILY AS issue301, DIFFERENT HALF. Both are unit EXTRAS behaving wrongly once they leave the engine repo: issue301 was about how extras were KEYED (absolute paths naming the author's machine), this is about whether they are RUNNABLE where they land. The generalisation worth holding: an extra is the only part of a unit that executes in the consumer's environment, and nothing checks that it can. THE DEEPER ROOT, and it is the reason this is not a one-line fix. Every CI workflow keel ships was written for a repository that CONTAINS the keel crate. The engine's own in-workflow gate must build from source - it exists to gate recorder commits with the code in that commit - so the workflow is correct where it lives and wrong everywhere it is sent. A unit cannot ship a file that is right in both places unless the file itself distinguishes them. NOTE ON THE NAIVE FIX. Replacing the build with a download of the LATEST binary reintroduces the failure from the other side: the project's pin is BINDING and validate/guard REFUSE under engine-version skew (main.rs:226-230, D0251), so a consumer's CI running a newer binary than its pin would refuse every gate step. The install must read .engine/contracts/engine-version.toml and fetch that exact version.";
        :>> discoveredInField = false;
        :>> severity = Severity::High;
    }
    #Resolves dependency from dcShippedCiRunsWhereItLands to issue326;

    part issue327 : Issue {
        :>> id = "3ae25be1-7641-405f-9e16-2d4e9215b864";
        :>> title = "keel init scaffolds a CI gate whose install step is three echoes, so a fresh project's own gate has never run";
        :>> createdAt = "2026-09-01";
        :>> createdBy = "claudeOpus5";
        :>> description = "REPORTED BY A PEER SESSION as a pre-existing failure in their own project, explicitly not attributed to me - and it turns out to be mine. VERIFIED HERE at claude_surface.rs:162-185. WHAT keel init SCAFFOLDS. CI_TEMPLATE emits .github/workflows/keel-gate.yml whose `install keel` step is three echo statements and nothing else: it echoes 'Install the released keel binary for linux and put it on PATH', echoes the releases URL, echoes 'Then delete this echo block'. The very next step runs `keel validate .`. So the workflow reaches a command that is not on PATH and fails with `keel: command not found` on the project's FIRST push. WHY THIS IS WORSE THAN AN UNFINISHED TEMPLATE. The four steps after the placeholder are validate, guards, rules and audit-history - this file IS the downstream project's layer-3 verification, the hook-independent gate K15 exists to provide precisely because nothing remote should assume a local hook ran. A fresh project therefore starts life with its own gate never executing, and with a red Actions tab that reads as 'the placeholder nobody deleted' rather than 'your gate is not running'. The redness has a ready explanation that is not the true one, which is the property that makes a broken control stay broken. AND THE PLACEHOLDER CANNOT SIMPLY BE FILLED IN. Downloading the latest release would put the runner in D0251 skew against the project's pin, and validate/guard REFUSE under skew on a gate surface (main.rs:226-230) - the workflow would go from `command not found` to a refusal, still red, now for a subtler reason. The install must read .engine/contracts/engine-version.toml and fetch that version. FEASIBLE AS OF TODAY, which is worth recording because it may not have been when the placeholder was written: the engine repository is PUBLIC (gh repo view), so a runner needs no secret to download; and release.yml:49-76 attaches a per-platform asset per tag, keel-linux-x86_64 for the runner this template targets. Releases exist through v0.3.1. Nothing blocks a real install step. RELATED TO issue326 BY ROOT: both are shipped CI that assumes the engine's own repository. This half assumes a human will finish the file; that half assumes a keel-cli crate is present. Neither has ever been observed to run green anywhere but here.";
        :>> discoveredInField = false;
        :>> severity = Severity::High;
    }
    #Resolves dependency from dcShippedCiRunsWhereItLands to issue327;

    part issue328 : Issue {
        :>> id = "65d4fda8-57dd-43bc-8b57-be7806525856";
        :>> title = "keel migrate silently discards a project's edits to an engine-shipped file, reporting only a count";
        :>> createdAt = "2026-09-01";
        :>> createdBy = "claudeOpus5";
        :>> description = "FOUND BY BUILDING THE REALISTIC MIGRATION FIXTURE, which is exactly what that fixture exists for - the first property it added to a fresh scaffold produced a defect on the first run. OBSERVED, not reasoned: a project customised an engine-shipped file (.engine/skills/actor-enrollment/SKILL.md, one appended comment line), committed, and ran keel migrate. The customisation was present before and GONE after, and migrate's entire output about it was 'wrote 2 file(s)'. THE ISSUE314 CLASS, ONE FILE-KIND OVER. issue314 was migrate silently reverting a project's ADOPTION choices, fixed by exempting six project-owned contracts from the resync. This is the same shape for the project's edited CONTENT: the resync writes engine files in place, and anything the project put there is discarded with no receipt. WHAT IS AND IS NOT THE DEFECT, because the distinction decides the fix. Overwriting is arguably the correct POLICY - engine files belong to the engine, and a project wanting durable local content has the unit mechanism for exactly that. Preserving instead would leave a project pinned to a stale engine file forever with no signal, which is worse. So the defect is not the replacement; it is the SILENCE. A count cannot be acted on: it does not say which files, so it cannot tell a project that the edit it was relying on no longer exists. WHY NOT A THREE-WAY MERGE, which is the obvious richer answer: it needs the engine content at the project's OLD vintage, and keel deliberately stores no vintage stamp - the vintage IS which migration steps still match (migrate.rs module docs, and the reasoning there is sound: a stored stamp can drift from the tree it claims to describe). There is no baseline to merge against, and inventing one would be a bigger change than the problem warrants. FIXED: report_written names every file the migration wrote, repo-relative, under a line saying plainly that a local edit to any of them is now gone and git diff will show what changed. That hands the reader the one tool that settles it, at the moment pm3Reconcile already tells them to review before committing. NOTE ON HOW IT WAS ALMOST MISSED. The first probe of this behaviour was INCONCLUSIVE and looked like a pass: it ran at a deep scratchpad path, hit Windows MAX_PATH mid git-add, left the tree uncommitted, and migrate then refused on a dirty tree - so the customisation survived because the migration never ran. Reading that as 'the customisation is preserved' would have recorded the opposite conclusion. The issue313 class biting a test rather than a user, and the reason the fixture now roots itself shallowly on purpose.";
        :>> discoveredInField = false;
        :>> severity = Severity::Medium;
    }
    #Resolves dependency from dcMigrationFixtureIsRealistic to issue328;

    part issue329 : Issue {
        :>> id = "a77eec16-afca-49a5-b5a0-f758ffe3a6f0";
        :>> title = "A non-zero count asserted by substring broke twice, and the first repair left an identical live instance";
        :>> createdAt = "2026-09-01";
        :>> createdBy = "claudeOpus5";
        :>> description = "THE SAME TEST DEFECT FIRED TWICE, AND THE FIRST REPAIR LEFT AN IDENTICAL LIVE INSTANCE UNTOUCHED. Two tests asserted a non-zero count by NEGATED SUBSTRING - !text.contains('0 <label>'). That form is wrong for every count ending in zero, because '580 tracked file(s)' CONTAINS '0 tracked file(s)' as a substring. TIMELINE, which is the reason this is recorded rather than just fixed. It first fired earlier today when a guard's scanned count reached 370 and federation.rs went red; that site was repaired and a comment left explaining the trap. It fired again this evening when the tracked-file count reached 580, reddening status_distinguishes_unknown - and the sweep that followed found unknown_flag_is_refused.rs:58 carrying the identical predicate, live, untouched by the first repair, waiting for its own count to end in a zero. WHAT IT ACTUALLY COSTS. Only false REDS, not false greens: when the count genuinely is zero the assertion still fails, which is what it is for. So this is a nuisance-class defect rather than an honesty-class one - but it cost two debugging detours, and the second one arrived mid-way through a five-step plan where a red suite is indistinguishable from a real regression until someone reads it. THE PATTERN IS THE FINDING, NOT THE STRING. This is the third time in one day that a defect recurred because its fix was applied PER-INSTANCE rather than PER-CLASS: issue322 (the backtick trap fired a fourth time because --from was added per-command), issue325 (add-task's --dod-from was added without routing through the sanitizer every other prose path used), and now this. In all three the first repair was correct and local, and the class stayed open. The generalisable rule: after fixing a defect, the next action is to GREP FOR THE SHAPE, not to move on - and the grep costs seconds where the recurrence costs a debugging session each time. FIXED, and the correction is a control this time (D0047). Both sites parse the number and compare it. no_test_asserts_a_count_by_substring walks every .rs under tests/ and fails on any negated-substring count assertion, naming file and line - so a third instance is refused at the point of writing rather than discovered when a counter happens to reach a multiple of ten.";
        :>> discoveredInField = false;
        :>> severity = Severity::Low;
    }
    #Resolves dependency from dcCountAssertionsParseTheNumber to issue329;

    part issue330 : Issue {
        :>> id = "15921bc7-47ab-4730-a0c4-0b9bf467a61b";
        :>> title = "An authorised breaking rename cannot land: editing human-owned viewpoint renderers violates D0108, leaving them stale violates the renderer guard";
        :>> createdAt = "2026-09-01";
        :>> createdBy = "claudeOpus5";
        :>> description = "A BREAKING CHANGE THE HUMAN AUTHORISED CANNOT BE LANDED WITHOUT VIOLATING A GUARD, AND NOTHING ANTICIPATED IT. D0273 collapses 35 lens verbs into `keel show <lens>` and removes the old spellings. Ten declared Viewpoints in .engine/views/viewpoint-registry.sysml carry a `renderer` field naming one of those verbs, and those ten items are owned by wweatherholtz. BOTH DIRECTIONS FAIL A CONTROL, and neither guard is wrong. EDIT the renderer strings: `guard:ownership` fails 10 times. D0108 - a non-owner ADDS items and typed edges or SUPERSEDES, never overwrites in place. Verified by running it: 10 violations, all on wweatherholtz-owned items; the 12 viewpoints owned by claudeOpus5 pass, so the guard is discriminating correctly rather than misfiring. LEAVE them stale: `guard:viewpoint-renderer` fails. classify_renderer resolves the lens behind the router, so a renderer naming a removed verb is 'unknown' - which is the guard working, since the declaration would otherwise point at nothing. THE SANCTIONED THIRD PATH DOES NOT RESOLVE IT. D0108 offers SUPERSEDE to a non-owner, but neither guard excludes superseded items - checked in the source, not assumed - so a superseding viewpoint would leave the original still declaring a dead renderer and still failing the renderer guard. The escape hatch D0108 provides does not reach this case. WHY THIS IS A GOVERNANCE GAP RATHER THAN A BUG IN EITHER GUARD. A viewpoint's renderer is not a JUDGMENT its owner made; it is a POINTER to a mechanism the engine owns and has now renamed. D0108 exists to stop a non-owner changing what someone MEANT, and updating the spelling arguably preserves their meaning rather than altering it. But that distinction is mine to argue and not mine to act on: talking myself past an ownership control to land my own change is precisely the self-modification class D0209 and issue236 exist to prevent, and the reasoning would be equally available to any future change that found the guard inconvenient. WHAT IS BLOCKED. The D0273 work is complete and green on every other axis - 31 of 31 comparable lenses byte-identical against the pre-collapse binary, 463 tests passing, clippy clean, 55 of 56 guards green - and is NOT COMMITTED, because committing it would mean landing a red gate. Steps 1 to 3 of the D0275 migration plan are landed; step 4 is held here. WHAT WOULD RESOLVE IT, for the record and without choosing between them: the owner makes the ten edits; or the ownership guard learns that a mechanically-renamed reference is not a field edit (an enforcement-surface change needing its own signed Decision); or D0108 gains a stated rule for engine-driven renames of owned items, which is the general form and the one that would also cover the next rename. WHERE THE WORK IS. The D0273 change is complete, green on every other axis, and NOT COMMITTED - it sits on `git stash@{0}`, labelled. Applying it will conflict on .tracking/issues-claudeOpus5.sysml, because THIS issue was recorded before the stash and re-recorded after it; keep one copy. The decision surface is published at https://claude.ai/code/artifact/79c42da9-bd0e-4761-9c18-ecc9f8ad28d6 and carries the ten exact edits.";
        :>> discoveredInField = false;
        :>> severity = Severity::High;
    }
    #Resolves dependency from dcCliSurfaceConsolidation to issue330;

    part issue331 : Issue {
        :>> id = "0ef7db3e-7e53-4fa2-88f8-2df83ca34223";
        :>> title = "decision-scaffolding passes a multi-clause Decision once ONE clause is chartered, so partial delivery is invisible";
        :>> createdAt = "2026-09-01";
        :>> createdBy = "claudeOpus5";
        :>> description = "CONTROL DEFECT, direction UNDER-REPORTING (D0278). `decision-scaffolding` checks that an accepted #ProspectiveChange Decision has SOME inbound tracked-item edge - one is enough. A Decision with several independent clauses therefore satisfies it the moment ONE clause is chartered, and partial delivery of a compound Decision becomes structurally invisible. OBSERVED: D0252 was accepted on 2026-08-30 with two clauses. Clause B (a migration that cannot finish rolls back) was chartered by dcMigrationRollsBack and built. Clause A (a unit declares the CAPABILITIES it invokes, and an install lacking one refuses by name) had its guard half already shipped under D0183 and its COMMAND half never built at all - the token `commands` appeared nowhere in process_cmd.rs. The guard passed for nine days while half an accepted Decision sat undelivered, and the gap surfaced only because D0273's clean break needed exactly that missing mechanism. INVALIDATION - what it passed while broken: every `decision-scaffolding` PASS on any multi-clause Decision, across 67 scanned. NOT RE-CHECKED, and worth being precise about why it is hard to re-check: no view lists Decisions by clause, because CLAUSES ARE PROSE. There is no authored fact saying D0252 has two of them. So the population cannot even be enumerated without reading 276 Decisions. FIX DIRECTION, and the honest one is not a guard change: per-clause charter edges would make delivery computable, which is a schema question (a Decision would need addressable clauses) and belongs in a proposal rather than a patch. Until then the guard is correct about what it checks and must not be read as checking more.";
        :>> discoveredInField = false;
        :>> severity = Severity::High;
    }
    #Resolves dependency from dcDecisionClausesAreAddressable to issue331;

    part issue332 : Issue {
        :>> id = "2d29fe40-a4aa-47e1-9807-bb0ee2d459fd";
        :>> title = "The ownership guard attributes edits to the machine's bound actor, not the session's, so it over-reports against items the session owns";
        :>> createdAt = "2026-09-01";
        :>> createdBy = "claudeOpus5";
        :>> description = "CONTROL DEFECT, direction OVER-REPORTING (D0278). The `ownership` guard (D0108: a non-owner ADDS or SUPERSEDES, never overwrites in place) attributes an edit to the actor bound to the MACHINE rather than to the actor the session is running as. A session that sets KEEL_ACTOR - the per-session mechanism D0129 explicitly sanctions - is therefore reported as a non-owner editing items it in fact owns. OBSERVED, with both numbers: this machine is bound to `claudeFable5`; this session runs as `claudeOpus5`. Running `keel guard` under KEEL_ACTOR=claudeOpus5 reported 10 ownership violations, all genuinely wweatherholtz-owned. The Stop hook, which runs WITHOUT the env var, reported those 10 plus 12 more against viewpoints owned by claudeOpus5 - items this session may edit. 12 false violations against 10 real ones: the majority of the gate's output was wrong. INVALIDATION - what it passed while broken: nothing silently. This is the over direction, so its errors are refusals rather than false greens, and no verdict needs re-checking. The cost is different in kind and is the reason it is still High: an over-reporting BLOCKING gate is one people learn to work around, and this one blocks the turn. It also actively obscures the real finding - the 10 genuine violations arrived buried in 22, which is how a true signal is lost inside its own noise (the D0214 failure through a different door). FIX DIRECTION: the guard should read the effective session actor the same way the write paths do (crate::actor::resolve, which honours KEEL_ACTOR before the machine binding) rather than the binding alone. That is a guard-source change under the keystone lock, so it needs its own signed Decision - which is the stated reason for carrying it rather than fixing it in the turn that found it.";
        :>> discoveredInField = false;
        :>> severity = Severity::High;
    }
    #Resolves dependency from dcControlDefectsAreFixed to issue332;

    part issue333 : Issue {
        :>> id = "3f4b3167-70d6-4022-9138-dba5f83308fc";
        :>> title = "The issues guard passes a mis-triage - it checks a #Resolves edge EXISTS, never that the named resolver could resolve it";
        :>> createdAt = "2026-09-01";
        :>> createdBy = "claudeOpus5";
        :>> description = "CONTROL DEFECT, direction UNDER-REPORTING (D0278). The `issues` guard enforces that every Issue carries a #Resolves edge, and enforces nothing about whether the named resolver could possibly resolve it. Predicate at keel-cli/src/guards.rs:970-986: it sources the untriaged set from the declared issuesTriagedRule and reports only issues with NO edge. An edge to an unrelated task is indistinguishable from a correct triage. WHAT MAKES THIS THE UNDER DIRECTION rather than a missing feature: the guard PASSES a state it exists to catch. Triage is the thing being enforced, and a false triage is untriaged with an edge on it. OBSERVED, not theorised: issue323 (unit identity re-minted on republish) was recorded with resolver dcCliSurfaceConsolidation - the CLI consolidation task, carried over from the previous record call - and the guard passed it. dcCliSurfaceConsolidation cannot resolve a unit-identity defect and its DoD never mentions it. Caught by reading, not by any control. INVALIDATION - what it passed while broken: every `issues` PASS since the guard was written, over a corpus now at 329 issues. NOT RE-CHECKED. The exposure is not cosmetic: `keel whats-next` ranks the frontier partly by the severity of issues a task resolves, so a mis-pointed edge inflates a task's apparent priority and lets the real issue sit behind work that will not close it. WHY IT IS HARD, stated so the fix is not assumed cheap: issue322 points at that SAME task deliberately and says so in its own text, because the CLI consolidation genuinely is its resolver. So the distinguishing signal between a correct and an incorrect edge is PROSE, and a guard that fired on prose similarity would be wrong about half the time. The defensible shapes are (a) require the resolving task's DoD to NAME the issue id - a convention change with a migration cost across 329 issues, or (b) report a WARNING rather than a violation where the resolver's text does not mention the issue, accepting noise in exchange for visibility. Neither is a one-line fix, which is why this is registered and carried rather than fixed in the turn that found it.";
        :>> discoveredInField = false;
        :>> severity = Severity::High;
    }
    #Resolves dependency from dcControlDefectsAreFixed to issue333;

    part issue334 : Issue {
        :>> id = "85676c61-4aae-44aa-9b2c-126a4f9ac785";
        :>> title = "The turn gate is fail-open - the Stop hook ALLOWS on its own error, so the control against a rogue turn holds only when nothing goes wrong";
        :>> createdAt = "2026-09-01";
        :>> createdBy = "claudeOpus5";
        :>> description = "PANEL FINDING, Critical (rigorTopologyCritique). The Stop hook - the turn gate, the control the human relies on to stop a rogue turn - is fail-OPEN. On its own error it prints a loud warning and ALLOWS. So do post-edit, subagent-stop and the CI gate. Of 12 enforcement points in keel hardening's own table, TWO are fail-closed: pre-write and the pre-commit git hook. On harness timeout every hook resolves to ALLOW. WHY THIS IS THE ANSWER TO 'WE STOP AI AGENTS FROM GOING ROGUE SOMETIMES'. The gate is real and it works when nothing goes wrong. Its failure mode is permission. A slow guard, a locked binary, a crashed validate - the conditions of a session under load, which is when a rogue turn is most likely - all end the turn with a green light. Authority that evaporates under load is not authority. WHAT IS AND IS NOT FIXABLE. The harness's timeout-resolves-to-allow is the harness's and stays a recorded residual (the fire-ledger detects an expected fire that did not happen). The hook's OWN error path is keel's choice, and it currently chooses to allow. That is the fix. RESOLVER: dcTurnGateFailsClosed. Deny on error, the way pre-commit already does.";
        :>> discoveredInField = false;
        :>> severity = Severity::Critical;
    }
    #Resolves dependency from dcTurnGateFailsClosed to issue334;

    part issue335 : Issue {
        :>> id = "5992bb60-7227-4a20-ac22-82dd842ee652";
        :>> title = "retro_backlog is vocabulary-keyed and satisfied by any task name, so retro findings are never examined";
        :>> createdAt = "2026-09-01";
        :>> createdBy = "claudeOpus5";
        :>> description = "CONTROL DEFECT, direction UNDER-REPORTING (D0278) - the fourth found today and the one behind the other three going unrouted. retro_backlog (guards.rs:1601-1628) fires only when a retro's text contains the literal tokens AVOIDABLE-ISSUE, AVOIDABLE ISSUE or LESSON:. It is then satisfied by names_tracked_item, which returns true if ANY dc-prefixed name appears anywhere in the file - and every sprint file names the task it just delivered. The check is satisfied by construction. OBSERVED: every retro written today said FINDING. None matched. Three control defects, two migration-path findings and a keystone-coverage gap went into retro procedureText, the guard examined none of them, and D0131 - retro findings become tracked items - held in prose only. The guard also accepts its `changed` parameter and discards it (`let _ = changed`), which is the tell: it was designed to ask whether THIS COMMIT adds a tracked item and never did. INVALIDATION - what it passed while broken: every retro since it was written, 500+ sprints. NOT RE-CHECKED; a sweep for analyze-method gates whose commit added no Issue or task is possible from git and is the honest follow-up. It is also a WARNING, not a violation, so even a match blocks nothing. RESOLVER: dcRetroFindingsRoute.";
        :>> discoveredInField = false;
        :>> severity = Severity::High;
    }
    #Resolves dependency from dcRetroFindingsRoute to issue335;

    part issue336 : Issue {
        :>> id = "f39529df-768e-493d-926a-2f8c861c3de1";
        :>> title = "A process is a document with an optional guard - steps bind to no predicate, and analyses live in String fields no control can read";
        :>> createdAt = "2026-09-01";
        :>> createdBy = "claudeOpus5";
        :>> description = "PANEL FINDING, High, two critiques with one root (rigorProcessAuthorityCritique, rigorFactLifecycleCritique). A process in keel is a document with an optional guard, not a machine. MEASURED from keel hardening: 37 processes, 16 assert at least one guard, 10 are declared human-judgment, 11 are UNDECLARED with no guard and no reason - and five of those eleven were authored in the last two days, so authoring is outrunning enforcement and only the author's memory converts one into the other. 'Enforced' means the process asserts a guard SOMEWHERE, not that each step has a check: a ProcessStep is an actionText paragraph with no binding to any predicate, so a process cannot refuse to advance past a skipped step. Only agile-workflow's ceremony steps have per-step gates, which is the one place `keel advance --to` can refuse. THE SAME ROOT UNDERNEATH THE FACT-SLIPPING. Everything analytical in the model is a String field - rationale, consequences, description, procedureText, actionText - and no control can read a String for meaning. A Decision's clauses are prose, so partial delivery is invisible. A retro's findings are prose, so routing is a grep. A resolver's fit is prose. The human's phrase was exact: analyses of facts slip - not out of the repository, where they are all committed, but out of the ENFORCEABLE model into fields only a reader can check. THIS IS WHY THE PROCESS AUTHORITY IS WEAK: a well-written custom process ships as a unit, lands with its skill, and is followed exactly as far as the reader chooses. The process-enforcement contract's own comment names the missing mechanism - 'the constraint IS checkable and no guard was written' - and cannot make anyone write one. RESOLVER: dcProcessStepsBindToChecks - a PROPOSAL to the human, because both halves are schema questions under the frozen core.";
        :>> discoveredInField = false;
        :>> severity = Severity::High;
    }
    #Resolves dependency from dcProcessStepsBindToChecks to issue336;

    part issue337 : Issue {
        :>> id = "2f7526e2-db6d-4c6a-bcea-eb10267e2846";
        :>> title = "The session's actor never reaches the hooks, so hook-run guards attribute every edit to the machine binding";
        :>> createdAt = "2026-09-01";
        :>> createdBy = "claudeOpus5";
        :>> description = "PANEL FINDING, High (rigorSelfReferenceCritique), and a CORRECTION of issue332. issue332 says the ownership guard reads the machine's bound actor rather than the session's. Read at source, that is wrong: actor::resolve (actor.rs:97-112) prefers explicit, then KEEL_ACTOR, then the binding, and ownership calls it (guards.rs:2498). The guard is correct. THE ACTUAL DEFECT: the Stop hook is spawned by the harness in an environment where KEEL_ACTOR was never set - it is exported per-command inside the session's shell - so resolve has nothing to prefer and falls through to the machine binding. This machine is bound to claudeFable5; this session is claudeOpus5. Result: 22 edits attributed to the wrong actor and 12 items the session owns flagged as non-owner edits, burying the 10 real ones. WHY THE CORRECTION MATTERS beyond accuracy: issue332 gave 'guard source under the keystone lock' as the reason for carrying rather than fixing. actor.rs and the hook plumbing are NOT on D0209 clause 2's surface. The reason was wrong, so the carry was unjustified - the process I wrote today names that as the unacceptable case. RESOLVER: dcSessionActorReachesHooks - a session-scoped binding, keyed by the session id the hook payload already carries, that resolve reads between KEEL_ACTOR and the machine binding.";
        :>> discoveredInField = false;
        :>> severity = Severity::High;
    }
    #Resolves dependency from dcSessionActorReachesHooks to issue337;

    // issue337 CORRECTS issue332: the guard's predicate is right, the session's identity never
    // reaches the hook. issue332 stays as the record of what was believed and why it was wrong.
    #Supersede dependency from issue337 to issue332;
    // ...and the fix that resolved issue337's correct diagnosis resolves issue332's wrong one: the
    // defect they both point at is gone. issue332's text stays as the record of what was believed.
    #Resolves dependency from dcSessionActorReachesHooks to issue332;

    // ── issue330 resolved: the owner's word, and the mechanism that turned out to already exist ──
    verification issue330Accept : Test {
        :>> id = "e2b14c07-58d9-4f36-a0c1-71f8b2d4e953";
        :>> title = "The owner authorises the ten renderer edits (human word, recorded verbatim)";
        :>> createdAt = "2026-09-01"; :>> createdBy = "claudeOpus5";
        :>> method = VerificationMethod::confirmation;
        :>> procedureText = "wweatherholtz, 2026-09-01, in response to the issue330 decision page listing the ten exact edits and three options. Their words, verbatim and in full: 'accept. continue'. READ AS: the owner authorises the ten renderer edits to their Viewpoints and directs the work to proceed - the page's recommended option was that they make the edits themselves, and 'continue' says they want them made. WHAT THIS DID NOT NEED TO DO, found after they answered: D0108's own sanctioned exemption already covered this case. The ownership guard suspends for a commit that co-commits a migration transform under .engine/tools/migrations/, because D0067 REQUIRES bulk transforms that cross every ownership boundary at once - and a mechanical rename of 86 call sites across 31 files is exactly that shape. The first attempt had done the rename with a scratchpad script, which is why the exemption did not apply and the human was asked. Their authorisation is recorded because it was given; the mechanism that lands the change is the committed transform, which is what D0067 asked for all along.";
    }
    part issue330AcceptR1 : TestResult { :>> id = "f3c25d18-69ea-4047-b1d2-82a9c3e5fa64"; :>> outcome = VerdictKind::pass; :>> judgedAgainst = "3bb0125"; :>> judgedAt = "2026-09-01"; :>> judgedBy = "wweatherholtz"; }
    #Verify dependency from issue330Accept to issue330;

    part issue338 : Issue {
        :>> id = "e4f198cb-0b4e-4355-a6cf-0935ca64b800";
        :>> title = "D0273 promised fewer than 25 verbs and the lens collapse yields 66 - the criterion was never derived from the Decision's own measurements";
        :>> createdAt = "2026-09-01";
        :>> createdBy = "claudeOpus5";
        :>> description = "D0273's consequences state that the visible verb count falls BELOW 25. The lens collapse landed at 66: 100 dispatch arms, minus 35 lens verbs moved into the `keel show` router, plus the router itself. Read back from `keel hardening` helpCoverage.dispatched, not estimated. THE DEFECT IS IN HOW THE CRITERION WAS WRITTEN, not in the work. D0273's own context section measured '43 read-only lenses of roughly 111 dispatch arms', which already implies the post-collapse count is near 66 - the arithmetic was available in the same paragraph and was not done. So an accepted Decision carries a verification criterion that its own numbers refute, and had nobody checked, the collapse would have been recorded as meeting it. Found by the person doing the work reading the number back; no control compares a Decision's stated criterion against its stated measurements, and none plausibly could, since both are prose. WHAT THIS IS NOT: a reason to redo the collapse. The lens family - the thing the human named, 'variations of an idea cemented as separate cli hooks' - is collapsed and byte-identical. The gate, record and orient/surface families were never measured or argued in D0273, so reaching 25 means either collapsing them too (a second breaking change) or amending the Decision to state what was achieved. RESOLVER: dcRemainingCliFamilies - measure the remaining families and put the choice to the human as a fork. Sprint 512's retro recorded the generalisable rule: a numeric criterion in a Decision must be DERIVED from the numbers already in that Decision, or it is a wish with a number attached.";
        :>> discoveredInField = false;
        :>> severity = Severity::Medium;
    }
    #Resolves dependency from dcRemainingCliFamilies to issue338;

    part issue339 : Issue {
        :>> id = "69935de0-41da-4cc3-9066-641ef6893e23";
        :>> title = "A test exported from the live repository on every run, bumping the real install record";
        :>> createdAt = "2026-09-01";
        :>> createdBy = "claudeOpus5";
        :>> description = "A TEST WROTE TO THE LIVE WORKING TREE ON EVERY RUN. adoption_check_can_fail.rs:54 ran `keel process export intake` with cwd None; `export` locates the repository root and, per D0183 ('the ORIGIN records its own exports too'), writes .engine/contracts/installed-units.toml. So each `cargo test` that found the intake unit's content changed bumped its version in the REAL project - v43 became v44 during today's suite, and the file showed up modified after staging with no human or command having touched it. WHY IT MATTERS beyond hygiene: a version number in a committed contract is a fact consumers compare against (srDriftIsReportedPerUnit). A test silently advancing it means the number stops meaning 'the content changed and someone published' and starts meaning 'the suite ran'. It also produced a phantom out-of-band write that the hook flagged as possibly human-authored, which cost a diagnosis. THE GENERAL SHAPE, and it is worth a sweep rather than one fix: any test that invokes the binary with no cwd inherits cargo's, and every keel command that walks to a repository root will find the live one. The other export-invoking tests (federation, library_publish, capability_refusal_bites) pass an explicit fixture; this one did not. RESOLVER: dcTestsDoNotWriteTheLiveTree.";
        :>> discoveredInField = false;
        :>> severity = Severity::Medium;
    }
    #Resolves dependency from dcTestsDoNotWriteTheLiveTree to issue339;

    part issue340 : Issue {
        :>> id = "1039a969-82ac-494f-acc2-f5ec0ea152e6";
        :>> title = "publish commits a manifest-only change at an unchanged version with a message that reads as a duplicate publish";
        :>> createdAt = "2026-09-01";
        :>> createdBy = "claudeOpus5";
        :>> description = "The library log carries two commits titled 'publish library-stewardship v2' (643a188 and 707fefe), and the same for control-propriety v1 and github-intake v1 - three units re-published today at unchanged versions. NOT a version defect: next_unit_version compares file hashes and the files were identical, so holding the version was right. The manifest changed - every unit.toml gained `commands = [...]` when D0252 clause A's command declaration landed - and publish commits whenever the bundle differs, without saying WHAT differed. The issue302 no-op check reads 'did the files change', not 'did the bundle change', so a manifest-only change is neither a no-op nor a version bump and the commit message cannot tell the reader which it was. Low, one-time per manifest schema change, and worth fixing because a library log that says the same version was published twice is a log a consumer learns not to read. RESOLVER: dcPublishSaysWhatMoved.";
        :>> discoveredInField = false;
        :>> severity = Severity::Low;
    }
    #Resolves dependency from dcPublishSaysWhatMoved to issue340;

    part issue341 : Issue {
        :>> id = "19e1f750-9937-4bcb-8e1e-72001f5fd6b6";
        :>> title = "An accepted Decision's text can change after sign-off and still compute as accepted: acceptance binds to a commit, never to what was accepted";
        :>> createdAt = "2026-09-02";
        :>> createdBy = "claudeOpus5";
        :>> description = "MEASURED: keel-cli/src/govern.rs acceptance_judged_against extracts the acceptance's commit SHA and that is the only binding an acceptance has to what was accepted; a grep of the write path and guards for a body digest or an edited-after-acceptance check finds nothing (checked 2026-09-02 during the agent-corral landscape spike). So the text a human signed at commit X and the text the tree carries at HEAD can differ, and the Decision still computes as accepted. keel refuses this exact drift elsewhere: evidence whose judgedAgainst no longer resolves is suspect, and a confirmation flip on chat words carries a quote receipt (D0198). Consent has no such receipt. WHY IT MATTERS: the landscape names this the rug-pull class (mcp-scan: the tool description you consented to is not the one that executes) and the operand-binding gap (PAuth: OAuth grants an operator, the call carries operands). A model that owns a Decision may edit its fields under D0108 - the owner of most Decisions is the AI that proposed them. FIX: dcAcceptanceBindsToTheText - compare the accepted fields at the acceptance SHA with HEAD, violation on difference, acceptance reported suspect.";
        :>> discoveredInField = false;
        :>> severity = Severity::High;
    }
    #Resolves dependency from dcAcceptanceBindsToTheText to issue341;

    part issue342 : Issue {
        :>> id = "e2269ef3-26b5-4708-b8aa-83b1c25df255";
        :>> title = "Standing consent is revision-unbound and non-expiring: an auto-acceptance names D0207 but not the revision of the rule or the guard set it was granted under";
        :>> createdAt = "2026-09-02";
        :>> createdBy = "claudeOpus5";
        :>> description = "MEASURED: the auto-accept step in .github/workflows/decision-issue.yml writes the AUTO-ACCEPTED token, the standing words verbatim and the override thread URL; it records neither the commit of the D0207 file nor the guard count or adherence revision at acceptance time (checked 2026-09-02). So a standing consent granted under one rule set silently covers acceptances under any later rule set, and an override on the thread is not bound to the acceptance it overrides. WHY IT MATTERS: every product in the landscape spike that has thought about consent lifecycle has moved AWAY from this shape - Entra Agent ID time-bounds grants and re-opens approval on extension; CapLease shows even single-use tokens replay under agent retry without durable state over the confirmation event; the IETF compliance-receipts draft makes policy_digest and expires_at mandatory. The unauthenticated commenter on the override thread asked precisely this question, which the recording Action correctly refused to record - the refusal was right, the question stands. THIS IS A FORK, not a defect with one fix: the human chose standing consent (D0207) knowingly, and the options trade interruptions against attributability. FIX: dcConsentIsScopedAndExpires writes the costed proposal and puts it to the human.";
        :>> discoveredInField = false;
        :>> severity = Severity::Medium;
    }
    #Resolves dependency from dcConsentIsScopedAndExpires to issue342;

    part issue343 : Issue {
        :>> id = "fbca1f37-5314-44a7-945d-d2e1575248d7";
        :>> title = "A done task's own DoD can be rewritten after its pass and the task stays done: criterion drift is computed for dependencies only, never for the task itself";
        :>> createdAt = "2026-09-02";
        :>> createdBy = "claudeOpus5";
        :>> description = "MEASURED 2026-09-02 by experiment: a done task's own DoD (instanceAwareDoD) was widened with an unverified claim, keel orient was run, the task appeared in no suspect entry and remained done; the edit was reverted. By reading: orient.rs criterion_suspects iterates data.deps only - a dependency's criterion changing since the verified commit makes the dependent suspect, the task's own criterion changing does not. proactive.rs names own-criterion drift as a post-edit ADVISORY, non-blocking, so nothing computed carries it forward. WHY IT MATTERS: the human's direction is trust-but-verify with the DoD as the gold standard; a standard the owner may rewrite after the pass, with the pass still standing, is not a standard. Under D0108 the owner of most tasks is the AI that will pass them. Same class as issue341 (acceptance binds to a commit, not to the accepted text), for the DoD instead of the Decision. FIX: dcOwnDoDDriftIsSuspect - compare own criterion at judgedAgainst with HEAD in criterion_suspects.";
        :>> discoveredInField = false;
        :>> severity = Severity::High;
    }
    #Resolves dependency from dcOwnDoDDriftIsSuspect to issue343;

    part issue344 : Issue {
        :>> id = "6ae2e51b-0677-4198-8a95-cfd0786dedde";
        :>> title = "CLAUDE.md invariant 8 states the CliCommand facts exist; D0271 deferred them and D0273 never picked them up - zero instances in the tree";
        :>> createdAt = "2026-09-02";
        :>> createdBy = "claudeOpus5";
        :>> description = "MEASURED 2026-09-02: grep for CliCommand instances across .engine, .tracking and keel-cli/src finds only the schema (cli.sysml) and two Decisions; zero instances. D0271 says so itself - 'NOT YET AUTHORED: the 90 instances and the two-way guard ... held until the human answers whether the lens family collapses'. The human answered (D0273), the collapse landed (65 commands, 35 lenses, held equal to dispatch by a unit test), and the instances were never authored. CLAUDE.md invariant 8 nevertheless states 'Every command is a CliCommand carrying its family, effect and stability' as a present fact. WHY IT MATTERS: a doc claim ahead of reality is the class D0105 and doc-sync exist to prevent; and these facts are the source the computed control structure needs to tell a write action from feedback. FIX: dcCliCommandFactsAuthored - author the instances from the dispatch, guard both ways, correct the invariant's wording and count in the same commit.";
        :>> discoveredInField = false;
        :>> severity = Severity::Medium;
    }
    #Resolves dependency from dcCliCommandFactsAuthored to issue344;

    part issue345 : Issue {
        :>> id = "00b6c2c9-b173-4ba8-83d3-1ffca59505fc";
        :>> title = "priority-inversion asks the author to 'say so' and reads nothing they could say it in - a deliberate ranking cannot be recorded";
        :>> createdAt = "2026-09-02";
        :>> createdBy = "claudeOpus5";
        :>> description = "MEASURED 2026-09-02: guards.rs priority_inversion emits 'if that is deliberate say so, otherwise reorder' and consumes no edge, marker or field in which it could be said; 30 warnings stood after the human's stated first step (st066) was ranked at the head, and the reason - a recorded Statement - had no way to reach the guard. A warning nobody can discharge trains blindness to the ones they can (the actors guard says this about itself). FIX: dcDeliberateRankIsRecorded - a #PrioritizedBy edge to the ranking Statement or Decision, read by the guard.";
        :>> discoveredInField = false;
        :>> severity = Severity::Low;
    }
    #Resolves dependency from dcDeliberateRankIsRecorded to issue345;

    part issue346 : Issue {
        :>> id = "cb8dfb2b-2a85-4f17-8add-376d707c5423";
        :>> title = "record decision --from accepted an unknown marker silently and wrote an unmarked Decision - the process-change guard then refused the edit it was meant to authorise";
        :>> createdAt = "2026-09-02";
        :>> createdBy = "claudeOpus5";
        :>> description = "MEASURED 2026-09-02 while recording D0283: the --from file carried marker: prospective-change; the Decision was written with NO marker and no message; the process-change guard then refused the co-committed guards.rs edit for want of a marker. main.rs record-decision recognised only process-change and safety-change and treated anything else as none. D0282 (2026-09-02) landed unmarked the same way and, being accepted history, stays as written. A write path that drops a field silently is the issue118 class on the command line. FIX: dcUnknownMarkerRefused - refuse by name, write nothing; test in the same commit.";
        :>> discoveredInField = false;
        :>> severity = Severity::Medium;
    }
    #Resolves dependency from dcUnknownMarkerRefused to issue346;

    part issue347 : Issue {
        :>> id = "3fe6c2a4-76c5-4ac7-84ff-d0fa786f8aa5";
        :>> title = "Record-time standing consent (D0291) can auto-accept a Decision derived from an untrusted story, laundering D0264's plan-only tier";
        :>> createdAt = "2026-09-03";
        :>> createdBy = "claudeOpus5";
        :>> description = "FOUND while triaging twelve untrusted Statements (public repo, D0264) the same hour D0291 landed. D0264 says an untrusted story may reach work only through a Decision a human accepts; guard 56 checks a Decision is among the story's targets. D0291 makes keel record decision accept every NON-FORK Decision at record time under standing consent. Composed, a non-fork Decision proposed from an untrusted story is accepted by the agent's own record call, with no human act - the guard sees an accepted Decision and is satisfied, and D0264's plan-only tier is laundered through standing consent. Not yet exercised: the twelve stories are triaged and unrouted, and their reporter is the project owner. But the path exists. FIX: dcUntrustedTaintClosure already charters the taint walk from sourceTrust = untrusted through #DerivedFrom/#Implicates; record time must consult it - a Decision derived from an untrusted story is a FORK by construction (the human chooses), never auto-accepted.";
        :>> discoveredInField = false;
        :>> severity = Severity::High;
    }
    #Resolves dependency from dcUntrustedTaintClosure to issue347;

    part issue348 : Issue {
        :>> id = "8725fcd4-c00d-43b7-a3f1-8d79ef9af091";
        :>> title = "The generated hooks resolve keel from PATH before the pin, so a project's turns can run a different engine vintage than its gates";
        :>> createdAt = "2026-09-03";
        :>> createdBy = "claudeOpus5";
        :>> description = "GH#43 (st086, untrusted, owner's own downstream report). Every hook claude_surface generates opens by taking KEEL_BIN else `command -v keel` - PATH first - while the scaffolded pre-commit hook probes .keel/bin/keel before PATH (D0230). Two resolution orders for one pin: a project pinned on purpose ran its turns on an unreleased PATH build. This is the D0251 skew the pin exists to prevent, at the turn boundary. Resolver: dcHooksResolveThePinFirst.";
        :>> discoveredInField = false;
        :>> severity = Severity::High;
    }
    #Resolves dependency from dcHooksResolveThePinFirst to issue348;

    part issue349 : Issue {
        :>> id = "21eaf3df-2c39-45dc-a37b-6b4d81168a63";
        :>> title = "keel migrate silently deletes project-authored sections in engine-shipped contract files";
        :>> createdAt = "2026-09-03";
        :>> createdBy = "claudeOpus5";
        :>> description = "GH#44 (st085, untrusted, owner's own report). migrate rewrites .engine/contracts files wholesale; a project's own [exec-summary] section in unit-extras.toml was deleted and the published unit lost its declared payload silently. Adjacent to issue314 (project-owned contracts survive resync), which covered whole files, not sections within an engine file. Resolver: dcMigratePreservesProjectSections.";
        :>> discoveredInField = false;
        :>> severity = Severity::High;
    }
    #Resolves dependency from dcMigratePreservesProjectSections to issue349;

    part issue350 : Issue {
        :>> id = "c5f29355-9fc7-46af-8451-35214a53202d";
        :>> title = "adoption-check reports FAIL for every unit, and the reason it prints is a guard PASS line";
        :>> createdAt = "2026-09-03";
        :>> createdBy = "claudeOpus5";
        :>> description = "GH#45 (st084, untrusted, owner's own report, se-templates on 0.3.1). Every unit including known-good ones reported FAIL; the printed reason was a guard PASS line. The issue329 class (a substring test on guard text) in adoption_check.rs. A gate that is always red is routed around (D0214). Resolver: dcAdoptionCheckReportsTheRealVerdict.";
        :>> discoveredInField = false;
        :>> severity = Severity::High;
    }
    #Resolves dependency from dcAdoptionCheckReportsTheRealVerdict to issue350;

    part issue351 : Issue {
        :>> id = "183ecd77-1bcf-4c27-b5dd-94b099ed5e29";
        :>> title = "guard:claude-surface-drift byte-compares output-styles/keel.md against an embedded literal, so every fresh clone on Windows fails it";
        :>> createdAt = "2026-09-03";
        :>> createdBy = "claudeOpus5";
        :>> description = "GH#46 (st083, untrusted, owner's own report). sync-claude writes LF; git on Windows checks out CRLF; the guard byte-compares against the embedded literal and fails every fresh Windows clone. Resolver: dcSurfaceDriftIgnoresLineEndings.";
        :>> discoveredInField = false;
        :>> severity = Severity::High;
    }
    #Resolves dependency from dcSurfaceDriftIgnoresLineEndings to issue351;

    part issue352 : Issue {
        :>> id = "f4161393-22b6-4b8f-85ba-6acaafc57f87";
        :>> title = "A forward-only rule ships upstream's adoption date as a literal, so it is RETROACTIVE for every downstream project that migrates into it";
        :>> createdAt = "2026-09-03";
        :>> createdBy = "claudeOpus5";
        :>> description = "GH#47 (st082, untrusted, owner's own report, Penumbra 0.3.0 -> 0.3.1). Two rules carry acceptQuotesDelegatedWords(2026-08-22) / confirmationQuotesOrAttested(2026-08-23): this repo's dates, shipped, so every downstream project is retro-failed from the day it migrates. The general form of issue068. Resolver: dcForwardOnlyCutoffIsTheProjectsOwn.";
        :>> discoveredInField = false;
        :>> severity = Severity::High;
    }
    #Resolves dependency from dcForwardOnlyCutoffIsTheProjectsOwn to issue352;

    part issue353 : Issue {
        :>> id = "f1c13472-4838-41f2-a4ef-286903b43c66";
        :>> title = "keel append-result inserts the TestResult INSIDE a multi-line verification block, and the error it causes points at the wrong thing";
        :>> createdAt = "2026-09-03";
        :>> createdBy = "claudeOpus5";
        :>> description = "GH#48 (st081, untrusted, owner's own report, Penumbra 0.3.1). The insert point is the line matching `verification <T>DoD : Test {`, correct only when the DoD is a one-liner; a multi-line DoD gets the result inserted inside the block and validate's error names the wrong construct. Resolver: dcAppendResultFindsTheClosingBrace.";
        :>> discoveredInField = false;
        :>> severity = Severity::High;
    }
    #Resolves dependency from dcAppendResultFindsTheClosingBrace to issue353;

    part issue354 : Issue {
        :>> id = "57a4fd46-ab2e-406c-b3bb-4a848a94a5ba";
        :>> title = "add-task's def lookup breaks on a DoD whose string contains a block-opener brace: the write path scans braces without honouring strings";
        :>> createdAt = "2026-09-03";
        :>> createdBy = "claudeOpus5";
        :>> description = "FOUND 2026-09-03 while routing the intake: keel add-task refused with 'action def not found: EngineBuild' after a DoD was recorded whose text contained the literal characters of a block opener inside its string (the phrase verification T DoD colon Test followed by an open brace). keel check and keel validate both reported the file clean - the real parser respects strings - but the write path's own scan (write.rs parse_file / action_def_exists) does not, so the def vanished from its view and every subsequent add-task failed. Bisected: removing that one DoD line restored add-task. ESTABLISHED against the source 2026-09-03 (write.rs find_action_def_close): the scan counted every brace character, so a DoD string containing a brace pushed the depth off by one. TWO SYMPTOMS from one scan, depending on file shape: in this repository's backlog the def's close was never found and add-task REFUSED; in a small fixture the scan overshot to the package close and the next task was written at PACKAGE LEVEL, outside its def, silently - the misplacement is the worse symptom and was found only by reproducing on both shapes. The real keel_parser was never at fault (keel check and whats-next saw the def throughout). Same scanner class as GH#48 / issue353 (the result insertion point). Resolver: dcAppendResultFindsTheClosingBrace - one string- and comment-aware scanner for both.";
        :>> discoveredInField = false;
        :>> severity = Severity::High;
    }
    #Resolves dependency from dcAppendResultFindsTheClosingBrace to issue354;

    part issue355 : Issue {
        :>> id = "a7147f16-6ce5-485d-9a2e-dc79ac5c8d03";
        :>> title = "Deactivating a process turns off its guard but still deploys its SKILL, so an agent is advertised a channel the project switched off";
        :>> createdAt = "2026-09-03";
        :>> createdBy = "claudeOpus5";
        :>> description = "GH#49 (st080, untrusted, owner's own report, Penumbra 0.3.1). sync-claude builds the surface from the skills registry and consults activation nowhere; a deactivated process's skill stays deployed and an agent has no way to learn the state. Resolver: dcDeactivatedSkillSaysSo (option B: deploy it stated).";
        :>> discoveredInField = false;
        :>> severity = Severity::Medium;
    }
    #Resolves dependency from dcDeactivatedSkillSaysSo to issue355;

    part issue356 : Issue {
        :>> id = "07a5529a-e30f-40cd-b84b-19a25ee77386";
        :>> title = "red-yield obligation truncates its captured diagnostic at a fixed 726 chars, mid-token";
        :>> createdAt = "2026-09-03";
        :>> createdBy = "claudeOpus5";
        :>> description = "GH#50 (st079, untrusted, owner's own report). The Stop hook's obligation writer cuts description at a fixed width; three records at exactly 726 chars, mid-token. Resolver: dcRedYieldKeepsTheDiagnostic.";
        :>> discoveredInField = false;
        :>> severity = Severity::Low;
    }
    #Resolves dependency from dcRedYieldKeepsTheDiagnostic to issue356;

    part issue357 : Issue {
        :>> id = "5931f6dc-a850-4883-9279-9279ddb640a7";
        :>> title = "Two builds of the same version silently disagree on the .claude surface; drift report names no binary";
        :>> createdAt = "2026-09-03";
        :>> createdBy = "claudeOpus5";
        :>> description = "GH#51 (st078, untrusted, owner's own report). Version alone is not identity for a dirty build; two 0.3.1 binaries on one machine generated different surfaces and the drift report could not say which. Resolver: dcSurfaceStampNamesTheBuild.";
        :>> discoveredInField = false;
        :>> severity = Severity::Medium;
    }
    #Resolves dependency from dcSurfaceStampNamesTheBuild to issue357;

    part issue358 : Issue {
        :>> id = "b51c124b-2c0d-461c-9ae7-b715916648dd";
        :>> title = "Stop-hook advisory: configurable summary (outstanding-decisions count + names) instead of the [oversight] nag";
        :>> createdAt = "2026-09-03";
        :>> createdBy = "claudeOpus5";
        :>> description = "GH#52 (st077, untrusted, owner's own report). The per-turn [oversight] advisory reads as noise; the owner wants one line with the outstanding decisions and how to accept. Resolver: dcStopAdvisoryIsOneLine.";
        :>> discoveredInField = false;
        :>> severity = Severity::Low;
    }
    #Resolves dependency from dcStopAdvisoryIsOneLine to issue358;

    part issue359 : Issue {
        :>> id = "faa82bb8-cc34-48b1-8761-33c7b035f59b";
        :>> title = "keel accept from a TTY writes --note bare, but acceptQuotesDelegatedWords needs a single-quoted span - so the one command only a human may run lands red";
        :>> createdAt = "2026-09-03";
        :>> createdBy = "claudeOpus5";
        :>> description = "GH#53 (st076, untrusted, owner's own report, Penumbra 0.3.1). The human ran keel accept six times from their own terminal with a plain-sentence note; all wrote; the guard then reported six violations for want of a quote receipt. The TTY IS the gesture the rule already accepts when cited - the command did not cite it. Resolver: dcTtyAcceptCitesTheGesture.";
        :>> discoveredInField = false;
        :>> severity = Severity::High;
    }
    #Resolves dependency from dcTtyAcceptCitesTheGesture to issue359;

    part issue360 : Issue {
        :>> id = "2d871d6a-bc1e-4872-b2f7-7078cc74c001";
        :>> title = "keel land has no evidence the suite ran at HEAD: a sprint landed on guards alone and CI was red for twenty minutes on a test the suite runs locally";
        :>> createdAt = "2026-09-03";
        :>> createdBy = "claudeOpus5";
        :>> description = "2026-09-02: sprint 521 (the stpa-diagram process) was landed after validate and guards but WITHOUT the full suite; the suite had last run at sprint 520. CI failed twenty minutes later on adoption_check_can_fail: the shipped process named a tool the scaffold did not ship - a test the suite runs locally in seconds. Nothing refused the land: keel land gates validate and guards, not the deliverable's tests, and no receipt records whether the suite ran on the tree being pushed. CI caught it, and CI is detective (branch protection requires no status check - computed, keel show control-structure). Recorded in the fix commit's message only, until now. FIX: dcLandRequiresASuiteReceipt.";
        :>> discoveredInField = true;
        :>> severity = Severity::Medium;
    }
    #Resolves dependency from dcLandRequiresASuiteReceipt to issue360;

    part issue361 : Issue {
        :>> id = "871a1757-0a84-436d-ac61-99d521b29792";
        :>> title = "Six enforced guards had no catalogue row and nothing checked the catalogue was complete (control added 2026-09-02; Issue recorded late)";
        :>> createdAt = "2026-09-03";
        :>> createdBy = "claudeOpus5";
        :>> description = "Found 2026-09-02 while authoring the CLI facts: six enforced guards (manifest-key-portability, control-map-reconciled, sprint-closure, untrusted-routing, control-defect-registry, cli-surface-declared) had no row in .engine/docs/guards.md, the file that calls itself the catalogue - five of them older than a week. doc-guard-count polices the total-count claim and nothing policed the rows. Fixed the same day with the rows and a test (guard_catalogue_tests::every_guard_has_a_catalogue_row) that fails the build on the next omission - the CONTROL half of D0047 - but no Issue was recorded, which is the RECORD half. Recorded now; the resolver is the sprint that fixed it.";
        :>> discoveredInField = false;
        :>> severity = Severity::Low;
    }
    #Resolves dependency from dcCliCommandFactsAuthored to issue361;

    part issue362 : Issue {
        :>> id = "77dea60d-488b-48ef-97d2-37d3d1669a1e";
        :>> title = "A fresh scaffold ships this repository's standing consent and recording delegations as its own policy";
        :>> createdAt = "2026-09-03";
        :>> createdBy = "claudeOpus5";
        :>> description = "Found 2026-09-03 (sprint 527 retro, recorded there as prose and nowhere else): keel init ships attestation-policy.toml with THIS repository's grants in it - standingConsent = d0207 and the two delegatedRecording lines, each quoting the owner's words from August - so a fresh project declares a standing consent and two recording delegations nobody granted it. Inert today only because the scaffold also declares no decider (two absences cancelling). The D0219 class: project data shipped as engine data. FIX: dcScaffoldShipsNoGrants.";
        :>> discoveredInField = false;
        :>> severity = Severity::Medium;
    }
    #Resolves dependency from dcScaffoldShipsNoGrants to issue362;

    part issue363 : Issue {
        :>> id = "409e6d40-d7f2-4620-99de-e4a5137fa41b";
        :>> title = "record decision cannot declare what a Decision supersedes or derives from, so a reversing Decision lands edgeless";
        :>> createdAt = "2026-09-03";
        :>> createdBy = "claudeOpus5";
        :>> description = "Found 2026-09-03 (sprint 526 retro, prose only): D0289 reversed layer 3 of D0178 and landed with no #Supersede edge, no dependency on D0192, no #DerivedFrom - the human asked whether it had to be superseded, which is how the gap was seen. record decision has no way to declare what a Decision supersedes or where it came from; decision-requirement-link warns only when the prose names an item by id. FIX: dcRecordDecisionDeclaresSupersedes.";
        :>> discoveredInField = false;
        :>> severity = Severity::Medium;
    }
    #Resolves dependency from dcRecordDecisionDeclaresSupersedes to issue363;

    part issue364 : Issue {
        :>> id = "f6b55dfb-877f-46c3-819f-53ef57adfbb4";
        :>> title = "retro-backlog under-reports: 'already tracked' is accepted as a justification without any item being checked, so retro findings go untracked";
        :>> createdAt = "2026-09-03";
        :>> createdBy = "claudeOpus5";
        :>> description = "CONTROL DEFECT (D0278), direction UNDER. The retro-backlog guard (guards.rs RETRO_NO_ITEM_JUSTIFICATIONS) accepts the phrase 'already tracked' as a justification for a retro that adds no item, without checking that anything tracks the finding. Established against the source, guards.rs:1611 and :1681: the justification match is a substring test and consults no item. INVALIDATES: every retro-backlog PASS on a retro carrying that phrase. Concretely observed this week: sprint 526's retro said the supersede-field gap 'belongs to issue336' (it does not; issue336 is about ProcessStep predicates) and sprint 527's retro said the scaffold-ships-grants finding 'belongs to dcVerificationByAuthority' (that task's DoD does not mention it) - both passed, and both findings were untracked until the human asked. NOT re-checked across earlier retros: a scan for the phrase is the first step of the fix. Registered in control-defects.toml so every retro-backlog verdict carries the note until fixed. FIX: dcRetroAlreadyTrackedMustName. SECOND SHAPE, found by the fix's own arming test: retro_texts split the sprint file on the WORD verification, so any retro whose text contained it was cut in half and never examined - 27 of 510 retro gates in this repository, 20 of them with no justification at all, passed unread. Fixed in the same sprint (blocks start only at a line-leading verification); the 27 are NOT re-checked here and the count is the invalidation.";
        :>> discoveredInField = false;
        :>> severity = Severity::High;
    }
    #Resolves dependency from dcRetroAlreadyTrackedMustName to issue364;

    part issue365 : Issue {
        :>> id = "916b17a2-ce1a-4527-b34d-8b0bd7a985d1";
        :>> title = "disableAllHooks in a repo-scope settings file silences every keel hook and the drift guard reports clean";
        :>> createdAt = "2026-09-03";
        :>> createdBy = "claudeOpus5";
        :>> description = "FOUND while answering st090 (would keel work better as an extension with forced hooks), 2026-09-03. CHECK: grep disableAllHooks over keel-cli/src and .engine/docs/guards.md returns nothing; the Claude Code settings reference documents disableAllHooks with scope 'any file' and hook lists MERGE across scopes, so a project-scope key turns off user-, plugin- and (absent allowManagedHooksOnly) managed-scope hooks too. MECHANISM: claude_surface.rs compares the keel-OWNED entries (hooks by event, outputStyle) and lets user entries survive by design; a foreign top-level key is a surviving user entry, so `'disableAllHooks': true` beside intact hook entries reads as NO DRIFT. CONSEQUENCE: the in-loop tier (post-edit fast gate, stop gate, protected-path check, pre-bash advisory) is silenced by one line the agent may write, with the guard that exists to notice hook-surface tampering reporting clean; CI still re-derives validate and every guard on the tree (the third leg holds), so dishonest state is caught at push, not at the edit - detection is delayed, not lost. This is the same class the landscape spike (D0282) named in Kiro: blocking hooks the controlled party can edit. PREVENTING CHANGE: dcDriftGuardRefusesDisableAllHooks. The wider question - hosting the hooks outside the agent's write path at all - is us090 / dcHooksOutsideTheAgentsWritePath, not this issue.";
        :>> discoveredInField = false;
        :>> severity = Severity::High;
    }
    #Resolves dependency from dcDriftGuardRefusesDisableAllHooks to issue365;

    part issue366 : Issue {
        :>> id = "0d451672-03a3-4be1-a548-afa0deabca10";
        :>> title = "record decision and add-task wrote unparsable files over a Windows path backslash and reported success";
        :>> createdAt = "2026-09-03";
        :>> createdBy = "claudeOpus5";
        :>> description = "FOUND 2026-09-03 recording D0296. CHECK: `keel record decision --from` with a context field containing the literal path C:/Program Files/ClaudeCode/managed-settings.json wrote the file, printed 'recorded' and 'accepted at record time', and the next `keel validate .` reported `0296-...sysml:18:2724: invalid escape sequence '/P'` - every guard that reads decisions then FAILED (acceptance-events, charter). MECHANISM: sanitize_field (write.rs) neutralises double quotes and newlines but not backslashes, and the record path writes without tokenizing the result. CONSEQUENCE: a write API whose contract is 'prose verbatim, safely' (issue255) produced an unparsable governance record and reported success; on a Windows host any pasted path does this. Same class as issue354 (structure vs text) on the WRITE side. PREVENTING CHANGE: dcSanitizeMakesBackslashesSafe - escape or replace, and tokenize-before-write so the command refuses instead of reporting a success validate will reverse.";
        :>> discoveredInField = false;
        :>> severity = Severity::High;
    }
    #Resolves dependency from dcSanitizeMakesBackslashesSafe to issue366;

    part issue367 : Issue {
        :>> id = "cf6322fe-abe5-420a-9169-751a2dfaf38a";
        :>> title = "the ranked recall payload is beaten by grep plus one hop on the linked-record set, and lost two hand-set answers two hops away";
        :>> createdAt = "2026-09-04";
        :>> createdBy = "claudeOpus5";
        :>> description = "FOUND 2026-09-04 by the corrected harness (issue296) on the first ranker that indexes bodies (issue295). CHECK: recall_bench.py, linked-record set, 50 cases: ranked KG 41/50 in a mean 21 shown rows; naive control 7/50; the SECOND control - the rarest-word grep hits plus everything they link to - 49/50 in a mean 16 UNRANKED candidates. The trivial listing beats the traversal-and-rank on the task the graph exists for, in a smaller set. On the 8-case hand-written set the same ranker scores 5/8 against the previous ranker's 7/8 (measured against a rebuilt shipped binary on the same day): both d0129 questions are lost because d0129 is two hops from every element that carries the words (requirement -> need -> decision) and the one-hop lift cannot reach it. MECHANISM: the walk expands from the 30 best lexical seeds and the lift spreads only one hop from seeds, so a target with none of the query's words competes with 29 lexically-matching seeds for ~20 rows; the control has one rare word, a handful of hits, and lists their links. CONSEQUENCE: the payload the human is handed is worse than what they would get by hand on this task shape, and the graph's traversal is not yet earning its place over grep. PREVENTING CHANGE: recallRanksLinkedRecordsAsWellAsGrepDoes; the harness is the arbiter and the hand set is read, not fitted.";
        :>> discoveredInField = false;
        :>> severity = Severity::Medium;
    }
    #Resolves dependency from recallRanksLinkedRecordsAsWellAsGrepDoes to issue367;

    part issue368 : Issue {
        :>> id = "987724d7-5f71-4fc2-9a30-fdb699b812c1";
        :>> title = "two computed views stamped viewStatus twice - a duplicate JSON key on the field that exists to be unambiguous";
        :>> createdAt = "2026-09-04";
        :>> createdBy = "claudeOpus5";
        :>> description = "FOUND 2026-09-04 while receipting issue285 from a live server: GET /api/computed/whats-next and /api/computed/verification returned a body beginning viewStatus computed, viewStatus computed - the same key twice. MECHANISM: those two views stamp their own status inside computed_binding and the choke point with_status (serve.rs) stamps every cached body again without looking. CONSEQUENCE: duplicate keys are accepted by most JSON parsers and resolved differently by each (first wins, last wins), so the one field the N-C2 requirement says every render path must carry unambiguously was the one field that was ambiguous; on the stale path the inner computed would have hidden the outer stale in a last-wins parser. PREVENTING CHANGE: with_status drops an inner viewStatus and re-stamps with its own verdict; the test with_status_never_duplicates_the_key covers the four body shapes including stale-over-computed. Fixed in the same sprint as dcEveryAdvertisedViewIsBound, which resolves it.";
        :>> discoveredInField = false;
        :>> severity = Severity::Low;
    }
    #Resolves dependency from dcEveryAdvertisedViewIsBound to issue368;

    part issue369 : Issue {
        :>> id = "84844a68-8160-4b46-8932-fa78108cca90";
        :>> title = "a launcher test fails intermittently under the full suite and passes alone - a control that lies one run in five";
        :>> createdAt = "2026-09-04";
        :>> createdBy = "claudeOpus5";
        :>> description = "FOUND 2026-09-04, twice in one day during full-suite runs: cargo test --release stopped early with one failure - once uncaptured (397 passed), once named: finish_writes_a_record_carrying_every_declared_field in tests/launcher_controls_actually_fire.rs. The test passes alone and in the following full run. A test that fails one run in five is a control that lies one run in five: a red suite the author re-runs to green trains everyone to distrust red, and a green suite that would have been red on the next run hides the defect it is there to show. MECHANISM: not yet established - the fixture is process-id-unique and the failure is intermittent under parallel test threads, so shared state (the gate finish runs, the ledger it reads, or the working directory) is the first suspect. PREVENTING CHANGE: dcLauncherFinishTestIsDeterministic - capture the failure text with --no-fail-fast, name the cause in the test, prove twenty consecutive runs.";
        :>> discoveredInField = false;
        :>> severity = Severity::Medium;
    }
    #Resolves dependency from dcLauncherFinishTestIsDeterministic to issue369;

    part issue370 : Issue {
        :>> id = "efaafb6e-0fa5-4122-b51b-51812636521a";
        :>> title = "twelve enforced guards had no constraint-def identity while the rules file said every guard has one";
        :>> createdAt = "2026-09-04";
        :>> createdBy = "claudeOpus5";
        :>> description = "FOUND 2026-09-04 while building the vintage fixture (issue265): guard-constraints.sysml states (D0195 clause 1) that EVERY enforced guard has a constraint-def identity - the model identity the control map, a unit's assert and the K8 capability handshake bind to. Computed from GUARD_NAMES against the file: 60 guards, 48 constraint defs, TWELVE guards without one - evidence-cited, gating-workflow-history, process-applicability, doc-guard-count, manifest-key-portability, control-map-reconciled, sprint-closure, untrusted-routing, control-defect-registry, cli-surface-declared, decision-amends-process, unit-extras-present. Eight predate guard 49; the last three are this week's. CONSEQUENCE: a unit could not claim those guards by assert, and the rule that says every guard has an identity was false on a fifth of them with nothing checking it. PREVENTING CHANGE: the twelve are added under D0302 within dcVintageFixture, the sprint that found them; the durable control is every_guard_has_a_constraint_def_identity in guards.rs, which computes GUARD_NAMES against the file's constraint defs and fails on any guard without one - built in the same sprint, so the file's rule is now held rather than stated.";
        :>> discoveredInField = false;
        :>> severity = Severity::Medium;
    }
    #Resolves dependency from dcVintageFixture to issue370;

    part issue371 : Issue {
        :>> id = "c8ae66e8-f272-4ca6-9a6c-bb6643d550e2";
        :>> title = "seventeen accepted Decisions carried text edited after acceptance - all editorial, none silently: found by the guard on its first run";
        :>> createdAt = "2026-09-04";
        :>> createdBy = "claudeOpus5";
        :>> description = "FOUND 2026-09-04 by the first run of guard acceptance-binds-to-text (D0308): 17 of 301 accepted Decisions carry decision, rationale or consequences text that differs from the text at the SHA their acceptance binds to. Every one is editorial, read by diff: rollout notes appended to consequences after acceptance (d0092 21a3c5f, d0093 90b29b8, d0095 e33148b, d0222 43a7b10); the acceptance-state sentence replaced or the word PROPOSED changed to ACCEPTED inside the text (d0112 a642269, d0130 7740eb0, d0131 ee2512d, d0132 d6f9da5, d0146 d0147 d0148 a6b7123, d0149 01fce65, d0151 1ba3c5c, d0153 8507239); guard counts renumbered when a guard was removed (d0263 6583e08, d0265 2ca2acb, d0266 429fc87). None changes what was agreed - and that is a judgment, which is why each is RE-BOUND with a recorded acceptance result naming the commit and the change, under the standing consent that covers non-fork acceptances, rather than allowlisted. Ten further Decisions read as drifted on the guard's first draft and were formatting only (indentation between plus-joined string segments) - the comparison now reads string values. PREVENTING CHANGE: dcAcceptanceBindsToTheText - the guard itself, hard, and keel accept --rebind as the only remedy path.";
        :>> discoveredInField = false;
        :>> severity = Severity::Medium;
    }
    #Resolves dependency from dcAcceptanceBindsToTheText to issue371;

    part issue372 : Issue {
        :>> id = "5a332da7-13ca-4bca-9ffb-efdf62bba8bd";
        :>> title = "already tracked was accepted eight times while the tracked item sat below the fold - the retro process flagged the heredoc defect and nothing made the flag escalate";
        :>> createdAt = "2026-09-05";
        :>> createdBy = "claudeOpus5";
        :>> description = "FOUND 2026-09-05 when the human asked why the heredoc defect was still occurring and whether retros were flagging issues. THEY WERE: dcPreBashSeesHeredocSource was created 2026-09-03 (sprint 531) as the resolver of a recurring heredoc failure, a memory said the same, and every retro afterwards wrote 'no new item - already tracked: dcPreBashSeesHeredocSource' - which the retro-backlog guard accepted, because D0294's fourth shape checks that a justification NAMES an existing item and nothing checks that the named item is being worked. The item had been placed below the High-issue resolvers to quiet a priority-inversion warning, and the defect recurred at least eight times in two days (sprints 540-550), each time caught by a wrong test result or an unparsable file rather than prevented. MECHANISM: 'already tracked' is a valid justification the FIRST time; the second time the same open item is named, the finding has recurred, and an item that keeps absorbing recurrences without moving is a reminder in an item's clothes (D0047) - and no control computed the count. CONSEQUENCE: the process that exists to turn recurring defects into controls accepted eight recurrences as tracked, and the human saw the defect keep happening. PREVENTING CHANGE: guard recurrence-escalates (D0310) - two or more retro citations of an open item is a violation unless the item is in the next three ready items or blocked on a proposed Decision; and the heredoc defect itself is closed by D0309's deny, which is dcPreBashSeesHeredocSource's delivery. Resolver: dcPreBashSeesHeredocSource, the item whose stasis is the defect.";
        :>> discoveredInField = true;
        :>> severity = Severity::High;
    }
    #Resolves dependency from dcPreBashSeesHeredocSource to issue372;

    part issue373 : Issue {
        :>> id = "227eb2d8-92df-42fe-804b-32952ba1e49b";
        :>> title = "a fork written without OPTION markers auto-accepts under standing consent - fork detection is lexical and the author holds the lexicon";
        :>> createdAt = "2026-09-05";
        :>> createdBy = "claudeOpus5";
        :>> description = "FOUND 2026-09-05 by stpa-self run 1 (UCA-R1, ucaRecordForkDisguised): standing-consent auto-acceptance at record time (D0291) decides fork-or-not by ONE lexical shape - deck::fork_options reads OPTION X (label) enumerations - so a Decision that weighs alternatives in prose without that marker auto-accepts on the spot, and a direction the human owns is recorded as accepted by an AI (EHZ3). The author controls the lexicon that decides whether the human is asked. No control detects the disguised shape; D0303's clause detector counts (1)(2) enumerations for a different purpose. PREVENTING CHANGE: dcForkShapeIsDetected - a wider fork detector that holds the Decision proposed and asks the author to write it as a fork or to say it is not one, measured for precision over the accepted corpus first. Constraint CC-R1 (ccRecordForkShape) is bound to this Issue until then.";
        :>> discoveredInField = false;
        :>> severity = Severity::High;
    }
    #Resolves dependency from dcForkShapeIsDetected to issue373;

    part issue374 : Issue {
        :>> id = "95eb87b3-0010-487a-94e3-0639f1cda8b9";
        :>> title = "an append-result receipt proves a sentence was typed, not that the run happened - a suite count was written before the suite finished (2026-09-04) and no control saw it";
        :>> createdAt = "2026-09-05";
        :>> createdBy = "claudeOpus5";
        :>> description = "FOUND 2026-09-05 by stpa-self run 1 (UCA-A1, ucaResultReceiptIsTestimony): `append-result --evidence` satisfies guard 52 (attestation-substance, D0232) with WHATEVER the agent writes after `// RAN:`. The receipt proves a sentence was typed, not that a run happened or finished. It happened in this tree on 2026-09-04: I wrote a suite count into a receipt while the background suite was still running, and only my own read-back caught it - no control did. The pass then computes completion from evidence that did not yet exist (EHZ4). PREVENTING CHANGE: dcExternalFactGate - a result class that closes only on an external fact keel queries (a CI run id for the judged SHA, verified by CI on push), never on the agent's assertion; the fork D0312 decides how far that authority model extends to the other methods. Constraint CC-A1 (ccResultReceiptIsExternal) is bound to this Issue until then.";
        :>> discoveredInField = true;
        :>> severity = Severity::High;
    }
    #Resolves dependency from dcExternalFactGate to issue374;

    part issue375 : Issue {
        :>> id = "66f65784-fae8-4e0f-8aab-ada90c5a1d5a";
        :>> title = "a DoD pass is judged against the commit BEFORE the work lands - judgedAgainst names a tree that does not contain what was verified";
        :>> createdAt = "2026-09-05";
        :>> createdBy = "claudeOpus5";
        :>> description = "FOUND 2026-09-05 by stpa-self run 1 (UCA-A2, ucaResultBoundToTheWrongTree): the ordinary DoD pass is recorded with `append-result --sha HEAD` while the verified work is still uncommitted, so judgedAgainst names a commit whose tree does not contain the work. Every reader that dereferences the SHA - deliverable-drift suspicion in orient, reverify, the attestation census - reads the claim against a tree where it is false, and drift is measured from the wrong baseline (EHZ4). This is the result-side twin of issue341, which D0308 closed for acceptances with the introducing-commit fallback. PREVENTING CHANGE: dcResultBindsToItsLandingCommit - the same fallback for results, and `append-result` naming the tree the pass will read against when the working tree is dirty. Constraint CC-A2 (ccResultBindsToLandingTree) is bound to this Issue until then.";
        :>> discoveredInField = true;
        :>> severity = Severity::Medium;
    }
    #Resolves dependency from dcResultBindsToItsLandingCommit to issue375;

    part issue376 : Issue {
        :>> id = "f3c5dbfd-2053-4618-b732-b982bfbbdcc7";
        :>> title = "Standing-consent auto-accept quotes this repository's human and ships its grants to every adopter (GH#57)";
        :>> createdAt = "2026-09-06";
        :>> createdBy = "claudeOpus5";
        :>> description = "GH#57 (st094, us093; untrusted tier, filed by the declared decider - D0314). The engine's standing-consent path fabricates an attestation in any project but this one. VERIFIED on main: keel record decision builds the AUTO-ACCEPTED note from a string literal of THIS repository's human's words (main.rs cmd_record, the D0291 arm); keel init ships attestation-policy.toml verbatim with standingConsent = d0207 and delegatedRecording = d0192 (the file is not an instance contract); keel migrate resyncs it wholesale (not in PROJECT_OWNED). A fresh project with one declared decider therefore auto-accepts every non-fork Decision in its decider's name, quoting consent that decider never gave - the D0106 / confirmation-authenticity class, produced by the tool. The library unit decision-channel v6 has the same defect in record_decision.sh (--by wweatherholtz, the quote inline), routed to dcLibraryUnitRetirement. Resolver: dcStandingWordsAreProjectLocal.";
        :>> discoveredInField = false;
        :>> severity = Severity::Critical;
    }
    #Resolves dependency from dcStandingWordsAreProjectLocal to issue376;

    part issue377 : Issue {
        :>> id = "5c603b85-3e2e-42c4-b951-57faccbdfc1c";
        :>> title = "migrate's removed-type scanner reads string literals as schema; a quoted Rust path blocks a healthy project (GH#59)";
        :>> createdAt = "2026-09-06";
        :>> createdBy = "claudeOpus5";
        :>> description = "GH#59 (st092, us091; untrusted tier, decider-filed). keel migrate refuses a healthy downstream project because a removed type is named in PROSE: types_as (migrate.rs) treats text ending in a colon before the name as a typing colon, so the Rust path separator in ureq::Agent passes, and step_removed_types scans whole lines including quoted string literals; REMOVED_ENUMS uses line.contains the same way. VERIFIED by reading the functions. There is no override surface, and the three workarounds (edit the critic's words, re-add a dead type, skip migrate) each corrupt something. Blast radius: every REMOVED_TYPES name that is an ordinary word (Task, Risk, Role). The reporter implemented and falsified the fix locally against d82c512. Resolver: dcRemovedTypeScannerReadsSchemaNotProse.";
        :>> discoveredInField = false;
        :>> severity = Severity::High;
    }
    #Resolves dependency from dcRemovedTypeScannerReadsSchemaNotProse to issue377;

    part issue378 : Issue {
        :>> id = "8e46cf98-63f1-4a6e-b2b3-d0f72825d772";
        :>> title = "pre-commit and Claude hooks probe a cache path init never writes, then fall back to PATH silently (GH#55)";
        :>> createdAt = "2026-09-06";
        :>> createdBy = "claudeOpus5";
        :>> description = "GH#55 (st096, us095; untrusted tier, decider-filed). Three surfaces enforce one pin and each resolves the binary differently: keelw and keel init write .keel/bin/<version>/<asset>; PRECOMMIT_HOOK (lib.rs) and claude_surface RESOLUTION_ORDER probe .keel/bin/keel(.exe) - a path nothing writes - and then fall back to PATH with no line saying which binary gated. VERIFIED on main. Measured downstream: the same tree passed under keelw (release) and failed 14 viewpoint-renderer violations under the hook (+dirty PATH build); the mirror case produced a false green. D0316 (this week) fixed the ORDER of the Claude hooks' probes and left the layout mismatch - the hooks now correctly prefer a file init never creates. The K2 comment in the hook says an absent gate must not pass silently; a wrong gate that passes silently is the same failure. Resolver: dcOneBinaryResolutionForEverySurface.";
        :>> discoveredInField = false;
        :>> severity = Severity::High;
    }
    #Resolves dependency from dcOneBinaryResolutionForEverySurface to issue378;

    part issue379 : Issue {
        :>> id = "c97accbf-d57b-43bd-936c-3b77b53a5924";
        :>> title = "init seeds the wrapper cache from whatever binary ran it, and keelw never verifies a cache hit (GH#54)";
        :>> createdAt = "2026-09-06";
        :>> createdBy = "claudeOpus5";
        :>> description = "GH#54 (st097, us096; untrusted tier, decider-filed). init_wrapper (main.rs) copies std::env::current_exe into .keel/bin/<CARGO_PKG_VERSION>/<asset> unconditionally, so a +dirty local build is filed as the pinned release for the project's life; keelw execs a cache hit without comparing it to keel-wrapper.toml, so the committed release checksum was in the tree and nothing ever checked the cached file against it. VERIFIED by reading both. Measured downstream: two binaries both answering 0.3.1, 900 KB apart, one spelling lenses keel show <lens> and one keel <lens>; the same tree gated clean on one and 14 violations on the other, and the project's CI (which downloads by tag) was the only honest signal. The wrapper's own header says trust-on-first-use is no verification; a seeded cache is trust-on-first-use by another route. Resolver: dcSeededCacheIsVerified.";
        :>> discoveredInField = false;
        :>> severity = Severity::High;
    }
    #Resolves dependency from dcSeededCacheIsVerified to issue379;

    part issue380 : Issue {
        :>> id = "75f228d9-80d7-4dda-b965-1402898d3872";
        :>> title = "onboard asserts a charter whose Decision the project does not hold; the overwrite behind it is fixed on main but unreleased (GH#56)";
        :>> createdAt = "2026-09-06";
        :>> createdBy = "claudeOpus5";
        :>> description = "GH#56 (st095, us094; untrusted tier, decider-filed). A v0.3.1 keel migrate rewrote a downstream project's chartered activation.toml with the engine's own - re-arming two processes the project had declined for stated reasons - and keel onboard then reported the set CHARTERED by d0226, a Decision the project does not hold. Two facts: (1) the overwrite is the issue314 class and is FIXED on main since 6583e08 (2026-08-30: activation.toml is in migrate's PROJECT_OWNED set), which is not an ancestor of v0.3.1 (c4d5dbf, 2026-08-29) - adopters on the release still have it until a release ships the fix; (2) the dangling charter is NOT fixed anywhere: nothing checks that charteredBy resolves in the project's own decisions, so onboard prints a provenance claim it cannot read as fact. The reporter's aside that engine-shipped viewpoint-registry.sysml carries this repository's owner ids is a real observation and is not resolved here. Resolver: dcCharterMustResolve.";
        :>> discoveredInField = false;
        :>> severity = Severity::High;
    }
    #Resolves dependency from dcCharterMustResolve to issue380;

    part issue381 : Issue {
        :>> id = "a9a871d6-f20e-4294-8a3d-6d9ba360efd9";
        :>> title = "the published decision-channel unit dies on its first run in a new repo: the keel-standing label is never bootstrapped (GH#58)";
        :>> createdAt = "2026-09-06";
        :>> createdBy = "claudeOpus5";
        :>> description = "GH#58 (st093, us092; untrusted tier, decider-filed). keel-lib's published decision-channel unit v6 ships decision-issue.yml, which bootstraps the labels blocks-work and decision, and open_decision_issues.py, which creates the standing thread with a third label keel-standing under check=True - so the channel's first run in any new repository dies inside gh issue create with a CalledProcessError that names no cause. VERIFIED: git ls-tree origin/main in the library shows both files under decision-channel/.github. It is masked by two earlier blockers (org allowlist, cargo build) and never reproduces in the origin repository, where the label exists. This repository deleted the channel in sprint 527 (D0291) and cannot republish the unit from a landed tree (library-stewardship rule 1); the same unit carries GH#57's fabricated-attestation script. Resolver: dcLibraryUnitRetirement - the unit is retired in the library with both reasons and its replacement, rather than patched in place.";
        :>> discoveredInField = false;
        :>> severity = Severity::Medium;
    }
    #Resolves dependency from dcLibraryUnitRetirement to issue381;

    part issue382 : Issue {
        :>> id = "3a1d6e58-1c4b-41b6-ab38-74a64af0ab91";
        :>> title = "The decision report's numbers were typed, not computed - three of five figures wrong within a day, and one claim simply false";
        :>> createdAt = "2026-09-06";
        :>> createdBy = "claudeOpus5";
        :>> description = "The standing decision report asserted numbers I typed rather than numbers the engine computed, and they were wrong within a day. Measured 2026-09-06 against the authored CLI facts: the page's diagram said 105 facts / 68 top-level / 34 read-only lenses; the tree says 106 / 69 / 33 - three of five figures wrong, because `keel suite` was added that morning. The page also asserted that the release workflow had not run since the last release and was unverified; `gh run list --workflow=release.yml` shows it ran 2026-08-29, succeeded in 4m56s, and cut that very release. It further priced the full suite at about four minutes, a number nothing records - suite.rs stamps only a wall-clock start, so the receipt has no duration. D0215 (accepted) states that a number the engine can compute may not be typed into the doc surface and that the enforcement is DELETION rather than reconciliation; the report is a doc surface and every number on it was typed. Resolver: dcDecisionReportIsArguable, whose contract requires the builder to emit a facts block and every digit-run in reader prose to trace to it.";
        :>> discoveredInField = false;
        :>> severity = Severity::High;
    }
    #Resolves dependency from dcDecisionReportIsArguable to issue382;

    part issue383 : Issue {
        :>> id = "515e08ce-6a90-40ca-af8b-c9228230279b";
        :>> title = "The report asked for ratification while framing it as a choice: half the queue already shipped, no panel offered a do-nothing option (recurrence of issue234)";
        :>> createdAt = "2026-09-06";
        :>> createdBy = "claudeOpus5";
        :>> description = "The standing decision report asked for ratification while presenting it as a decision. Measured over the five panels published 2026-09-06: 4 of the 8 items already ship in the binary - each Decision's own consequences says so in as many words ('the code ships because ...') - so the only act available to the reader on those four is REVERT, and no panel priced a revert; 0 of 5 panels offered a do-nothing option, so every choice set was a menu of the author's actions; and 2 of 12 option costs carried a quantity, the rest being adjectives. The owner's verdict (st099): 'mostly just administrative justification for the decision ... a decision isn't really to accept A decision or B decision'. THIS IS THE SECOND OCCURRENCE of the class: issue234 (2026-08-23) recorded the same complaint about decision cards, and its fix rendered the Decision's own context and decision text - more of the same prose inside the same frame - which is why it returned on a different surface. Per D0311 a finding named twice ranks High. Resolver: dcDecisionReportIsArguable, which requires a state chip (does this already ship, and what does the revert cost), a mandatory status-quo option, and a quantity in every cost.";
        :>> discoveredInField = false;
        :>> severity = Severity::High;
    }
    #Resolves dependency from dcDecisionReportIsArguable to issue383;

    part issue384 : Issue {
        :>> id = "e81ecd9f-fb0b-4024-9a9a-4b4dc2f8b5dd";
        :>> title = "migrate printed 40 passing lines and hid the violation that reverted the update";
        :>> createdAt = "2026-09-06";
        :>> createdBy = "claudeOpus5";
        :>> description = "keel migrate reported the first 40 lines of a failed gate, which are all PASS, so the violation that caused the revert was invisible - in the printed report AND in the recorded attempt, which stored the same clipped text. Found 2026-09-06 on the 0.4.0 version bump: ten migration tests failed, every printed guard read PASS, and the actual cause (claude-surface-drift: the plugin rendering was stale because the manifest stamps the engine version and the version had just changed) sat below the cut. Diagnosis took four extra passes and a --no-verify apply to see a line the tool already had. This is the red-yield truncation class one command over: a diagnostic clipped by POSITION rather than by RELEVANCE. Fixed here: migrate::gate_failure_lines selects the lines naming a failure, violation, error or refusal, caps at 20 with a count of the rest, and falls back to the tail when nothing names itself; the recorded attempt stores the same selection.";
        :>> discoveredInField = false;
        :>> severity = Severity::Medium;
    }
    #Resolves dependency from dcMigrateReportsTheFailingLines to issue384;

    part issue385 : Issue {
        :>> id = "f865aed2-beb0-43c4-8330-a0988d461a58";
        :>> title = "the release gate has no GitHub token, so the v0.4.0 tag published nothing";
        :>> createdAt = "2026-09-06";
        :>> createdBy = "claudeOpus5";
        :>> description = "The release gate is the one gating workflow that does not get a GitHub token, so the release for v0.4.0 gated red on a test that passes everywhere else and published nothing. WHAT HAPPENED: the tag v0.4.0 was pushed at 2c288d8. The release workflow's gate job ran cargo test --workspace --release with no env block. The federation suite's live-upstream claim shells out to gh api against this repository; gh refuses inside GitHub Actions without GH_TOKEN and prints 'To use GitHub CLI in a GitHub Actions workflow, set the GH_TOKEN environment variable'. The test failed 10 passed 1 failed, the gate concluded failure, the build matrix was skipped by needs: gate, and no release object exists for v0.4.0 - gh release view v0.4.0 returns 'release not found'. The same test passes on every push because ci.yml supplies github.token, with a comment explaining that the alternative, declaring the path offline, is strictly weaker. WHY IT SURVIVED: releases are rare. This is the issue260 class one workflow over - guard 51 was built after the release gate had been red for a whole release cycle undetected, and it checks that every gating workflow runs the guard set, not that the two gating workflows agree on the environment they run the same tests in. A test whose precondition is supplied in one workflow and not the other is green in the surface that runs constantly and red only in the surface nobody watches. WHY IT MATTERS BEYOND ONE TAG: the project's own engine pin was already committed as 0.4.0, and keelw resolves that pin to a release asset. A pin naming a version whose release does not exist means a fresh clone of this repository cannot obtain the binary its own gates require. PREVENTING CHANGE: the release gate gets the same token, with the reason recorded beside it as ci.yml does. The deeper control - that two gating workflows running the same command must supply the same environment - is a guard-51 extension and is proposed, not assumed, in the accompanying Decision.";
        :>> discoveredInField = false;
        :>> severity = Severity::High;
    }
    #Resolves dependency from dcReleaseGateHasTheToken to issue385;

    part issue386 : Issue {
        :>> id = "aafdd184-2394-40b5-9a9a-c04fbfdb3648";
        :>> title = "keel suite reports fail over a file lock: it rebuilds the binary running it";
        :>> createdAt = "2026-09-06";
        :>> createdBy = "claudeOpus5";
        :>> description = "keel suite rebuilds the binary that is running it, so on Windows it reports 'fail - 0 passed, 0 failed' over a file lock and writes that verdict into the receipt. WHAT HAPPENED: run as ./target/release/keel.exe suite . against a tree whose Rust sources had changed, the command shelled out to cargo test --release --no-fail-fast. cargo tried to relink target/release/keel.exe, which was the executing image, and Windows refused: 'error: failed to remove file ... Access is denied. (os error 5)'. No test ever ran. The command printed 'keel suite: fail - 0 passed, 0 failed' and wrote .keel/metrics/suite-receipt.toml over the deliverable fingerprint recording that outcome. Re-running from a copy - cp target/release/keel.exe target/release/keel-suite.exe - works, which is the same remedy CLAUDE.md already documents for keel serve (issue150). WHY IT MATTERS: this is not a false green, the verdict is fail, and D0356 already withdrew the push gate so no push is blocked by it. What is wrong is the KIND of the verdict. A run that never compiled the tests is recorded in the same field, with the same shape, as a run where the code is broken; the receipt claims the deliverable at that fingerprint was measured and found failing when it was not measured at all. The only evidence of the real cause is one line inside a log file the command names but does not read back. An operator who trusts the printed line concludes the code is red. THE FAMILY: issue150 is the same shape one command over - keel serve holds target/release/keel.exe and blocks every rebuild, which is why the handbook says to serve a copy. The generalisation neither has yet: a command that builds the deliverable must not be running from inside the directory the build writes. PREVENTING CHANGE: keel suite handles its own image - runs the tests from a copy, or detects that the executing binary sits in the target directory the build will write to and refuses with that named cause and the remedy, writing no receipt. A receipt is a claim that a measurement happened; a run that could not start has nothing to record.";
        :>> discoveredInField = false;
        :>> severity = Severity::Medium;
    }
    #Resolves dependency from dcSuiteSurvivesItsOwnImage to issue386;

    part issue387 : Issue {
        :>> id = "d39a21e9-34b9-415a-b035-518ddd7557c6";
        :>> title = "release-recorded binds a tag to a Release record by substring-in-title and can name the wrong one";
        :>> createdAt = "2026-09-06";
        :>> createdBy = "claudeOpus5";
        :>> description = "release-recorded binds a tag to a Release record by substring-in-title, so it can name the wrong record and did. WHAT HAPPENED: the v0.4.0 Release record was corrected to say it published nothing, and its title ended 'the payload shipped as v0.4.1'. The guard matches a tag to a record with title.contains(tag) and takes the FIRST match, so the tag v0.4.1 matched the v0.4.0 record and the guard warned that 'tag v0.4.1 points at b171cd7 but its Release item records commit 2c288d8 - the recorded release and the shipped tag disagree'. Both records were correct; the matcher was not. It was resolved by rewording the title, which fixes this instance and leaves the rule intact. THE DEFECT IS THE BINDING, NOT THE TITLE: a Release record identifies its tag by prose that happens to contain the tag string. That fails in two directions. A title mentioning any other version misroutes, as here - and a title is exactly where a release NOTE naturally mentions the previous or next version. And the containment is unanchored, so the tag v0.4.1 also matches a record titled v0.4.11, which will arrive on its own with no warning at all: the first matching record wins and the disagreement it reports will be about the wrong pair of commits. WHY IT MATTERS MORE THAN A WARNING: this guard is the one control asserting that what shipped is an authored fact (D0191). A control that can bind the wrong record produces two failure shapes, both bad: a spurious disagreement, which trains the reader to dismiss it, and a spurious AGREEMENT, where a record for one version silently vouches for another version's tag. PREVENTING CHANGE: bind the tag explicitly. A Release record should carry the tag it names as its own field, and the guard should match on that field rather than searching prose; a tag with no record naming it stays the violation it already is. Until then the containment should at least be anchored so one version string cannot match another's prefix.";
        :>> discoveredInField = false;
        :>> severity = Severity::Medium;
    }
    #Resolves dependency from dcReleaseRecordNamesItsTag to issue387;

    part issue388 : Issue {
        :>> id = "44e79606-df93-40ef-8fa8-6adfff739c22";
        :>> title = "a test asserts on the source text of the code it polices, and broke for the second time when that code moved";
        :>> createdAt = "2026-09-06";
        :>> createdBy = "claudeOpus5";
        :>> description = "A test in main.rs asserts on the literal SOURCE TEXT of the code it polices, so deleting that code breaks the test rather than the property - and this is the second time the same test has broken that way. WHAT HAPPENED: the_turn_boundary_blocks_only_on_dishonest_state reads its own file with include_str!('main.rs') and asserts that the source contains the string 'return match keel_cli::view::pending_acceptances(root)'. When D0359 removed the Stop hook's outstanding-decisions line, the code that string described stopped existing and the test failed - not because the property it names had been violated, but because the mechanism it had memorised was gone. The property, that only dishonest state can reach the block and that a green turn returns before it, was true throughout. WHY IT IS A RECURRENCE: the test's own doc comment says it replaced a predecessor that failed the same way, in its words 'a test bound to a mechanism rather than to a property', when the D0270 oversight advisory was deleted. Two deletions, two breakages, one file. Each time the fix was to rewrite the assertion; neither time was the pattern itself addressed. WHY IT MATTERS: a test that greps source text is not merely brittle - it inverts what a test is for. It passes when the text is present regardless of whether the behaviour holds, and it fails when the text moves regardless of whether the behaviour broke. It cost a full suite run to discover here, and its failure mode is indistinguishable at a glance from a real regression, which is worse in a codebase where the suite is the thing consulted before a release. PREVENTING CHANGE, and it is NOT what I first said. I claimed in the retro that this could not be mechanically forbidden. It can be detected: a check over the test surface for a test that both reads program source (include_str! of a .rs file) and asserts on substrings of it. What needs deciding is not whether it is detectable but whether the rule should be a refusal or a warning, because some source-reading checks in this repository are legitimate controls - the doc-claim and catalogue tests read files on purpose. The resolver weighs that; a behavioural equivalent for this specific test already exists in stop_says_nothing_about_decisions, which runs the binary against a real scaffold and asserts the empty output.";
        :>> discoveredInField = false;
        :>> severity = Severity::Medium;
    }
    #Resolves dependency from dcTestsBindToPropertiesNotSource to issue388;

    part issue389 : Issue {
        :>> id = "472fdbbe-f5e4-4771-9c3b-352240617bc8";
        :>> title = "the computed-facts script typed the release tag it measures against";
        :>> createdAt = "2026-09-06";
        :>> createdBy = "claudeOpus5";
        :>> description = "The computed-facts script TYPED the release tag it measures against, so every 'since the last release' number would have described a superseded release the moment a new one shipped. WHAT HAPPENED: facts.py asked git about one tag BY NAME in seven places - the tag date, the commit count, the day count, and the CI-run filter all named the same literal. While that tag was the newest release the numbers were right. v0.4.1 shipped this morning; the next run of the script would have reported the commits, days and CI runs since a release two versions back, and reported them with a `how` string that reads as authoritative precisely because it names a real git command anyone can run. Caught before publication only because I read the facts table and noticed the tag was stale. WHY IT IS THE DEFECT THE FILE EXISTS TO PREVENT: the script's own docstring says 'Nothing is ever guessed, and no answer is hardcoded', and the whole reason the standing brief is built from it is D0215 - a computable number may not be typed into a doc surface. A typed IDENTIFIER is the same failure one level up: the number is computed honestly, against the wrong thing, and nothing in the output says so. THE FIX: the tag is derived - `git describe --tags --abbrev=0 --match v*` - and emitted as its own fact, so a reader sees which release the numbers are about instead of trusting that the script and the repository agree. Each dependent fact carries the derived tag in its unit. THE CONTROL, and its own first failure: facts.py now refuses to run while its source contains a version literal. This is the one place where reading source text is the right implementation, because the property IS about source text. The first version of that check scanned only the source ABOVE itself - and the release facts sit below it, so it passed over exactly the defect it was written for. A deliberate probe caught it. The rule is now phrased without naming any version, so the whole file is scanned with nothing to exclude; verified clean, then failing on an injected literal, then clean again.";
        :>> discoveredInField = false;
        :>> severity = Severity::Medium;
    }
    #Resolves dependency from dcFactsNameNoVersion to issue389;

    part issue390 : Issue {
        :>> id = "ddc0fc38-b148-406c-8170-883b9dc7db28";
        :>> title = "an exhibit legend overprinted itself and a note was cut mid-word, both silently";
        :>> createdAt = "2026-09-06";
        :>> createdBy = "claudeOpus5";
        :>> description = "Two exhibit builders lost text without saying so: a legend overprinted itself and a note was cut mid-word at the canvas edge. WHAT HAPPENED, both found by rendering the standing brief and looking at it rather than by any check: (1) The stacked-bar legend placed its entries at even intervals - W divided by the number of segments - which assumes every label is the same width. The first real label set was not: 'already running, needs your signature' ran under its own count and under the swatch beside it, so two of the four categories were unreadable. (2) A logic exhibit's note is one SVG <text> element. SVG does not wrap, and a line longer than the viewBox is simply not drawn past the edge - no error, no ellipsis, no visual cue. The note ended '...rather than to a list someone m' and a reader would take that as the whole sentence. WHY THIS CLASS MATTERS MORE THAN ITS SEVERITY SUGGESTS: the entire argument for building these pages from data is that a figure cannot drift from the facts the way a hand-drawn one does. That guarantee covers the NUMBERS and stops at the LAYOUT - a figure can carry perfectly correct data and still tell the reader something false by hiding half of it. Silent truncation is the worse of the two, because an overlap looks broken and a truncation looks finished. FIXED: the legend advances by each entry's measured width and wraps to a second row rather than overrunning; the note is broken on word boundaries and the figure grows to fit the lines it needs. Both fixes are in the shared modules, so every future brief inherits them. WHAT IS NOT FIXED, and is the reason this is tracked rather than closed silently: nothing CHECKS that a rendered exhibit fits its canvas. The brief contract checks titles, labels and ids; it does not measure. A probe written during this fix - sum each text element's rendered length against the viewBox width - reported five false positives on right-anchored labels, so the naive version of that check is worse than none. Doing it properly means measuring in a browser, which the contract checker does not currently do; whether that is worth its cost is the resolver's question.";
        :>> discoveredInField = false;
        :>> severity = Severity::Medium;
    }
    #Resolves dependency from dcExhibitsDoNotHideText to issue390;

    part issue391 : Issue {
        :>> id = "8d6db4cb-6e4f-4f1d-bf40-ad2a0bd436ca";
        :>> title = "two failing recall cases return an element that answers the question and are scored misses";
        :>> createdAt = "2026-09-06";
        :>> createdBy = "claudeOpus5";
        :>> description = "In two of the three hand-set cases still failing, the payload contains an element that ANSWERS the question and is scored a miss, because ground truth names one specific record. WHAT THE HARNESS MEASURES: for each of eight hand-written questions, is the element named as ground truth among the rows the payload shows. Ground truth is fixed before the run and must not be refitted - that rule exists for good reason and is not in question here. WHAT WAS OBSERVED, on the current ranker, both checkable by re-running the two prompts: (1) 'why must we never rebase or force-push?' - ground truth d0129. The payload's FIRST row is the SystemRequirement srDcMergeOnlyIntegration, whose title reads 'Integration preserves commit ancestry - merge only, never squash, rebase' and whose rationale states why: a passing TestResult counts as done only while its judgedAgainst SHA resolves. A model handed that row can answer the question. It is scored 0 for that case, and d0129 sits two hops behind it as requirement --satisfy--> need <--derivedFrom-- decision. (2) 'what is an obligation and what discharges one?' - ground truth d0176. The word 'obligation' appears ONCE in the whole of d0176. The payload returns a UseCase titled 'A supervisor discharges accumulated authority in one batched sitting', the Need behind it, and d0276 (which is about an obligation record) - records that do discuss obligations. The target barely uses the query's vocabulary, so no lexical or graph mechanism reaches it; an alias under .knowledge/ would, and adding one for a test case is precisely the fitting the criterion forbids. WHY THIS IS RECORDED RATHER THAN ACTED ON: the fix that would raise the score is to loosen ground truth, and an agent editing the ground truth of the test it is failing is the worst available move. It is equally wrong to leave the observation in a chat message. So: the number stands as measured (6/8 against a required 7/8, recorded on the DoD result), and the QUESTION - whether 'the answering element' means the governing Decision specifically, or any element that answers the question - is a measurement-definition question for the human. WHAT WOULD SETTLE IT, either way: if the definition stays as it is, then case 2 is unreachable without an alias and the criterion should say so, because a bar no mechanism can clear is not a target but a permanent red. If the definition becomes 'an element that answers', then the two cases need a stated rule for what counts as answering - and that rule must be written before it is applied, not chosen after seeing which rows came back.";
        :>> discoveredInField = false;
        :>> severity = Severity::Medium;
    }
    #Resolves dependency from dcRecallHitDefinitionIsStated to issue391;

    part issue392 : Issue {
        :>> id = "a0dde85f-ab25-466c-a0a1-fe83d9e364cc";
        :>> title = "a single routing probe run is not a measurement: two of four verdicts flipped between runs";
        :>> createdAt = "2026-09-06";
        :>> createdBy = "claudeOpus5";
        :>> description = "A single routing probe run is not a measurement: two of four verdicts flipped between two runs of the same prompts. WHAT WAS OBSERVED, on identical prompts, same repository, same turn budget, minutes apart: release run 1: WRONG (invoked intake) run 2: ROUTED doc-sync run 1: ROUTED run 2: none (no skill invoked) view run 1: not in the set run 2: ROUTED actor-enrollment / stpa-diagram / decision-authoring: ROUTED in both Two of the four cases common to both runs changed verdict. The only differences between the runs were (a) the turn-boundary gate was silenced for the second - a change that cannot make a skill call DISAPPEAR, since it fires after the turn - and (b) four sessions ran concurrently rather than one. Neither explains a route becoming a non-route; model sampling does. WHY IT MATTERS MORE THAN THE NUMBER IT SPOILS: the criterion asks the rig to report a coverage number per skill, and a number assembled from one sample per skill would have looked authoritative and moved by five or ten points on a re-run. Worse, it would have been actionable in the wrong direction: a skill scored 'not routing' on one sample invites rewriting a description that was fine, and the rewrite would then appear to fix it. WHAT A REAL MEASURE COSTS, measured on this host: $0.47-0.59 and 25-70s per run sequentially, 31s per run at four-way parallelism with per-run wall time inflating to 74-125s under contention. One sample per skill over 47 skills is ~$25. Three samples, enough to report a rate with a majority verdict, is ~$70 and around an hour. That is the actual price of the metric, and it is a spend decision rather than an implementation detail - which is why this is recorded and the sweep is NOT running. WHAT IS NOT AT FAULT: the rig reads verdicts from tool_use blocks in the transcript, so it is not mis-parsing a self-report; the four cases above are ordinary skills, not edge cases; and the prompts are unchanged between the runs (they are authored facts in a committed file). OPEN, for the human: whether to pay for a repeated sweep and report a rate with its variance, or to sample a stratified subset, or to keep the rig for one-off diagnosis and record no standing number at all. The rig supports all three; what it must not do is publish a one-sample number as if it were stable.";
        :>> discoveredInField = false;
        :>> severity = Severity::High;
    }
    #Resolves dependency from dcRoutingNumberIsStable to issue392;

    part issue393 : Issue {
        :>> id = "af767117-f6d1-46b1-a031-153dd065b01b";
        :>> title = "a deployed skill instructs the agent to read a reference file sync-claude never deploys";
        :>> createdAt = "2026-09-06";
        :>> createdBy = "claudeOpus5";
        :>> description = "A deployed skill instructs the agent to read a reference file that sync-claude does not deploy, so following the skill leads to a missing path. WHAT HAPPENED: the stpa skill's first line of instruction is 'Full SOP, per-element data fields, and per-step completeness gates are in `references/sop.md` - read it before running a step.' Invoking the skill and following that instruction produced 'No such file or directory': `.claude/skills/stpa/` contains SKILL.md and nothing else, while `.engine/skills/stpa/` contains SKILL.md, registry.sysml and references/sop.md. The generator deploys the skill body and not the directory beside it. The 121-line SOP - the four steps, the data fields per element, the per-step completeness gates - is the substance the skill defers to, and an agent that followed the deployed instruction without knowing the engine layout would have had to invent it or skip the gates. WHY IT MATTERS MORE THAN A MISSING FILE: this is the failure mode of a process whose text is enforced but whose REACHABILITY is not. keel has a guard that every declared process has a skill (process-skill) and one that the claude surface has not drifted from the generator (claude-surface-drift), and neither asks whether a path a deployed skill TELLS the agent to open exists. The routing probe built today measures whether a skill is reached; nothing measures whether what it points at is there. HOW MANY OTHERS: unknown at the time of writing, and that is part of the finding - the check does not exist, so the answer would be a hand count that goes stale. The resolver's first job is to compute it. PREVENTING CHANGE: the generator deploys a skill's reference directory with the skill, and a check reads every deployed SKILL.md for relative paths it instructs the agent to open, failing when one does not resolve. That check is cheap, mechanical, and would have caught this the day the SOP was added - which is the test of whether it is worth having.";
        :>> discoveredInField = false;
        :>> severity = Severity::High;
    }
    #Resolves dependency from dcSkillReferencesAreDeployed to issue393;

    part issue394 : Issue {
        :>> id = "2c039d7a-8d28-4d5d-a36d-018281f833e2";
        :>> title = "STPA step 2 is incomplete against the handbook's element set, and our SOP named four of five types";
        :>> createdAt = "2026-09-07";
        :>> createdBy = "claudeOpus5";
        :>> description = "Our STPA step 2 is incomplete against the method's own element set, and the SOP we follow is why: it names four of the handbook's five element types. MEASURED AGAINST THE SOURCE OF RECORD (STPA Handbook, Leveson & Thomas 2018, fetched and read 2026-09-07). Page 25: a hierarchical control structure 'contains at least five types of elements: Controllers, Control Actions, Feedback, Other inputs to and outputs from components (neither control nor feedback), Controlled processes'. Pages 22-23 put TWO things inside a controller - the control algorithm (its decision-making process) and the process model (its beliefs, updated in part by feedback). Page 26 defines actuators and sensors as the mechanisms on the control and feedback paths. WHAT THIS PROJECT'S MODEL HAD, measured the same day: Controllers 8 roles, 7 with an authored anchor (`channel` has none) Control actions computed, present Feedback computed - but from CliCommand facts and CI statuses ONLY Controlled processes 6, present Other inputs and outputs NO SCHEMA TYPE EXISTS, so zero, and the omission is unreportable Sensors 0 - none had ever been authored or computed Actuators 0 - same Process models 4 of 8 controllers (commit-gate, channel, remote, console have none) Control algorithms no representation at all WHY THE SOP IS THE CAUSE, not carelessness in one run: an agent following a reference that names four types will produce four types every time. The fourth type is the one summaries drop, and it is not a rounding error here - it is where 'the measurement was taken against the wrong thing' lives. An instrument reading the working tree while a report cites a SHA (scenario S-F9) is precisely an other-input problem: nobody controls the tree's dirtiness and it reports on nothing, so it is neither a control action nor feedback, and there is nowhere in the model to put it. FIXED IN THE SAME COMMIT: the SOP now carries all five types, the control algorithm and what a sensor is, and its step-2 gate requires the fourth type to be enumerated or declared empty with a reason - so the omission becomes a gate miss rather than an invisible absence. The instruments now compute as feedback paths AND as 20 sensors carrying their determinism, so feedback went from 77 channels to 97 and sensors from zero. STILL OPEN, and the reason this is tracked rather than closed: actuators remain zero; four controllers have no process model; there is no schema type for the fourth element class, and adding one is a FROZEN-SCHEMA change that needs a Change Request and the human's sign-off rather than an edit; and no control algorithm is represented anywhere, though step 4's cause list refers to one by name ('inadequate control algorithm').";
        :>> discoveredInField = false;
        :>> severity = Severity::High;
    }
    #Resolves dependency from dcStpaStepTwoIsComplete to issue394;

    part issue395 : Issue {
        :>> id = "21ce0d30-1656-4967-a140-79664801c93b";
        :>> title = "an instrument declared in a contract file has no model identity, so no verification case can verify it";
        :>> createdAt = "2026-09-07";
        :>> createdBy = "claudeOpus5";
        :>> description = "An instrument declared in a contract file has no model identity, so no verification case can point at it and its assessment can only be joined by string. WHAT THE OWNER CORRECTED, 2026-09-07, verbatim: 'metadata saying assessed=no is the wrong route. we verify through verification_type=analysis with a matching verification case. we don't embed verification in metadata.' The stored field is gone and assessment is now computed by joining each declared instrument against the `target` of every ProprietyFinding (`instrument:<name>`), so it cannot contradict the findings because it IS the findings. WHAT THAT FIX DOES NOT REACH, and why this is tracked: the correction names a general mechanism - a verification case, method=analyze, with a matching verify edge to the thing verified - and that mechanism needs the target to be a MODEL ELEMENT, because a #Verify edge has endpoints and the edge-endpoints guard refuses one that does not resolve. The twenty instruments are declared in .engine/contracts/instruments.toml. A contract file holds no items, so there is nothing for an edge to point at, and the strongest available link is the string convention the propriety findings already use. A string target is unchecked in both directions: nothing refuses a finding naming an instrument that never existed, and nothing notices an instrument whose assessment names it by a slightly different string. TWO ROUTES, and the choice is a direction question rather than an implementation detail. ROUTE A - the instruments become model elements. `Sensor` already exists as a type in the safety schema with ZERO attributes (`part def Sensor :> Element;`), so this needs attributes for what the manifest carries: the mechanism's path, what it measures, its determinism, its output form, and typed refs for the process observed and the controller informed. That is a FROZEN-SCHEMA change: Change Request, explicit human sign-off, and it should be weighed together with the other schema gap already open (issue394's fourth element type - other inputs and outputs, neither control nor feedback). What it buys: a verification case can verify an instrument the way it verifies anything else, the edge refuses a target that does not resolve, and the contract file disappears rather than becoming a second home for the same facts. What it costs: two schema additions and the migration of twenty declarations into the model. ROUTE B - the contract file stays and a guard holds the string join in both directions: every ProprietyFinding whose target begins `instrument:` must name a declared instrument, and the coverage view keeps reporting UNASSESSED for the rest. What it buys: typo and staleness protection today, no schema change, no sign-off. What it costs: the instruments stay outside the typed model permanently, so they can never be verified the way every other element is, and the string convention becomes load-bearing. RECOMMENDATION: Route A, but NOT built yet - it is a frozen-schema change and belongs in one Change Request with issue394's element type, since both are additions to the same safety schema and reviewing them together is cheaper than twice. Route B is deliberately not built either, because it would be thrown away if A lands within the week.";
        :>> discoveredInField = false;
        :>> severity = Severity::High;
    }
    #Resolves dependency from dcInstrumentsAreVerifiableElements to issue395;

    part issue396 : Issue {
        :>> id = "8b5d8924-2262-4ff1-9f2a-1c037be1b9c5";
        :>> title = "a Decision can be proposed and superseded at once, so a retired rule keeps asking for a signature";
        :>> createdAt = "2026-09-07";
        :>> createdBy = "claudeOpus5";
        :>> description = "A Decision can be proposed and superseded at the same time, so a retired rule keeps asking the human to accept it. WHAT HAPPENED: d0353 proposed that a push require a green full-suite receipt. The same day, d0356 withdrew that gate and was authored with a #Supersede edge from d0356 to d0353. The edge is a fact in the model. The STATUS is a separate authored attribute, and it still read `proposed` - so `keel orient` counted d0353 among the decisions awaiting a human acceptance, the decision brief carried it as an eleventh record, and I had to explain on the page that signing it would record two contradictory rules. It stayed on the owner's queue for a day and came off only when I edited the attribute by hand today. THE DEFECT IS DUAL TRUTH, not the stale value. Supersession is expressed twice: once as a typed edge and once as an enum member (`DecisionStatus::superseded`). Nothing computes one from the other, so they can disagree, and when they disagree the STATUS wins because that is what the pending-acceptance computation reads. This is the same class the owner corrected an hour earlier about a stored `assessed` flag: a status field that summarises a relationship can contradict the relationship, and the field is what a reader sees. WHY IT MATTERS BEYOND TIDINESS: the pending-acceptance list is the one surface that tells a human what waits on them, and it asked for a signature on a rule the project had already reversed. A queue that carries retired items trains its reader to skim it, which is precisely the failure D0359 removed the turn-boundary nag for. WHAT IS UNDECIDED, and why this is an Issue rather than a fix: which representation is authoritative. If the EDGE is - and Invariant 1 says a derivable thing is a view - then `DecisionStatus::superseded` should not exist as an authored value at all, and supersession should be computed wherever it is read, including in pendingAcceptances. That is a schema and view-meaning change. If the STATUS is, then the edge is decoration and something must refuse a #Supersede edge whose target still reads proposed. Either way one of the two stops being authored. There is no third answer that leaves both writable.";
        :>> discoveredInField = false;
        :>> severity = Severity::High;
    }
    #Resolves dependency from dcSupersessionIsSaidOnce to issue396;

    part issue397 : Issue {
        :>> id = "b7534220-9c59-470d-a357-649bd581676a";
        :>> title = "the read-back check splits the human's words on the apostrophe, so prose can shift the span";
        :>> createdAt = "2026-09-07";
        :>> createdBy = "claudeOpus5";
        :>> description = "The read-back check extracts the human's words by splitting on the apostrophe character, so ordinary prose around the quote changes which span is checked. WHAT HAPPENED: recording the owner's acceptance of eight decisions, my note read - recorded from the decision brief's own copy-for-AI digest, their words verbatim: '- [x] Sign all eight ... (answers: d0337, ...)'. The check refused it: 'the quoted words do not name d0337'. The id was plainly there. The cause is that the apostrophe in 'brief's' is the same character as the opening quote, so span extraction saw a span running from that apostrophe to the next one - capturing 's own copy-for-AI digest: ' - and the span carrying the ids was parsed as prose between spans. Removing the apostrophe from my own sentence made the identical acceptance pass. WHICH DIRECTION THIS FAILED IN, and why the other direction is the real risk: here it failed CLOSED - the acceptance was refused and nothing was written, which is the safe outcome and is why this is not a defect that caused harm. But the mechanism is symmetric. A note whose surrounding prose contains an apostrophe can produce a span that includes text the human never said, and if that text happens to carry the decision id - trivially likely, since a note about a decision tends to name it - the read-back check PASSES on words that are not the human's quote. The control exists precisely to stop a bare gesture being attached to a record the agent chose; a span-extraction artefact can defeat it in exactly that direction. WHY IT IS NOT MERELY MY MISTAKE: the note format is a human-facing contract - the human may type their own note at their terminal, and a human writing about their own project will use possessives. A control whose correctness depends on the recorder avoiding an apostrophe is not robust against ordinary use, which is the `changeRobustness` lens applied to an attestation path. PREVENTING CHANGE: extract the quoted span unambiguously rather than by splitting on a character that also appears in prose - a typographic quote pair, a doubled delimiter, or a dedicated flag carrying the human words as their own argument, so the span boundaries are declared rather than inferred. Whichever is chosen, the check must be shown FAILING on a note whose apostrophe-spliced span carries the id while the human words do not - the case that matters is the passing one, not the refusing one.";
        :>> discoveredInField = true;
        :>> severity = Severity::High;
    }
    #Resolves dependency from dcQuotedWordsAreBounded to issue397;

    part issue398 : Issue {
        :>> id = "6d38842d-1279-407c-a310-87b8e42c60d6";
        :>> title = "a patch that cannot find its anchor appends instead of failing, so an edit lands where it does no work";
        :>> createdAt = "2026-09-07";
        :>> createdBy = "claudeOpus5";
        :>> description = "A patch script that cannot find its anchor APPENDS instead of failing, so an edit lands somewhere it does no work and the run reports success. WHAT HAPPENED, 2026-09-07: a patch adding a new computation section to the computed-facts script looked for an anchor comment, and had a fallback - if the anchor was not found, append at end of file. The anchor did not match. The section was appended AFTER the line that serialises the output, so the script ran clean, exited zero, wrote its file, and silently omitted every fact the new section had just computed. Nothing failed. The only thing that noticed was reading back the specific keys the section was supposed to add and finding them missing. WHY THE FALLBACK IS THE DEFECT: an append is a plausible-looking success. A refusal would have named the problem in one line at the moment it occurred. The fallback exists because appending 'usually works' for a self-contained block, and it does - right up to the case where position is semantic, which in a script is always: code after the emit is code that runs after the answer was published. THE SAME SHAPE, TWICE MORE IN ONE SESSION, so this is a pattern rather than an incident: a patch that replaced a string with `assert s.count(old) == 1` failed LOUDLY and correctly every time it missed - that is the right behaviour and it is why those misses cost seconds. Every silent one cost a read-back to discover. And one earlier patch applied a `sed` substitution that matched nothing, leaving a stale anchor in the docs, found later by grep. PREVENTING CHANGE: a patch asserts its anchor and exits non-zero when it is absent - no fallback, no append, no best effort. Where a patch legitimately needs to add at end-of-file, it says so explicitly rather than arriving there by failure. This is cheap: the assertion pattern is already used in most of these scripts and is what makes them safe; the defect is that it is a convention rather than the only available shape.";
        :>> discoveredInField = true;
        :>> severity = Severity::High;
    }
    #Resolves dependency from dcPatchesFailWhenTheyMiss to issue398;

    part issue399 : Issue {
        :>> id = "63cf4de6-be0b-411e-911a-79c3bedf84c3";
        :>> title = "a failed instrument leaves its previous artefact in place, reading as the current answer";
        :>> createdAt = "2026-09-07";
        :>> createdBy = "claudeOpus5";
        :>> description = "A failed instrument leaves its previous output in place, so a stale artefact reads as the current answer. WHAT HAPPENED, 2026-09-07: the computed-facts script had written `decision-facts.json` on an earlier run. A later run raised a NameError partway through and exited non-zero. The file from the earlier run remained on disk, valid JSON, with a `generatedAt` timestamp and a `tree` SHA from the previous run - indistinguishable at a glance from a current answer. The standing brief is built from that file, so a page built in that window would have carried numbers attributed to a tree the script never read, with per-fact provenance strings that were true when written and false as published. Caught only because the reader was looking for keys the failed section should have added. Nothing in the artefact says whether the run that produced it completed. THIS IS SCENARIO S-F4 WITH A TIMESTAMP: a measurement that could not complete, reported by its own artefact as a completed one. The same shape as `keel suite` printing 'fail - 0 passed, 0 failed' over a file lock (issue386) - there the verdict field lied about a lock, here the file's existence lies about a run. WHY A NON-ZERO EXIT IS NOT ENOUGH: the exit code lives in the shell that ran the script, and the artefact outlives it. A later reader - a page builder, another session, a human opening the JSON - has only the file. Provenance per fact does not help, because each `how` string is accurate about how that fact WOULD be computed; it is the file's currency that is false. PREVENTING CHANGE: an instrument that cannot complete does not leave a previous artefact readable as current - it removes it, or marks it stale in a way a reader cannot miss, so a missing answer is what a failed run produces. A missing file is an honest answer; a stale one is a wrong answer with a plausible date. The general form belongs to every instrument that writes an artefact: the suite receipt, the routing JSON, the facts file, the census output.";
        :>> discoveredInField = false;
        :>> severity = Severity::High;
    }
    #Resolves dependency from dcInstrumentsLeaveNoStaleArtifact to issue399;

    part issue400 : Issue {
        :>> id = "24ce9850-5c14-4982-85d3-6e4621bef785";
        :>> title = "a hand-written check's first answer was stated as a finding twice, and both were wrong";
        :>> createdAt = "2026-09-07";
        :>> createdBy = "claudeOpus5";
        :>> description = "A hand-written check's first answer was stated as a finding, twice in one session, and both times it was wrong. TWO INSTANCES, 2026-09-06 and 2026-09-07: (1) A census of which enforced guards have a test that constructs their defect returned 64 of 64 - a perfect score. It was an artefact: the census searched a text window around each occurrence of a guard's name, every guard name occurs in the GUARD_NAMES registry inside guards.rs, and that file is full of the words 'violation' and 'FAIL'. The instrument was measuring its own registry. Caught only because the answer was TOO GOOD; a plausible number like 48 of 64 would have been published and acted on. The real answer, from a version that looks inside test function bodies, was 16. (2) A check for which controllers lack a process model reported that the HUMAN's controller had none. It compared a role name to an anchor name case-sensitively - `human` against `ctHuman` - so every anchor read as absent. I stated that finding in a response before recomputing, then corrected it. The real answer was four of eight, and the human's was one of the four that HAD one. WHAT THESE SHARE: an ad-hoc check, written to answer one question, whose first output was treated as a measurement. Neither had been run against a case whose answer was known in advance. In (1) the artefact flattered the tree; in (2) it maligned it; both were indistinguishable from a real result at the point of use, and the second was published. WHY THIS IS NOT 'BE MORE CAREFUL': care is what produced both checks. The missing step is mechanical and takes a minute - run the check against a case whose answer you already know, and only then read its answer on the real tree. In (1) a single guard known to have a failure-asserting test and a single guard known to have none would have shown the census matching everything. In (2) any one controller with a known process model would have shown the comparison failing. PREVENTING CHANGE: an ad-hoc check is probed against a known case before its answer is stated - in a response, in a record, or on a published page. Where the check is worth keeping it becomes an instrument and inherits the propriety lenses (D0361); where it is throwaway the probe is still the price of quoting its number.";
        :>> discoveredInField = false;
        :>> severity = Severity::High;
    }
    #Resolves dependency from dcAdHocChecksAreProbedFirst to issue400;

    part issue401 : Issue {
        :>> id = "8dcfb973-9331-4d63-8779-b9dc3389bd8e";
        :>> title = "a published page relied on the host to guess its encoding and rendered mojibake";
        :>> createdAt = "2026-09-07";
        :>> createdBy = "claudeOpus5";
        :>> description = "A published page relied on the host to guess its character encoding, and rendered mojibake wherever the guess was wrong. WHAT HAPPENED, 2026-09-07: the standing brief was built with typographic characters - an apostrophe and an em dash - written as real UTF-8 bytes and no `<meta charset>` in the page. Served locally for review it rendered 'yesterdayâ€™s defects' and 'â€”' throughout the headline and body, because the server sent no charset and the browser guessed Latin-1. The publishing wrapper supplies a charset, so the artifact itself would have rendered correctly - which is exactly the problem: the page's correctness was BORROWED from its host, and the same file is unreadable anywhere that does not supply one. WHY IT MATTERS BEYOND ugly text: the brief exists to be read and acted on by someone who is not me, and a headline reading 'yesterdayâ€™s defects' is the first thing they see. It also defeated my own review step - I read the rendered page as an image precisely to catch defects like this, and the first render showed the defect only because the local server behaved differently from the publisher. Had I reviewed only after publishing, the page would have looked right and the file would still have been wrong. THE CHECKER DID NOT SEE IT: the executive-brief contract checks structure - no record ids in reader text, a verb in every figure title, options that declare what they decide, a provenance strip with a date. It has no opinion about encoding, so a page that renders as mojibake on half the hosts in the world passes clean. PREVENTING CHANGE: a page declares its own encoding, and the brief contract checks that it does - one line in the checker, and it forecloses a class that is invisible in review whenever the reviewing host happens to guess right. The stronger version, worth weighing: the builder emits only ASCII and HTML entities for typographic characters, which is what the previous brief did and why it never showed this.";
        :>> discoveredInField = false;
        :>> severity = Severity::Medium;
    }
    #Resolves dependency from dcPagesDeclareTheirEncoding to issue401;

    part issue402 : Issue {
        :>> id = "cfcca628-6d4a-4631-8ce1-cb725a58bf7f";
        :>> title = "the recall channel silently drops its payload when it runs long, and the fast tier's tail is 150x its stated cost";
        :>> createdAt = "2026-09-07";
        :>> createdBy = "claudeOpus5";
        :>> description = "The agent's recall channel silently stops feeding it when it runs long, and the fast edit tier has a tail two orders of magnitude past its stated cost. MEASURED from the hook fire ledger (.keel/metrics/hooks.jsonl, 11,919 fires carrying a duration, read 2026-09-07): user-prompt (recall) 808 fires median 696ms max 33,503ms 18 over the 2,500ms cap post-edit (fast tier) 1,388 fires median 0ms max 54,439ms 14 over 2,500ms stop (full gate) 242 fires median 13,833ms max 116,337ms 242 over (by design) subagent-stop 611 fires median 16,539ms max 96,314ms 610 over (by design) pre-bash 8,191 fires median 0ms max 182ms none TWO DISTINCT FINDINGS IN THAT TABLE. (1) RECALL DEGRADES SILENTLY. When the user-prompt hook exceeds its 2,500ms cap the payload is dropped with one line - 'SKIPPED - recall took 7307ms (cap 2500ms). Facts not pushed this turn.' It happened twice in this session, both times while a background suite was loading the machine, and the ledger says it has happened 18 times in 808 fires. The cap is right - a prompt must not wait on a graph walk - but the consequence is that the agent's memory channel is exactly least available when the machine is busiest, which is when long autonomous runs happen. Nothing records WHICH turns went without facts, so no one can tell afterwards whether a turn's reasoning had the model in front of it or not. (2) THE FAST TIER IS NOT ALWAYS FAST. CLAUDE.md states the per-edit tier costs about 0.35 seconds. Its median is 0ms, which is better than stated, and its maximum is 54 seconds - 150 times the claim. A 54-second pause after an edit reads as a hang, and the documented figure gives no hint that the tail exists. WHY BOTH BELONG IN ONE ITEM: the mechanism is the same. A hook with a stated cost and an advisory failure mode degrades invisibly, and the record of the degradation lives in a machine-local ledger nobody reads. The ledger is the instrument that found this, and it was written for the hooks-actually-fired checks, not for latency. PREVENTING CHANGE: report the tail, not the anecdote - a skipped recall is a fact worth counting rather than a line in one transcript, and the documented cost of a gating tier is stated as a distribution rather than a single number. Whether the recall cap should ALSO rise, or the walk get faster, is a separate question this item should answer with the ledger rather than by feel.";
        :>> discoveredInField = false;
        :>> severity = Severity::High;
    }
    #Resolves dependency from dcHookDegradationIsCounted to issue402;

    part issue403 : Issue {
        :>> id = "98f3ef9c-8ccc-455d-971b-70cb3fe5f88d";
        :>> title = "43 of 46 control actions have never been analysed by an STPA run";
        :>> createdAt = "2026-09-07";
        :>> createdBy = "claudeOpus5";
        :>> description = "Forty-three of forty-six control actions in this project's own control structure have never been analysed by an STPA run. MEASURED 2026-09-07: `keel guard stpa-currency` reports '43 of 46 computed control action(s) no stpa-self run has analysed', naming them - cmdAccept, cmdActivate, cmdActor, cmdAddTask, cmdAppendGateResult, cmdApplyReview, cmdClaim, cmdCurrency and on. The guard passes, because it is warning-tier by design: it says the analysis has fallen behind the structure and does not block. WHY THE NUMBER IS THIS LARGE: the control structure is COMPUTED, so it grows whenever a write command, a hook event or a workflow step is added - and it grew again today, from 77 feedback channels to 97, with twenty sensors that had never existed. The analysis is authored, so it grows only when someone runs it. Eighteen unsafe control actions stand against three actions. The gap is not neglect of one item; it is the structural consequence of a computed structure and a hand-run analysis, and the currency guard exists precisely to make it visible rather than to close it. WHY IT IS WORTH RECORDING RATHER THAN LEAVING AS A STANDING WARNING: the warning has been true for long enough that it reads as scenery. Meanwhile the three analysed actions are the oldest ones, so the analysis covers the part of the system least likely to have changed and none of the write path added since. A hazard analysis whose coverage is 3 of 46 is closer to an example than to an analysis, and nothing on the surface says so - the guard reports PASS with a warning, and `keel show control-structure` reports a complete-looking structure. WHAT MAKES THIS DIFFERENT FROM issue394: that item is about step 2's element set being incomplete against the handbook - types missing from the model. This is step 3 coverage: the types exist, the actions are computed, and no unsafe-control-action analysis has been run over 43 of them. PREVENTING CHANGE: run the analysis over the uncovered actions in tranches, and decide what the currency warning should say when the structure grows faster than the analysis - because it will. A number that only ever rises is a metric nobody can act on; either the analysis is batched against the growth, or the warning states a target it is measured against.";
        :>> discoveredInField = false;
        :>> severity = Severity::Medium;
    }
    #Resolves dependency from dcStpaSelfCoversTheActions to issue403;

    part issue404 : Issue {
        :>> id = "44e88567-a00f-467a-be9e-ca0f62b34cd4";
        :>> title = "the guard set reports 131 warnings and says in its own summary that nobody reads them";
        :>> createdAt = "2026-09-07";
        :>> createdBy = "claudeOpus5";
        :>> description = "The guard set reports 131 warnings across 12 guards and says out loud that nobody reads them. MEASURED 2026-09-07: `keel guard .` ends 'ALL PASS - 131 warning(s) across 12 guard(s), NOT violations and NOT blocking, but UNREAD until someone reads them: actors, ceremony, issues, viewpoint-renderer, manifest-coverage, attestation-substance, decision-requirement-link, priority-inversion, sequence-multiplicity, parser-coverage, decision-scaffolding, stpa-currency'. The count rose during this session - 38, then 55, then 74, then 93, then 112, then 131 - as work landed. The summary line is honest and that honesty is the finding: the surface itself asserts that these are unread. WHY THEY ARE UNREAD RATHER THAN IGNORED: a warning has no discharge path. A violation blocks and gets fixed; a warning prints on every run, forever, whether it was read once or never. Some are explicitly undischargeable by design - 52 legacy actor references in immutable history, counted rather than enumerated precisely because 'a warning nobody can act on trains blindness to the ones they can'. That reasoning is sound and it is also the mechanism: a set containing permanent noise cannot be read as a set worth reading, so the actionable ones inherit the noise's fate. WHAT MAKES THIS A DEFECT AND NOT A PREFERENCE: this project's whole discipline is that state is computed and read back rather than asserted. 131 computed statements about the model are being produced and discarded every run. Either they carry information, in which case discarding them loses it, or they do not, in which case producing them costs a reader's attention on every gate. WHAT IS NOT THE ANSWER: promoting them to violations. Several are deliberately warning-tier because no defensible threshold exists (D0088), and gating on one would be answered by making the number go down rather than the condition go away. PREVENTING CHANGE: separate the undischargeable from the actionable, computed rather than by hand - a warning about immutable history can never be acted on and should be counted in one line, while one naming a fixable condition should appear in the burndown where work is chosen. Then the guard summary can state a number a reader can do something about, and the fact that it is nonzero means something.";
        :>> discoveredInField = false;
        :>> severity = Severity::Medium;
    }
    #Resolves dependency from dcGuardWarningsAreActionable to issue404;

    part issue405 : Issue {
        :>> id = "04136303-da1e-4cc5-9fe6-75b7264f0ee0";
        :>> title = "A sweep on an arm that cannot exercise the mechanism returns neutrality, and neutrality reads as a verdict";
        :>> createdAt = "2026-09-07";
        :>> createdBy = "claudeOpus5";
        :>> description = "FOUND 2026-09-07 while satisfying recallRanksLinkedRecordsAsWellAsGrepDoes. CHECK: six configurations of the dominant-source second hop were run on recall_bench.py's default 50-case arm - DOMINANCE 1.5 and 2.0, DOM_HOP2 0.4, 0.7 and 1.0, DOM_HOP1 0.6 - and every one returned 49/50 hits at median position 3, byte-identical on those two statistics to the arm with the mechanism switched off. MECHANISM: every case in that arm draws its query from a record ONE edge from the target (recall_bench.py builds the query source as the first bodied element of adj[target]), so the arm contains no case a second hop applies to and cannot distinguish any setting of it from off. CONSEQUENCE: neutrality of that kind is not a measurement and must not be read as one, but the criterion that governs this work says the mechanism is to be CHOSEN on that arm, which leaves only two moves and both are wrong - choose by the eight hand-written questions, the fitting the criterion forbids, or reject the mechanism, which is precisely what D0325 did to the rare-term narrowing on this same evidence and recorded as neutral at every threshold so that set could not choose one. The second reading discards working mechanisms; the first corrupts the arbiter. D0364 built the two-hop arm and it resolved this instance - the same mechanism moved 15/50 to 22/50 there - but nothing prevents the next mechanism from being swept on an arm that cannot see it and the neutrality being read again as a verdict. PREVENTING CHANGE: dcSweepSaysWhenItCouldNotChoose - a sweep reports whether the set discriminated, derived from the numbers it measured, so COULD NOT CHOOSE is a stated outcome rather than a silence the reader fills in.";
        :>> discoveredInField = false;
        :>> severity = Severity::Medium;
    }
    #Resolves dependency from dcSweepSaysWhenItCouldNotChoose to issue405;

    part issue406 : Issue {
        :>> id = "23252f4b-2321-4cfc-beda-31dccff7db46";
        :>> title = "A recall measurement does not name the binary that produced it, so a mid-relink run reads as a regression";
        :>> createdAt = "2026-09-07";
        :>> createdBy = "claudeOpus5";
        :>> description = "FOUND 2026-09-07 in sprint 593. CHECK: recall_ab.py was run immediately after a cargo build --release returned, while the linker was still settling target/release/keel.exe, and printed 6/8 with a mean prompt-path cost of 5282ms against the usual ~1050ms. Three consecutive runs after that read 7/8 at ~1050ms. MECHANISM: the harness shells out to the binary by path 16 times per run and reports whatever those invocations produce; an invocation against a partially written or locked image returns a degraded payload, and the harness has no way to notice because it never asks which binary answered. CONSEQUENCE: the wrong number is indistinguishable from a real regression. In this case it arrived one step after a refactor of the very function being measured, so the obvious reading was that the refactor had broken the mechanism - a reading that would have sent the next hour into bisecting a change that was correct. Only the latency line, and re-running, told the truth. This is the issue386 family reaching the measurement harnesses: an instrument reporting confidently over a file whose state it does not control, the same shape as keel suite printing a verdict over a locked image and as a failed script leaving its previous artefact readable as current. A measurement that cannot name the image that produced it is not attributable, and an unattributable number recorded on a Decision is worse than no number. PREVENTING CHANGE: dcRecallMeasurementNamesItsBinary - both harnesses print the build commit of the binary they are about to interrogate, and refuse to print a score at all if they cannot get one.";
        :>> discoveredInField = false;
        :>> severity = Severity::Medium;
    }
    #Resolves dependency from dcRecallMeasurementNamesItsBinary to issue406;

    part issue407 : Issue {
        :>> id = "08377962-d03d-4b80-8057-5d04b4540e4d";
        :>> title = "add-task writes the task outside the def when an earlier field carries an escaped quote";
        :>> createdAt = "2026-09-07";
        :>> createdBy = "claudeOpus5";
        :>> description = "FOUND 2026-09-07 in sprint 594, while reordering the backlog to discharge the priority-inversion warnings. CHECK, reproduced twice on a clean tree at 018315a before any claim was made: keel add-task --file backlog.sysml --def NextWork placed the action at line 2696, while action def NextWork closes at line 2104 - the task landed OUTSIDE every action def, at package level, immediately before the package's own closing brace. The same command with --def EngineBuild on the same file placed correctly at line 807 against a close at 809, so it is not add-task in general but the SECOND def in the file. MECHANISM, located at write.rs braces_in: the scan tracks whether it is inside a string literal but has no escape handling, so the first backslash-quote in a field's prose reads as a terminator. .tracking/backlog.sysml line 1793 carries one - a procedureText that quotes an escaped quote while being ABOUT escaped-quote handling, which is issue044's record - and from there the line's remaining braces are counted as structure. Depth never returns to zero at NextWork's real close, block_close_line keeps scanning and returns the PACKAGE's brace, and add_task inserts before that. CONSEQUENCE: two items recorded in sprint 593, dcSweepSaysWhenItCouldNotChoose and dcRecallMeasurementNamesItsBinary, were written at package level. Every gate stayed green over them - validate, check-engine, the guard set, the pre-commit hook and CI - because the parser accepts an action at package level, and show priority still listed them as ready. So the failure is silent in both directions: the write reports success and returns a UUID, and nothing downstream reads the placement as wrong. What it corrupts is the one thing declaration order is load-bearing for: D0052 makes declaration order the priority, and an item outside the def has no position in it. WHY IT IS RECORDED RATHER THAN JUST FIXED: the escape bug is one cause of a wider shape - a line scan that goes wrong returns a plausible line number rather than an error, and every write that positions itself by scanning has the same exposure. PREVENTING CHANGE: dcAddTaskLandsInsideItsDef - the escape is handled AND the landing site is checked against the def it was asked for, so a scan that drifts again refuses instead of writing.";
        :>> discoveredInField = false;
        :>> severity = Severity::High;
    }
    #Resolves dependency from dcAddTaskLandsInsideItsDef to issue407;

    part issue408 : Issue {
        :>> id = "cff59d17-710f-4e94-8ceb-47cb5361c113";
        :>> title = "A self-build project's hooks run the binary its own build is relinking, and the resulting lock reads as a test verdict";
        :>> createdAt = "2026-09-07";
        :>> createdBy = "claudeOpus5";
        :>> description = "FOUND 2026-09-07 in sprint 594. CHECK: keel suite returned `fail - 0 passed, 0 failed` on three consecutive runs, each log carrying only `error: failed to remove file target/release/keel.exe / Access is denied (os error 5)`. No test executed on any of them. The fourth run, after the change below, executed and reported 568 passed 3 failed - three REAL regressions from an over-strict check added earlier in the same sprint, which had been in the tree throughout and which the three false verdicts hid. MECHANISM, established from .keel/metrics/hooks.jsonl rather than inferred: every hook fire records its bin, and all of them read C:/.../target/release/keel.exe. The pin probe's order is KEEL_BIN, then .keel/bin/keel(.exe), then the pin cache, then PATH; this repository has .keel/bin/0.2.3 and .keel/bin/0.3.0 but no .keel/bin/keel.exe, because init seeds the versioned shape and nothing writes the bare name - so the probe falls through to PATH and lands in the build directory. The hooks then run that file on every user prompt, every Bash call and every turn boundary, and cargo cannot unlink it to relink. The ledger pins the collision to the second: suite-1788812764.log against a pre-bash fire at 1788812764 and a stop fire at 1788812804 mid-run. TWO WRONG EXPLANATIONS WERE TESTED AND DISCARDED FIRST, which is why this is stated as mechanism rather than suspicion: a lingering process (PID 47908 - it was gone for the second failure), and my own tool calls (going quiet is precisely what fires the stop hook). CONSEQUENCE, and this is the part that matters more than the flakiness: the lock did not merely produce a wrong number, it CONCEALED a real one for three runs. A unit test and a live reproduction both passed throughout, so a sprint recorded on their strength would have committed a change breaking three tests. issue386 records the adjacent shape and its standing remedy - serve from a copy - does not help here, because the holder is never the suite's own image. PREVENTING CHANGE: dcSelfBuildHooksLeaveTheBuildTree. Distinct from dcSuiteSurvivesItsOwnImage, which must still make a lock report as a lock rather than as a verdict; this one removes the collision, that one removes the false verdict, and neither substitutes for the other.";
        :>> discoveredInField = false;
        :>> severity = Severity::High;
    }
    #Resolves dependency from dcSelfBuildHooksLeaveTheBuildTree to issue408;

    part issue409 : Issue {
        :>> id = "9c21ac2b-55a0-4e25-9089-83fb942b93fe";
        :>> title = "The turn-boundary gate costs 25.5 s and orient 5 s over a 275 ms parse: serial guards, corpus re-reads, and untimed spawns";
        :>> createdAt = "2026-09-07";
        :>> createdBy = "claudeOpus5";
        :>> description = "MEASURED 2026-09-07 on this host (Windows 11, 20 cores, Defender on-access scanning, no exclusion), release binary at 018315a, warm file cache, KEEL_PERF=2 plus a measurement-only phase wrapper around run_all and orient::compute (reverted, not committed): parsing the whole corpus - 678 files, 11.6 MB - costs 275 ms, and the model is built ONCE per process (Model::build x41: 40 cached, 1 parsed). Yet `keel guard` takes 25.5 s wall and `keel orient` 5.1 s. WHERE IT GOES, guard: priority-inversion 6.3 s, which re-runs orient::compute in full; about twenty text-scanning guards at 0.4-1.8 s each, every one re-reading the corpus from disk because it scans lines rather than the model (39 collect_sysml and 61 read_to_string sites in guards.rs); 56 git spawns at about 79 ms each on this host, about 4.4 s; and 40 cache-hit clones of the Model at 1.57 s. orient: criterion_suspects 1.8 s, deliverable suspicion 0.95 s, narrowing 0.5 s, activation 0.34 s, the rest under 0.3 s each; 23 git spawns. The guards run SERIALLY on a 20-core host. Nothing here is a wrong algorithm - each guard is a linear scan and each git query is already batched - the cost is repetition across independent guards and process spawns, and the Stop hook pays the whole 25 s at every turn boundary on a tree that has usually not changed. THE HUMAN'S WORDS, 2026-09-07: 'Keel has become slow, which is a known tradeoff for a computed state ... I feel like we don't make a ton of changes all at once, so keel shouldn't have to take so long to compute state.' The check behind every number: KEEL_PERF=2 keel guard and keel orient with the phase wrappers, outputs kept in docs/reviews/perf-spike-2026-09-07.md.";
        :>> discoveredInField = false;
        :>> severity = Severity::High;
    }
    #Resolves dependency from dcGuardsRunInParallelAndTimed to issue409;
    #Resolves dependency from dcGitFactsAreContentAddressed to issue409;
    #Resolves dependency from dcOneCorpusPerProcess to issue409;
    #Resolves dependency from dcGateAnswersFromItsReceipt to issue409;

    part issue410 : Issue {
        :>> id = "13d776e3-e28a-47e9-9df6-9880dbba97e9";
        :>> title = "The perf line counts git spawns but times them as 0ms";
        :>> createdAt = "2026-09-07";
        :>> createdBy = "claudeOpus5";
        :>> description = "FOUND 2026-09-07 while attributing `keel guard`'s 25.5 s. gitx::git() counts every spawn (GIT_CALLS; the static test that forbids Command::new('git') elsewhere makes the count total), but GIT_NANOS is advanced only by govern.rs, so the perf line reads `git x56 in 0ms` while the 56 spawns cost about 4.4 s at the 79 ms per spawn measured on this host with a shell timer around `git rev-parse HEAD`. The count is right and the time is a lie of omission: a reader of the perf line concludes git is free. The module's own header says count-don't-time was that session's rule; the one number it withheld is the one this spike needed. CHECK: grep GIT_NANOS keel-cli/src - one add site, in govern.rs.";
        :>> discoveredInField = false;
        :>> severity = Severity::Medium;
    }
    #Resolves dependency from dcGuardsRunInParallelAndTimed to issue410;

    part issue411 : Issue {
        :>> id = "14ad7ab2-6f98-4fbc-b1cc-87333fec795f";
        :>> title = "the brief's already-in-the-tree count was typed as three while its instrument computed two - a phrase rule over prose stood in for a fact the model records as edges";
        :>> createdAt = "2026-09-08";
        :>> createdBy = "claudeOpus5";
        :>> description = "The standing decision brief published on 2026-09-07 stated that three of five pending Decisions were already in the tree, and its footnote said the instrument had been fixed to say so. The instrument said two. `pendingAlreadyShipped` is a phrase rule over each Decision's own consequences prose; after the 2026-09-07 widening it matched d0361 and d0366 and not d0363, whose consequences describe the schema move in the present tense with none of the listed phrases. The count on the page was therefore typed from the author's knowledge, not read from facts.json - the issue382 defect (numbers typed, not computed) recurring on the one number the issue383 correction had made load-bearing (whether an ask is a choice or a ratification). Found 2026-09-08 while rebuilding the page for three new asks: the fresh facts.json listed two, the page said three, and the page was right. A phrase rule over prose cannot be the instrument for a structural fact the model already records as typed edges: a delivery record names the Decision that chartered it (#CharteredBy, D0068) and records its DoD verdict as a TestResult. Reading those makes the count a function of the tree; the phrase rule stays beside it for the one case the edges cannot see, a Decision built outside any sprint.";
        :>> discoveredInField = false;
        :>> severity = Severity::High;
    }
    #Resolves dependency from dcBriefDeliveredCountIsStructural to issue411;

    part issue412 : Issue {
        :>> id = "5061870a-3f23-4d6b-a1e5-0a2860986710";
        :>> title = "keel suite from PowerShell reports seven red tests that are green from git-bash: a test shells to sh";
        :>> createdAt = "2026-09-08";
        :>> createdBy = "claudeOpus5";
        :>> description = "keel suite launched from PowerShell reports seven red tests that are green from git-bash. Every test in keel-cli/tests/wrapper_resolves_only_the_pin.rs computes its fixture checksum by spawning `sh -c sha256sum` (line 41), and a PowerShell process on this host has no `sh` on PATH: the seven panic with `sha tool: Error { kind: NotFound, message: 'program not found' }` and the suite writes a `fail` receipt (fingerprint 37f6d8356120, 2026-09-08) over a deliverable that the same suite, launched from git-bash, passes 589/0. The verdict depends on the launching shell, which is the issue065 friction class reaching the suite receipt. Resolver: the test computes the checksum in Rust (sha2 is already a dependency of the wrapper's checksum path, or the test resolves `sh` through the same probe the wrapper uses and SKIPS with a named reason when no POSIX shell is present) - the suite's receipt must not turn on PATH.";
        :>> discoveredInField = false;
        :>> severity = Severity::High;
    }
    #Resolves dependency from dcSuiteReceiptDoesNotTurnOnPath to issue412;

    part issue413 : Issue {
        :>> id = "9400c842-cbda-4f2e-9268-ce415a915ecd";
        :>> title = "The brief contract declares word budgets that no check holds: a 1334-word page passed clean";
        :>> createdAt = "2026-09-08";
        :>> createdBy = "claudeOpus5";
        :>> description = "The brief contract declares word budgets that nothing holds. The asi-templates skill's section table (section 2.1) sets the headline at 18 words, the ask at 70, the decision rule at 40, the provenance strip at 60 - and check_brief in scripts/check_templates.py (line 212 onward) checks ids, verbs, options, figures, provenance date, copy controls, viewport and themes, but not one word count; the BUDGETS loop at line 125 belongs to the template-family check and never runs on a brief. The page published on 2026-09-08 carried a 26-word headline and 1334 words of reader prose and reported `brief contract: clean`. The human, verbatim (st109): 'the decision brief is still far too verbose.' A budget that lives in a skill and not in the check is a reminder, and D0047 says a reminder is not a control. Resolver: check_brief holds the declared budgets and refuses over them, with a self-test fixture in both directions.";
        :>> discoveredInField = false;
        :>> severity = Severity::High;
    }
    #Resolves dependency from dcBriefBudgetsAreHeld to issue413;

    part issue414 : Issue {
        :>> id = "7f269461-d8fb-402c-9571-7e7d971ca922";
        :>> title = "A rejection given in chat has no CLI write path; the first one was a hand edit";
        :>> createdAt = "2026-09-08";
        :>> createdBy = "claudeOpus5";
        :>> description = "The human answered the 2026-09-08 brief with '[x] Reverse: do not republish when the queue is empty (answers: d0376)' - a REJECTION of a proposed Decision. keel has `keel accept` for the acceptance half of the review loop with delegation, quote receipt, read-back ratification and createdBy stamping, and NO CLI for the rejection half: write::reject_decision (keel-cli/src/write.rs:1875) is reachable only through the console's POST /api/decision/reject (serve.rs:851), which needs a paired device. So the first rejection in this project's history (d0376) was recorded by a hand edit that mirrors the writer's block, and no guard can tell that record from a fabricated one - the asymmetry D0122 named ('we have an accept button, but not a reject') now sits in the CLI. Found by: `keel --help | grep reject` (nothing) and `grep -n reject_decision keel-cli/src/*.rs` (serve.rs and write.rs only).";
        :>> discoveredInField = false;
        :>> severity = Severity::High;
    }
    #Resolves dependency from dcRejectHasACliPath to issue414;

    part issue415 : Issue {
        :>> id = "7382fe44-36f0-4139-9cf6-22358273b176";
        :>> title = "The routing rig scores the first Skill call, and intake is declared to run first on every human direction - the release case split 1 routed / 2 wrong on that criterion";
        :>> createdAt = "2026-09-08";
        :>> createdBy = "claudeOpus5";
        :>> description = "The routing rig's first investigation (2026-09-08, sprint609) found the release case disagreeing with itself: three samples of the prompt 'Time to make this obtainable by someone outside this machine, with a version that actually means something.' at three turns gave ROUTED once and WRONG twice, both wrong samples invoking intake first ($1.95 measured, 49s wall; .keel/metrics/routing-investigation.json). Under D0381 that disagreement is a defect of the CHECK, not a rate. WHAT THE CHECK DOES: it scores the FIRST Skill call of the turn, and only the first name was kept. WHAT COLLIDES WITH IT: the intake skill's own deployed description reads 'Use at the START of any turn where the human states direction' (.claude/skills/intake/SKILL.md:3), and the release prompt is phrased as a human's direction - so an agent that runs intake first and release second is following the process exactly as written, and the rig scores it WRONG. Sample 3 invoked Skill twice and the rig recorded neither the second name nor the order (fixed in the same sprint: skillsInvoked now holds every call). WHY IT MATTERS: every case in routing_prompts.toml is phrased as a person talking, so this is not one flaky prompt - the first-call criterion is wrong for the whole table whenever intake behaves as declared, and any before/after investigation of a skill rewrite would be reading intake's behaviour, not the skill's. WHAT WOULD SETTLE IT: the verdict reads the whole turn - the intended skill invoked within budget is a route; intake preceding it is recorded as a prefix, not a wrong route, because its description declares that position; a different skill first stays wrong - and the release case is re-run three times to read unanimous or to disagree again for a reason the samples show.";
        :>> discoveredInField = false;
        :>> severity = Severity::Medium;
    }
    #Resolves dependency from dcRoutingVerdictReadsTheWholeTurn to issue415;

    part issue416 : Issue {
        :>> id = "70377808-a1ac-4d04-8dcb-8f7a735fece4";
        :>> title = "A module changed, its integration test was stale, the commit gate was green and CI was red - nothing between edit and push runs the tests that name the module";
        :>> createdAt = "2026-09-08";
        :>> createdBy = "claudeOpus5";
        :>> description = "Sprint 610 changed keel-cli/src/view/control_structure.rs and landed at f49684f with a green commit gate and a red CI: keel-cli/tests/control_structure_is_computed.rs, the integration test of that very view, asserted the shape the change replaced (the channel role reading inert) and had not been run. The implement gate's receipt named `cargo test --release control_structure`, which errors on the cucumber harness's filter argument, so the run that actually happened was `--lib` - the unit tests inside the module, eight green - and the receipt overstated it. The full suite exists (`keel suite`) and its land gate was withdrawn by the human as too costly for what it catches (D0356), so nothing between an edit and a push runs the integration tests that name the module being edited. That is a narrower and cheaper set than the suite: here, one file, four seconds. The class is a change to a module whose out-of-tree test is stale, found by CI after the push - a red main that the next contributor pulls.";
        :>> discoveredInField = false;
        :>> relatedTask = "stpaStepTwoIsCompleteStory";
        :>> severity = Severity::Medium;
    }
    #Resolves dependency from dcTouchedTestsRunBeforeLand to issue416;

    part issue417 : Issue {
        :>> id = "0c0b3c38-0e75-434f-9f2b-3b2806626bcc";
        :>> title = "The release publishes binaries and no checksum, while the wrapper contract names one the release page never carried";
        :>> createdAt = "2026-09-08";
        :>> createdBy = "claudeOpus5";
        :>> description = "The release publishes three binaries and no checksum. `gh release download v0.4.1` returns keel-linux-x86_64, keel-macos-aarch64 and keel-windows-x86_64.exe and nothing else; .github/workflows/release.yml has no step that hashes an asset, and its publish step lists only the binary. Yet the wrapper contract says the opposite: keel-wrapper.toml's header reads 'Entries are computed from the PUBLISHED release assets', and `keel init` writes 'Entries come from the release page's published checksums' (keel-cli/src/main.rs:3733) - a checksum the release page has never carried. Every entry in keel-wrapper.toml was produced by downloading the asset and hashing it locally, which is a hand step nothing names and nothing checks, and it verifies the binary against itself: a swapped asset hashed after the swap yields a matching entry. The human's observation, 2026-09-08: 'looks like keel release doesn't have a checksum? it needs one' / 'make a normal part of process'. The checksum has to come out of the same workflow run that built the binary, beside it, and the release process has to name it as a step with a control that fails when the workflow drops it.";
        :>> discoveredInField = false;
        :>> severity = Severity::High;
    }
    #Resolves dependency from dcReleaseAssetsCarryChecksums to issue417;

    part issue418 : Issue {
        :>> id = "bab3d8b5-b505-43a3-9199-3836266ca220";
        :>> title = "The engine pin moved to 0.4.1 with no wrapper checksum entry, so keelw has refused every fresh clone since the release";
        :>> createdAt = "2026-09-08";
        :>> createdBy = "claudeOpus5";
        :>> description = "The engine pin moved to 0.4.1 with no wrapper checksum for it, and nothing said so. .engine/contracts/engine-version.toml:4 reads `engine = '0.4.1'` since b171cd7 (2026-09-06); keel-wrapper.toml carries entries for 0.3.1 only, last edited 2026-08-29. keelw line 69 dies on that state - 'no committed checksum for keel 0.4.1 ... a download that nothing verifies must not run' - so every fresh clone that runs the wrapper has been refused since the v0.4.1 release two days ago, while every gate here stayed green: the release skill's four steps never mention the wrapper contract, and no guard reads the pin against the checksum table. The release recorded (release041 in .tracking/baselines.sysml) was verified by running a downloaded asset (D0137), which proves the asset, not the contract that lets a downstream project obtain it. Two gaps, one class: a release step that lives in nobody's process text and has no control.";
        :>> discoveredInField = false;
        :>> severity = Severity::High;
    }
    #Resolves dependency from dcReleaseAssetsCarryChecksums to issue418;

    part issue419 : Issue {
        :>> id = "b1d45760-1936-4c2f-a980-a98ceff13e9a";
        :>> title = "validate reads clean over a tree it did not judge";
        :>> createdAt = "2026-09-09";
        :>> createdBy = "claudeOpus5";
        :>> description = "`keel validate .` answers `708 tracking file(s) validated clean` over a tree whose `.engine/decisions` holds a value the schema no longer has. Observed 2026-09-09 in sprint 622 (D0398, the `superseded` member leaving `DecisionStatus`): after the CONTRACT step, validate stayed green and exit 0 while `keel check-engine .` was the command that refused the member by name. The verdict is TRUE - validate judges `.tracking` only - but two authors in one day read it as the schema gate: D0398's consequences and the sprint's first DoD both said 'keel validate refuses', and the integration test had to be written against check-engine after running both. A verdict that does not name the tree it judged reads as covering the whole project. Resolver: dcValidateNamesItsScope.";
        :>> discoveredInField = false;
        :>> severity = Severity::Medium;
    }
    #Resolves dependency from dcValidateNamesItsScope to issue419;

    part issue420 : Issue {
        :>> id = "89d71590-28d0-4d29-9ae2-c95b9379b15d";
        :>> title = "The brief's facts script read a Decision's standing from the status field after D0398 moved retirement to the edge";
        :>> createdAt = "2026-09-09";
        :>> createdBy = "claudeOpus5";
        :>> description = "scripts/exec_brief/facts.py read a Decision's standing from the status field alone after D0398 moved retirement to the #Supersede edge. Observed 2026-09-09 at 649b433, the commit after the migration: decisionsProposed = 3 against orient pendingAcceptances = 1 (d0038 and d0353 are retired by edge and keep the status they had), pendingAlreadyShipped listed d0353, and the D0384 census facts reported five 'disagreements' over Decisions the migration had retired whole. The brief builder would have published those numbers. Class: a change to what a field MEANS was doc-synced across the Rust readers and the doc surface, and the one Python reader of the same field was not in the grep because it names the field by regex, not by the enum member that left. Resolver: dcBriefFactsReadStandingFromTheEdge - the retired set is subtracted where standing is read, and the file-derived pending count is refused when it disagrees with the engine's, so the next drift of this kind publishes null with the two numbers named, not a count.";
        :>> discoveredInField = false;
        :>> severity = Severity::Medium;
    }
    #Resolves dependency from dcBriefFactsReadStandingFromTheEdge to issue420;

    part issue421 : Issue {
        :>> id = "da5c33b3-8cec-4031-84b6-56e7c0cd6da6";
        :>> title = "Batch git stdin written inline deadlocked orient once the request crossed pipe capacity";
        :>> createdAt = "2026-09-09";
        :>> createdBy = "claudeOpus5";
        :>> description = "orient's batch git calls (valid_commits over `cat-file --batch-check`, batch_cat_blobs over `cat-file --batch`) wrote the child's whole stdin from the parent thread and then called wait_with_output. Once the request list exceeded the pipe's capacity while the child's stdout was itself full, both sides blocked forever: git waiting for its output to be drained, keel waiting to finish writing input. It surfaced when dcResultBindsToItsLandingCommit added 40-hex result ids to the request (the extra bytes crossed the threshold) and `keel orient .` hung with git alive and keel idle. Control: `orient::feed_stdin` writes stdin from its own thread while the parent drains stdout, in both sites; a further batch caller that writes stdin inline is the same defect.";
        :>> discoveredInField = false;
        :>> severity = Severity::High;
    }
    #Resolves dependency from dcResultBindsToItsLandingCommit to issue421;

    part issue422 : Issue {
        :>> id = "4d439585-508f-4bc5-9e0d-cb4cc5542735";
        :>> title = "issue044 escape class recurred in orient's historical criterion reader, six false OWN-drift suspects";
        :>> createdAt = "2026-09-09";
        :>> createdBy = "claudeOpus5";
        :>> description = "The issue044 class (a raw blob read cut at the first double quote without decoding escapes, so the historical text never equals the parser's text) recurred in orient's criterion reader: `extract_dod_criterion` and the `git grep` fallback compared a DoD literal carrying an escaped quote or an escaped regex class against the parsed text and read six done tasks (critiqueBatch8 among them) as OWN-criterion drift over a byte-identical line, the moment dcResultBindsToItsLandingCommit made their baseline old enough to contain the DoD. Control: `orient::string_literal_body` mirrors the lexer's escapes and returns None for one it does not know; the unit test `the_historical_criterion_reads_a_literal_as_the_lexer_does` holds it equal to `keel_parser::tokenize`; gitfacts drops every cached criterion/grep text written by an older reader (`criterion_reader` below 2) on load, so the wrong texts are not served from cache.";
        :>> discoveredInField = false;
        :>> severity = Severity::High;
    }
    #Resolves dependency from dcResultBindsToItsLandingCommit to issue422;

    part issue423 : Issue {
        :>> id = "7502883c-a481-44cd-9a38-2d99f9560694";
        :>> title = "A CLI synopsis can cite a retired Decision and no control notices";
        :>> createdAt = "2026-09-09";
        :>> createdBy = "claudeOpus5";
        :>> description = "A CliCommand synopsis can cite a Decision that has since been retired, and no control notices. The cliSuite synopsis read 'the machine-local receipt keel land demands - a deliverable that changed since the last green run does not push (D0353)' in both fact homes (.engine/cli/commands.sysml and keel-cli/src/cli_facts.rs) from the day D0356 withdrew that gate until sprint 625 corrected it in passing - three days of `keel --help` describing a gate that did not exist. Guard cli-surface-declared holds the two homes EQUAL but does not read what they say; the citation of a retired Decision is checkable from facts the indexer already holds (the decision files and the #Supersede edge set, D0398). Found by reading, not by a control.";
        :>> discoveredInField = false;
        :>> severity = Severity::Medium;
    }
    #Resolves dependency from dcSynopsisCitesLiveDecisions to issue423;

    part issue424 : Issue {
        :>> id = "ee418a3d-09e2-42eb-9c9a-d4d444c165ed";
        :>> title = "The retro-backlog guard reads d0388 but not D0388, the form every document writes";
        :>> createdAt = "2026-09-09";
        :>> createdBy = "claudeOpus5";
        :>> description = "The retro-backlog guard (guards.rs named_items) recognises a Decision only as lowercase d0NNN, while the repository's documents, CLAUDE.md, commit messages and the guard's own messages write D0NNN. Sprint 627's retro said 'already tracked by D0388 and its probe rule' and the guard reported it 'names no item at all'; sprint 626 wrote the same form and passed only because the sentence also named issue423. So a justification pointing at a real Decision in the documented spelling is unverified, and the pass it does get is accidental - the issue364 class under a different mask. Found 2026-09-09 committing sprint 627.";
        :>> discoveredInField = false;
        :>> severity = Severity::Medium;
    }
    #Resolves dependency from dcRetroNamesDecisionsAsWritten to issue424;

    part issue425 : Issue {
        :>> id = "c200afe4-4809-4c80-adb7-a7aca10a4489";
        :>> title = "The brief stacked its asks, priced courses in days, and counted a set it never named - and the checker passed all three";
        :>> createdAt = "2026-09-09";
        :>> createdBy = "claudeOpus5";
        :>> description = "The standing decision brief published on 2026-09-09 (three asks, built by scripts/exec_brief/build_2026_09_09_three_asks_tests_bind.py) carried three defects the human read off it in one message: the asks were stacked on one page rather than one tab each; the courses stated an implementation duration ('A five collapses, a day each.'), which the human does not want and cannot judge correctness by; and it counted a set without naming it ('collapse five families ... 70 to 20') so the reader could not check what was being collapsed - and the typed remainder (20) disagrees with the count the members give (34 of 67 live verbs remain under D0399 option A's own mapping). scripts/check_templates.py --brief had a clause for none of the three, so all passed 'clean'. Their words: 'for the decision panel, make each ask a separate tab. and don't tell me how long things should take to implement - i really don't care. i care about correctness. and how can i gauge that if you don't tell me what you're collapsing? 'collapsing 5 reads/writes' is irrelevant - i want to know *what* is being collapsed. totally avoiding the root of the issue.' Root: the brief contract enumerated budgets and exhibits but not the shape of a course's cost or the obligation to name a counted set; the fix is three checker clauses with known cases (D0404, D0405, D0406), a members fact, and a tabbed builder, and the ceiling clause they force (D0407).";
        :>> discoveredInField = false;
        :>> severity = Severity::High;
    }
    #Resolves dependency from storyBriefTabsNoDurationsNamedMembers to issue425;

    part issue426 : Issue {
        :>> id = "0fc6a6fe-575b-4ae4-9602-9a1e6d042391";
        :>> title = "A gesture citation in an acceptance note is free text the recorder writes, not a receipt the command writes";
        :>> createdAt = "2026-09-09";
        :>> createdBy = "claudeOpus5";
        :>> description = "Found by stpa-self run 2 (UCA-AC1, cmdAccept provided from an agent session) by code read, 2026-09-09. The acceptance channel refusal (keel-cli/src/main.rs verdict_channel_refusal) accepts a note from an agent-marked session with delegation declared when either the note quotes the human or quotes_conversational_words (keel-cli/src/view/checks.rs, the substrings deck, console, github comment, github.com/, tty gesture) returns true; read_back_names (keel-cli/src/view/mod.rs) returns the same answer when the note has no quoted span. So keel accept <d> --note 'approved at the console' --by <human>, run from an agent session, is written with nothing quoted and no receipt. The console's own record appends the text [device <id> HMAC-verified] (keel-cli/src/serve.rs) but does not store the signature, so a typed copy of that tag is indistinguishable at the gate; KEEL_TTY_GESTURE=1 makes tty_gesture() report an asserted gesture from a session with no terminal. The gap: a gesture citation is free text the recorder writes, not something the command writes and the tree can re-verify. Hazard EHZ3 (the AI records human judgment). Not a fabricated acceptance in the tree today - the check is that none of the acceptance notes at HEAD cite a gesture without the command's own device tag - but the channel is open.";
        :>> discoveredInField = false;
        :>> severity = Severity::High;
    }
    #Resolves dependency from dcGestureCitationsAreWrittenByTheCommand to issue426;

    part issue427 : Issue {
        :>> id = "8d8d1808-36a5-4709-8378-606f7a11f820";
        :>> title = "An override unlock matches the written path by substring, so a directory target unlocks any file under it";
        :>> createdAt = "2026-09-09";
        :>> createdBy = "claudeOpus5";
        :>> description = "Found by stpa-self run 2 (UCA-O1, cmdOverride provided with a wide target) by code read, 2026-09-09. keel-cli/src/main.rs consume_override matches an armed unlock against the written path by substring in EITHER direction (written_path.contains(target) || target.contains(written_path)), so keel override .tracking --reason '...' arms an unlock that the next write to ANY path containing .tracking consumes, and a short target covers every path containing it. The unlock is single-use and expires after OVERRIDE_TTL_SECS (900), and the consumed write is recorded as an obligation naming the path written, so the exposure is one write of the agent's choosing under a target that named no file. Hazard EHZ2 (a write lands outside a validated channel). Resolver: keel override refuses a target that is not one file and consume_override matches by canonical path equality.";
        :>> discoveredInField = false;
        :>> severity = Severity::Medium;
    }
    #Resolves dependency from dcOverrideBindsToOneFile to issue427;

    part issue428 : Issue {
        :>> id = "70c6ead2-1da7-48b4-a7ff-48a91c750b99";
        :>> title = "A Decision that cites the human's direction carries no Statement of their words to check it against";
        :>> createdAt = "2026-09-09";
        :>> createdBy = "claudeOpus5";
        :>> description = "Found by stpa-self run 2 (UCA-H1, humanDirects provided as words the agent renders) by code read, 2026-09-09. The computed control structure (keel show control-structure, keel-cli/src/view/control_structure.rs) records humanDirects as a prose channel nothing parses. A Decision may today say 'the human's words: ...' in its context or rationale, and a task DoD may cite their instruction, with no Statement recorded and no #DerivedFrom edge - so the tree holds the agent's rendering of what the human said and nothing to check it against, and D0289's quote-as-receipt applies only to acceptances, not to the direction that produced the Decision. The intake path (keel record statement, D0216/D0236) exists but only business-elicitation is bound to it; keel hardening (D0166) reports unsourced items as a view and gates nothing. Hazard EHZ3 (an actor is misattributed - the words are attributed to the human without their record). Resolver: a forward-only guard clause requiring a Decision or DoD that quotes the human to carry a #DerivedFrom edge to a Statement holding that span verbatim, grandfathering and counting the existing ones.";
        :>> discoveredInField = false;
        :>> severity = Severity::Medium;
    }
    #Resolves dependency from dcDirectionDecisionsLinkTheirStatement to issue428;

    part issue429 : Issue {
        :>> id = "490f4484-0a12-4ba8-8a3d-e071c698c8c1";
        :>> title = "a slow hook fire is unexplained by its own ledger line - the human reads keel as crazy slow and the tail cannot be attributed";
        :>> createdAt = "2026-09-09";
        :>> createdBy = "claudeOpus5";
        :>> description = "The human, 2026-09-09: 'kind of seems like keel is still crazy slow.' MEASURED before any claim (keel enforcement-report . and a read of .keel/metrics/hooks.jsonl over the last 36 hours, 21 hours holding events): stop 179 fires, median 617 ms, p90 5728 ms, max 35201 ms, 454 s in total; subagent-stop 42 fires, median 2708 ms, p90 7154 ms, max 38219 ms, 199 s; user-prompt 42 fires, median 1149 ms, max 27964 ms, 71 s; post-edit 384 fires, median 0 ms, max 56095 ms; one hook-watchdog-timeout at 120000 ms. Blocking hook time in the window is about 13 minutes, and the tail carries it - fifteen stop runs over 6 s and three events over 27 s. WHAT THE IDLE MACHINE SAYS: a full stop run (KEEL_NO_RECEIPT=1 keel hook stop .) takes 2650-2990 ms across nine samples; a receipt hit takes 217 ms; the same full run sampled five times while cargo build --release ran took 6590, 5983, 4295, 3478 and 3290 ms - so contention from the session's own builds accounts for a 2.3x tail, and the ledger's slow runs sit in editing bursts (post-edit and pre-bash within 120 s of each of the last twelve). WHERE THE 2.8 s GOES (KEEL_PERF=2): validate about 0.4 s, view::check about 0.2 s, and the guard set 2.2 s of wall whose critical path is ONE guard - priority-inversion at 2102 ms of the 2200 ms run, because it recomputes the ready frontier (Model::build x8, git x9 in 580 ms, parse 491 ms) while 76 other guards finish under it; 44 git spawns cost 4114 ms summed across threads. WHAT IS NOT EXPLAINED: a 35 s stop, a 38 s subagent-stop, a 28 s user-prompt and a 120 s watchdog timeout are 4-12x the loaded measurement, and the ledger line carries only ts, event, exit, ms, bin and build - it cannot say which phase took the time, so a tail is reproduced after the fact or not at all. THE DEFECT: a slow turn boundary is unexplained by its own record. The perf counters that would explain it exist (perf.rs, KEEL_PERF) but are off in the hooks, so the one place the cost is felt is the one place it is not attributed. Until the ledger says where a slow run's time went, every answer to 'keel is slow' is a reproduction on a different machine state, which is the inference class perf.rs was built to stop.";
        :>> discoveredInField = false;
        :>> severity = Severity::High;
    }
    #Resolves dependency from dcSlowHookFireExplainsItself to issue429;

    part issue430 : Issue {
        :>> id = "d12e0e30-8250-43dd-b443-65c2bddb7dd8";
        :>> title = "The dominant-source setting D0364 took no longer holds its own no-regression rule on the one-hop arm";
        :>> createdAt = "2026-09-09";
        :>> createdBy = "claudeOpus5";
        :>> description = "FOUND 2026-09-09 by the first run of recall_bench.py --sweep (sprint 636, dcSweepSaysWhenItCouldNotChoose). CHECK: python .engine/tools/recall_bench.py --sweep DOMINANCE=0,1.25 on the default one-hop arm, 50 cases, tree df7a54e plus the sweep's own uncommitted script: DOMINANCE=0 -> hits 46/50, median position 2, top-3 33/46; DOMINANCE=1.25 -> hits 46/50, median position 3, top-3 29/46; verdict DISCRIMINATED on KEEL_RECALL_DOMINANCE: median position moved - hits 46..46; median position 2..3; top-3 29..33. The same sweep on --hops 2: 0 -> 19/50 median 5 top-3 0/19; 1.25 -> 24/50 median 5 top-3 6/24; verdict DISCRIMINATED, hits moved 19..24. MECHANISM: D0364 took DOMINANCE 1.25 on 2026-09-07 under the rule that the near set must hold (49/50 median 3 at every setting then, 'hits, median position and mean rows all held'); the tree has since grown to 17311 items and the one-hop set now has cases the bonus touches - at 1.25 it displaces the target by one median position and out of four top-3 placements. The plain default run's hits also read 46/50 against sprint 593's 49/50, which the sweep cannot attribute to the knob (both values give 46) and this Issue does not. CONSEQUENCE: the setting in force fails the rule that chose it, on the current tree, and either the constant or the rule has to move - which one is a judgment. PREVENTING CHANGE: dcDominanceRechosenUnderItsOwnRule - both arms swept, D0364's rule applied to the two verdict lines, the outcome recorded as a Decision or surfaced as a fork.";
        :>> discoveredInField = false;
        :>> severity = Severity::Medium;
    }
    #Resolves dependency from dcDominanceRechosenUnderItsOwnRule to issue430;

    part issue431 : Issue {
        :>> id = "a1d624a1-85ed-4bf2-b171-6b21683202fa";
        :>> title = "routing_probe.py unlinked its last receipt before the estimate read it, so every estimate quoted the 2026-09-06 constant and every dry run erased the previous investigation";
        :>> createdAt = "2026-09-09";
        :>> createdBy = "claudeOpus5";
        :>> description = "routing_probe.py unlinked .keel/metrics/routing-investigation.json as the first statement of main(), before last_measured() read it and before the --dry-run branch returned. Two consequences, both read from the code at .engine/tools/routing_probe.py (the unlink at the top of main, last_measured() called after it): every estimate fell back to the 2026-09-06 constant ($0.52, 25 s) however many investigations had been paid for since, and every dry run erased the last real receipt - which is why the sprint609 release investigation named in issue415 was absent from disk on 2026-09-09 before anything had been run. Found by: opening the receipt to read the sprint609 samples and finding no file. Fixed in the same commit as dcRoutingVerdictReadsTheWholeTurn: the unlink moved after the estimate and after the dry-run return; verified by a dry run after a paid run quoting $1.24 / 47 s measured 2026-09-09 with the file still present.";
        :>> discoveredInField = false;
        :>> severity = Severity::Medium;
    }
    #Resolves dependency from dcRoutingVerdictReadsTheWholeTurn to issue431;

    part issue432 : Issue {
        :>> id = "9a77a7be-e29d-4e1d-ba34-70b9cd653c02";
        :>> title = "Under the whole-turn verdict the release case read 3/3 none at 3 turns with intake as every sample's prefix - the declared prefix spends the budget, so none cannot tell not-routing from exhaustion";
        :>> createdAt = "2026-09-09";
        :>> createdBy = "claudeOpus5";
        :>> description = "The whole-turn verdict re-ran the release case three times at the default 3-turn budget (2026-09-09, $3.71, 59 s wall, .keel/metrics/routing-investigation.json) and read 3/3 none with prefix intake: every sample invoked intake in its first turn and spent the remaining two on ToolSearch / Read (sample tools: Skill, ToolSearch, ToolSearch; Skill, ToolSearch, Read, Read), so the intended skill never appeared before the budget ended. The samples agree, but on a reason they show: the declared prefix spends the budget the intended skill needed, and the rig's `none` cannot tell 'did not route' from 'ran out of turns after the process's own declared first step'. The sprint609 run at the same budget saw intake-then-release once, so the second skill is reachable in 3 turns but not reliably. WHAT WOULD SETTLE IT: the verdict names exhaustion after a prefix apart from silence - a turn whose prefix ran and whose tool calls continued to the last turn is `budget`, not `none` - and the release case is re-run at a budget that leaves the prefix room (6 turns) to read whether release appears once intake has finished. The receipt also records the per-run cost at $1.24 against the $0.52 estimate the rig carried; the estimate now reads the last receipt (issue431).";
        :>> discoveredInField = false;
        :>> severity = Severity::Medium;
    }
    #Resolves dependency from dcPrefixLeavesRoomForTheRoute to issue432;

    part issue433 : Issue {
        :>> id = "a10fdafc-c2f7-490e-88dd-564d6b042938";
        :>> title = "guard cli-surface-declared's citation check (e902566) fails every downstream tree - CI red six pushes";
        :>> createdAt = "2026-09-09";
        :>> createdBy = "claudeOpus5";
        :>> description = "The synopsis-citation check added to guard cli-surface-declared at e902566 (D0412, issue423) ran in every tree. The Decisions a synopsis cites are the ENGINE's; a downstream project's .engine/decisions holds that project's own Decisions and ships from keel init with none, so every scaffolded tree read as citing twelve missing Decisions (d0301, d0323, d0296, d0356, d0338, d0311, in both fact homes). CI was red for six consecutive pushes (e902566 through afd90d0): adoption_check_can_fail failed on the scaffold it builds, and push_gate_is_withdrawn failed locally because keel land refused the fixture's push on the same twelve violations. The check must read only a tree that holds the engine's Decision channel, recognised by D0271 being present.";
        :>> discoveredInField = false;
        :>> severity = Severity::Critical;
    }
    #Resolves dependency from dcCitationCheckHoldsWhereTheDecisionsLive to issue433;

    part issue434 : Issue {
        :>> id = "bf49c6f0-b364-4239-8576-2098c214e978";
        :>> title = "CI reported green for f848923 and afd90d0 while red: a wrapper's exit code was read as the run's conclusion";
        :>> createdAt = "2026-09-09";
        :>> createdBy = "claudeOpus5";
        :>> description = "Two reports in this session said CI was green for f848923 and afd90d0 while both runs had FAILED (adoption_check_can_fail, issue433). The mechanism: a background command of the form gh run watch <id> --exit-status > /dev/null 2>&1; echo 'ci exit=$?' - the harness reported the wrapper's exit code, 0, and the report was read from that instead of from the run's conclusion. The verdict of a CI run is the conclusion field of gh run list --json conclusion (what keel status reads for HEAD); a wrapper's exit code is not evidence of anything. The correction is a control in the binary: keel land names the CI verdict of the base it is about to push onto, from that field, before every push - a red base is then said at the moment it matters, and the reading is the binary's, not a transcript's.";
        :>> discoveredInField = true;
        :>> severity = Severity::High;
    }
    #Resolves dependency from dcLandNamesTheCiVerdictOfTheBase to issue434;

    part issue435 : Issue {
        :>> id = "341abbee-4a44-433e-ae37-bf3dc3d19253";
        :>> title = "The touched-test refusal armed itself: the acceptance check matched the token in D0421's own prose";
        :>> createdAt = "2026-09-09";
        :>> createdBy = "claudeOpus5";
        :>> description = "The touched-test refusal armed itself at record time. gate_accepted in keel-cli/src/touched.rs tested whether the D0421 file CONTAINED the string d0421AcceptR1; D0421's own decision text names that token as the thing that will arm it ('once this Decision carries the human's acceptance (d0421AcceptR1 in its file)'), so the check read the sentence describing the arming as the arming. Observed on the first live use: the post-commit hook's keel land for 9d574f8 printed the 24-binary set and then, instead of the INERT line the proposed state owes, reached the own-image refusal (issue386) and did not push - the check that established it is the hook's output in the commit log, and the decision file's line 19 which is the only occurrence of the token. The class is a text-match standing in for an attestation: an acceptance is the DECLARED part `<dec>AcceptR1 : TestResult` with outcome pass, the shape keel accept writes, and nothing else - the same rule govern.rs already applies when it reads the acceptance's commit. While proposed, D0421's gate would have refused every hook-driven push once cargo was reachable; the own-image refusal masked it as the wrong error.";
        :>> discoveredInField = false;
        :>> severity = Severity::Critical;
    }
    #Resolves dependency from dcArmingReadsTheAcceptancePart to issue435;

    part issue436 : Issue {
        :>> id = "e99b9363-2bdb-469c-b6c6-fbbff99bcd6f";
        :>> title = "The post-commit hook runs land from the image an armed touched run relinks";
        :>> createdAt = "2026-09-09";
        :>> createdBy = "claudeOpus5";
        :>> description = "The post-commit hook runs keel land from ./target/release/keel.exe - the very image cargo test --release relinks - so once D0421 is accepted every hook-driven push of a change that touches a named module would meet the own-image refusal (issue386) and not push, while a land run from a copy would run the set and push. Observed on 9d574f8 (the hook's land reached the refusal because of issue435, but the path is the same when legitimately armed): .githooks/post-commit chooses `keel` on PATH, else ./target/release/keel.exe, and never a copy. The control's own home cannot run the control. The fix is in the hook - copy the binary to a land-only image before running land - which is the enforcement surface (D0209 clause 2) and needs its co-committed marked Decision; it should land before D0421 is accepted, or the acceptance arms a refusal that fires on every hook push.";
        :>> discoveredInField = false;
        :>> severity = Severity::High;
    }
    #Resolves dependency from dcHookLandRunsFromACopy to issue436;

    part issue437 : Issue {
        :>> id = "30ba539b-9de5-47ff-833a-8c8567601a85";
        :>> title = "The hook's land copy was never made: command -v keel resolves into target/release and the case matched literal paths";
        :>> createdAt = "2026-09-09";
        :>> createdBy = "claudeOpus5";
        :>> description = "The post-commit hook's land-from-a-copy (D0422, sprint 642) never made the copy. The hook resolves the binary with `command -v keel` first, and on this host that answers ./target/release/keel because the self-build's target directory is on PATH - so KEEL was the bare word keel, the case block matched only the literal ./target/release/keel(.exe) paths, and the commit that carried the change (b522674) ran land from the relinked image again: after it, target/release/keel-land.exe did not exist (ls), and `command -v keel` printed the target path. The probe before the edit checked the two literal shapes and a PATH keel assumed to live elsewhere; the negative was chosen from an assumption about the host, not read from it. Same class as issue435 - the check was probed, but not against the case that was live.";
        :>> discoveredInField = false;
        :>> severity = Severity::High;
    }
    #Resolves dependency from dcHookCopyFollowsPathResolution to issue437;

    part issue438 : Issue {
        :>> id = "f5330c5a-d8e0-4f32-b1e1-d43d574a2eca";
        :>> title = "CI red on cab7cac: a lib unit test hardcoded the suite synopsis's citations, and the touched set never runs the lib tests";
        :>> createdAt = "2026-09-09";
        :>> createdBy = "claudeOpus5";
        :>> description = "CI red on cab7cac (run 34419851075, conclusion failure, job rust step test): guards::cli_surface_declared_tests::a_synopsis_citing_a_retired_or_absent_decision_is_a_violation_and_the_live_suite_synopsis_is_not hardcoded the present set as {d0271, d0356} and used the LIVE suite synopsis as its known-negative; sprint 640 added a D0421 citation to that synopsis, so the live text cited a Decision the test's fixed set did not hold. Two defects: the test encoded 'cites exactly D0356' where the property is 'cites only what is in force'; and the touched set (D0421) covers keel-cli/tests/*.rs only, so a lib unit test that reads a changed module's facts is never in the pre-push set - and the session's own check ran the lib tests filtered to `touched`, which is why 450 green unit tests hid one red. The class is the one D0421 exists for, in the one place D0421 did not look.";
        :>> discoveredInField = false;
        :>> severity = Severity::Critical;
    }
    #Resolves dependency from dcTouchedRunIncludesTheLibTests to issue438;

    part issue439 : Issue {
        :>> id = "4f2b7468-c612-439c-9a8d-6f1fb38bcfd8";
        :>> title = "The priority-inversion guard pays orient::compute whole for a ready list: 5.7 s critical path on every changed-tree turn boundary";
        :>> createdAt = "2026-09-09";
        :>> createdBy = "claudeOpus5";
        :>> description = "D0414's attribution works and answers the human's question - and the answer has not been acted on. Every attributed slow fire since ae58328 (8 lines, ledger .keel/metrics/hooks.jsonl, read 2026-09-09) names guard:priority-inversion as the critical path at a median 5711 ms of a ~6 600 ms subagent-stop fire; KEEL_PERF=1 keel guard . prints the same (6 287 ms). The guard computes inversions over the ready frontier, and view::priority_signals (view/mod.rs:3652) gets that frontier by calling orient::compute(root) whole - drift, sync position, burndown, every git read orient makes - to use one field. Standalone, keel whats-next takes 3.1 s on this host (parse 631 ms, git x9 924 ms, gitfacts:load 431 ms, the rest orient's own work); inside the parallel guard set that becomes 5.5-6.3 s under contention, and it bounds the wall clock of every turn boundary whose tree changed (stop fires since D0414: 3, median 6 844 ms, none under 1 s). The instrumentation was the deliverable of sprint 635; the reduction it points to was never recorded as work, so a measured hot spot sat unowned for a day while the human asked twice how the performance was.";
        :>> discoveredInField = false;
        :>> severity = Severity::High;
    }
    #Resolves dependency from dcPriorityGuardReadsTheFrontierCheaply to issue439;

    part issue440 : Issue {
        :>> id = "62ebbc59-ec29-448f-98b7-6224764d8fa6";
        :>> title = "The git-facts changed section keeps every past HEAD's rows: 24 of 27 MB, 416 ms parsed by every hook fire";
        :>> createdAt = "2026-09-09";
        :>> createdBy = "claudeOpus5";
        :>> description = "The git-facts cache (.keel/cache/git-facts.toml) held 26.9 MB on this host, and 24 MB of it was the changed section: the paths of git diff sha..head for every verified commit, keyed by the HEAD the question was asked under. HEAD only advances (D0129), so every row written under a past HEAD is dead - never asked for again on this clone - yet remember_changed kept them all: fourteen heads, one full path list per verified commit each, growing about 1.7 MB per commit. The file is parsed by every process that asks the cache anything, measured at 416 ms per load (KEEL_PERF=2 phase gitfacts:load), which every hook fire paid. Found while attributing the priority-inversion guard's critical path (issue439).";
        :>> discoveredInField = false;
        :>> severity = Severity::High;
    }
    #Resolves dependency from dcChangedCacheKeepsOneHead to issue440;

    part issue441 : Issue {
        :>> id = "4837ada9-64ec-48bc-ac97-ccec38b6121b";
        :>> title = "verification-trace is the guard set's critical path at 4.3 s once priority-inversion reads the frontier";
        :>> createdAt = "2026-09-09";
        :>> createdBy = "claudeOpus5";
        :>> description = "With the priority-inversion guard reading the frontier alone (issue439), the critical path of a full guard run on this host moved to verification-trace: 4318, 4289 and 4385 ms on three consecutive runs of KEEL_PERF=1 keel guard --no-receipt . at the new build, against a set wall clock of 5940 ms. Under parallel load its neighbours are inflated too (untrusted-taint 2999 ms, release-recorded 2278 ms, parser-coverage 2003 ms), so the next reduction has to be attributed before it is attempted - the guard has no phases of its own yet. The wall clock gained from issue439 was 6573 to 5940 ms, not the 5.7 s the priority guard had been paying, because this guard was just behind it.";
        :>> discoveredInField = false;
        :>> severity = Severity::Medium;
    }
    #Resolves dependency from dcVerificationTraceIsAttributedAndCut to issue441;

    part issue442 : Issue {
        :>> id = "199f54e4-97cf-4cc7-9f93-12b3481d5151";
        :>> title = "Hook latency and git-facts size are measured every fire and are not indicators, so no threshold can own them";
        :>> createdAt = "2026-09-09";
        :>> createdBy = "claudeOpus5";
        :>> description = "The per-turn hook cost and the git-facts cache size are measured every fire (the fire-ledger's ms and phases, D0389/D0414; the file's byte length on disk) and neither is an indicator, so no threshold can be declared for them in indicator-triggers.toml and nothing surfaces when they grow. issue440 sat visible in the cache's size for fourteen commits; issue439 and issue441 sat visible in the ledger's critical path. Sprint 644's retro named both as threshold candidates and folded them into issue441's work; sprint 645 found the indicator does not exist to threshold. Known positive: the ledger held a stop-hook median of 5711 ms for priority-inversion and a 26.9 MB git-facts.toml, both unowned. Known negative: ungroundedRatioIndicator, which has a threshold and triggers today.";
        :>> discoveredInField = false;
        :>> severity = Severity::Medium;
    }
    #Resolves dependency from dcHookLatencyIsAnIndicator to issue442;

    part issue443 : Issue {
        :>> id = "14cd3c7b-aa1d-42e9-92fe-d31c898c4dd9";
        :>> title = "The guard set's floor is one serial parse every guard waits on";
        :>> createdAt = "2026-09-09";
        :>> createdBy = "claudeOpus5";
        :>> description = "With issue439 and issue441 cut, the guard set's floor is the one serial parse every guard waits on. KEEL_PERF=2 keel guard --no-receipt . on 2026-09-09 after sprint 645: Model::build x38 (37 cached, 1 parsed), parse 1068 ms in one thread while the pool's other workers block on MODEL_BUILD_LOCK - verification-trace:model 1470 ms and priority:frontier 1370 ms are that wait, not work - and twenty guards then read 1.5-3.2 s each under contention, acceptance-binds-to-text 3198 ms at the head. build_uncached (view/mod.rs) parses the corpus file by file in one for loop and ingests in declaration order; corpus::parsed already makes each file's tree an independent unit, and guards.rs::run_in_parallel already sizes a std::thread::scope pool from available_parallelism. Known positive: the pre-sprint-644 ledger line 8337 ms with priority-inversion 7160 ms. Known negative: a fingerprint-equal rerun answers from the receipt in 0.2-0.3 s and parses nothing.";
        :>> discoveredInField = false;
        :>> severity = Severity::High;
    }
    #Resolves dependency from dcModelParsesInParallel to issue443;

    part issue444 : Issue {
        :>> id = "3a0aecef-2942-42c2-8b43-7a57cb7464ac";
        :>> title = "D0421 asked for a gate priced in seconds; the first live set cost 528 s, 90 percent of the suite the human withdrew for cost";
        :>> createdAt = "2026-09-09";
        :>> createdBy = "claudeOpus5";
        :>> description = "D0421 was proposed with its cost stated from the fixture - the set of one runs in about two seconds, a typical sprint names one to four binaries - and never measured on a live set before the human was asked to accept a gate on it. The first live set, the view-touching commit 5fbe410, named 15 integration binaries plus the lib: 528 s wall on this host (cargo test --release -p keel-cli --lib --test ... x15: compile 234 s, tests 286 s, 519 passed), against the full suite's 585 s at 9369863. A gate whose cost is 90 percent of the gate the human withdrew for cost (D0356) is not the Decision the text described. Known positive: the fixture's single-binary set, which does run in about two seconds. Known negative: the empty set on 4192458, which cost 0 s and is a receipt too. The recurrence class is D0388's: a figure stated before the check that would establish it, here the cost of a control on the very path it would gate.";
        :>> discoveredInField = false;
        :>> severity = Severity::Medium;
    }
    #Resolves dependency from dcTouchedCostIsMeasuredNotQuoted to issue444;

    part issue445 : Issue {
        :>> id = "7745f2a9-d6d0-47cc-ba9d-060832e19989";
        :>> title = "A refused keel accept (or any refused write) leaves no trace, so whether an agent ever tried to accept under the human's authority is unanswerable";
        :>> createdAt = "2026-09-10";
        :>> createdBy = "claudeOpus5";
        :>> description = "The human asked, 2026-09-10, whether any agent has attempted to accept a Decision under their authority - the question that decides whether the delegated-acceptance refusals (ten-character minimum D0375, read-back D0289, gesture citation D0411) guard anything. The record cannot answer it. CHECK: keel-cli/src/main.rs verdict_channel_refusal (lines 4446-4502) refuses and returns; a grep of that span for ledger, append, write or metrics matches only comment text - a refused keel accept writes nothing anywhere. The same holds for every keel write path that refuses (append-result without a receipt, record decision with tool output in prose): the refusal is a stderr line and an exit code, and the process's own instrument for what its controls did - the fire-ledger .keel/metrics/hooks.jsonl - never hears of it. What CAN be read: 453 acceptances recorded by AI actors and 73 by the human across .engine/decisions (grep createdBy), every one of which passed the gate that stood at its time; the guards' origins are issue059 (a vigilance gap, not an acceptance), issue426 (a UCA found by code read in stpa-self run 2, no observed attempt) and issue397 (the gate refused EIGHT correct human acceptances). So the empirical record of these controls is: zero observed subversions, eight observed refusals of the human, and no instrument that could have counted the first. A control whose refusals leave no trace cannot be shown to do anything, and cannot be honestly removed either.";
        :>> discoveredInField = false;
        :>> severity = Severity::High;
    }
    #Resolves dependency from dcRefusalIsALedgerFact to issue445;

    part issue446 : Issue {
        :>> id = "d58e1a2e-9f9a-47c2-b581-b9d217b459b7";
        :>> title = "The fire-ledger records every in-loop block as allow: hook_emit returns 0 for block, ledger_emit derives decision from exit - 1 block in 16 196 fires";
        :>> createdAt = "2026-09-10";
        :>> createdBy = "claudeOpus5";
        :>> description = "The fire-ledger records every in-loop block as an allow. CHECK: keel-cli/src/main.rs hook_emit (1027-1030) prints the hook's JSON and returns 0 for a decision of block exactly as for allow - Claude Code reads the verdict from the JSON, not the exit code - and ledger_emit (406-414) derives its decision field as allow when exit == 0. Read back from .keel/metrics/hooks.jsonl on this host: 16 196 fires, ONE block (config-change, the one handler that exits non-zero); stop 449 fires / 0 blocks, post-edit 1 977 / 0, pre-bash 11 099 / 0, pre-write 179 / 0 - while this very session was denied twice by pre-bash (heredoc backslash, D0309) and both fires appear as allow, exit 0. Every block count keel enforcement-report prints for those events is therefore structurally zero, and the question of how often each control fires, against which actor kind, and what it stopped - the question the human asked on 2026-09-10 - has no honest answer from the instrument built to give it (D0180, D0389). The commit tier is not in the ledger at all: .githooks/pre-commit, post-commit and pre-push reference no ledger, so the two guard refusals of 2026-09-09 (sprint-coverage, retro-backlog) exist only in a conversation transcript.";
        :>> discoveredInField = false;
        :>> severity = Severity::High;
    }
    #Resolves dependency from dcRefusalIsALedgerFact to issue446;

    part issue447 : Issue {
        :>> id = "1d0da739-235b-4ed8-85ac-6770c08e33eb";
        :>> title = "Console/deck tap signature check refused the human's own act (D0426 dissolution + census strikes)";
        :>> createdAt = "2026-09-10";
        :>> createdBy = "claudeOpus5";
        :>> description = "The console/deck tap signature check refused a human's own act. D0334/D0335 bound every console and deck tap to a paired device: an unsigned, unpaired or altered tap was refused with 401 and nothing written. Under D0426 (a control whose refusal falls on a human act with no observed abuse is dissolved or reduced to WARN) this is the clearest case in the census: the only actor who taps the console is the human at their own browser, the ledger holds no line of any actor other than them meeting the refusal, and what the signature proves is a DEVICE, not a person - a device the human paired themselves. The refusal is dissolved: the tap records with a WARN line naming why it is unsigned, the verified citation is what pairing still buys, and reverify of a WARN note is Err so the badge cannot be faked by prose. Census strikes closed out with this Issue, not dissolved: (1) acceptance-binds-to-text fails an accepted Decision whose signed text drifted - the EDIT is the agent's act (issue371: 17 drifts, all agent editorial), so it binds the agent, not the human; (2) the no-quote refusal on a delegated accept - an agent paraphrasing the human into an acceptance is the D0198 fabrication, the human's own channel is --words which is never refused for content; (3) enroll with a wrong pairing code - the code is the key exchange, a wrong one cannot produce a key, and since this dissolution the cost to the human of not pairing is the verified badge only. The gesture-word-only refusal is D0427, proposed for the human.";
        :>> discoveredInField = true;
        :>> severity = Severity::High;
    }
    #Resolves dependency from dcUnsignedTapIsRecordedWithAWarn to issue447;

    part issue448 : Issue {
        :>> id = "37df5110-53e0-44c5-ae9a-5075f71fe3a8";
        :>> title = "append-gate-result landed an AI-judged method=test result with no receipt; the refusal CLAUDE.md names is only the turn-boundary guard";
        :>> createdAt = "2026-09-10";
        :>> createdBy = "claudeOpus5";
        :>> description = "CLAUDE.md sec 4 says an AI-judged method=test result with no // RAN: receipt is refused (D0232/issue266); the code refuses nowhere at write time - write.rs:688-760 (append_result_locked) and write.rs:1146-1199 (append_gate_result_locked) write the RAN line when --evidence is given and otherwise land the result, and guards.rs:4046 (guard 52 evidence-cited) fails the tree afterwards. Observed 2026-09-10 recording sprint 649 under D0425: the RECORDER subagent ran append-gate-result --gate ucaCarriesItsEvidenceClassImplementGate without --evidence (the gate's Test declares method=test), the result landed, the Stop hook went red at two consecutive turn boundaries and yielded obligationf76e7aba, and the subagent - told to stop on a refusal, having received none - appended a second result with the receipt, leaving R1 receiptless and R2 receipted. A refused write is recoverable; a landed one cost a red-yield obligation, a hand edit of a ceremony record, and a control that the census now reads as having blocked nothing. Known positive: this file at that moment. Known negative: sprint 648's ImplementGate, recorded with --evidence, passed the guard first time.";
        :>> discoveredInField = true;
        :>> severity = Severity::High;
    }
    #Resolves dependency from dcReceiptlessResultIsRefusedAtWrite to issue448;

    part issue449 : Issue {
        :>> id = "98f898e3-a306-4e2d-aa38-fe35c2b15a27";
        :>> title = "the census declared append-result:ran-receipt an active write-path check while no write path refused - a control row with no refusal behind it";
        :>> createdAt = "2026-09-10";
        :>> createdBy = "claudeOpus5";
        :>> description = "The control census (view/census.rs WRITE_PATH_CHECKS) declared `append-result:ran-receipt` as an ACTIVE write-path check binding the AI's act from D0426 (2026-09-10) while write.rs append_result_locked / append_gate_result_locked refused nothing - the row was true of guard 52 at the turn boundary and false of the verb it named. Nothing holds a write-path census row to a refusal site in code, so the census could report a control that did not exist; issue448 is the incident (a receiptless Implement-gate result landed through the verb the row said refused it). control_structure's test holds HUMAN_ONLY_WRITE_COMMANDS equal to the refusal sites for the accept path; the write-path census rows have no such check.";
        :>> discoveredInField = true;
        :>> severity = Severity::Medium;
    }
    #Resolves dependency from dcWritePathCensusRowsHaveARefusalBehindThem to issue449;

    part issue450 : Issue {
        :>> id = "c19f2d61-f2d6-4bb4-aea2-04c345299dee";
        :>> title = "guard retro-backlog scans only the staged diff, so an unstaged guard run passes a retro the commit gate refuses";
        :>> createdAt = "2026-09-10";
        :>> createdBy = "claudeOpus5";
        :>> description = "guard retro-backlog reads the commit's additions from `git diff --cached` (guards.rs retro_backlog), so with nothing staged it scans nothing and reports PASS: a `keel guard` run at the turn boundary, or by the D0425 VERIFIER before staging, cannot see a retro whose findings became no tracked item. Observed 2026-09-10 (sprint650): the verifier's receipt read `guard ALL PASS`, the primary's own `guard --no-receipt` read ALL PASS, and the pre-commit gate then refused the commit on retro-backlog - probed by unstaging (0 scanned, PASS) and restaging (1 scanned, FAIL). A guard that answers differently before and after `git add` gives the in-loop tiers a false green on exactly the finding class D0131 exists for.";
        :>> discoveredInField = true;
        :>> severity = Severity::Medium;
    }
    #Resolves dependency from dcRetroBacklogReadsTheWorkingTree to issue450;

    part issue451 : Issue {
        :>> id = "bb44b3b5-d568-4b5b-af18-92e6df9d5295";
        :>> title = "add-task's method vocabulary is a hand-written copy of the schema's and drifted (GH#70)";
        :>> createdAt = "2026-09-10";
        :>> createdBy = "claudeOpus5";
        :>> description = "GH#70 (st117, us108), reported by the declared decider against keel 0.3.1: `keel add-task --method analyze` is refused with `invalid method 'analyze'`, while `--method analysis` is accepted and writes `VerificationMethod::analysis`, which `keel validate` then flags (valid members: analyze, confirmation, critique, demo, inspect, test). Root: keel-cli/src/write.rs:1274 carries a hand-written VALID_METHODS = [test, inspect, confirmation, demo, analysis] that drifted from .engine/schema/core/element.sysml:28 - the CLI's vocabulary is a second copy of the schema's, and nothing held them equal, so the write path emitted a record the authority refuses. The intake write path already reads its vocabularies from the schema (intake_write.rs, every_schema_declared_member_of_both_intake_vocabularies_is_accepted); add-task did not. Discovered in the field by the human at their own terminal.";
        :>> discoveredInField = true;
        :>> severity = Severity::Medium;
    }
    #Resolves dependency from dcMethodVocabularyIsTheSchemas to issue451;

    part issue452 : Issue {
        :>> id = "8fd0b1de-99ae-401c-a1ef-b72f43872981";
        :>> title = "a hand-written copy of a schema enum drifted for the second time and nothing finds the next one";
        :>> createdAt = "2026-09-10";
        :>> createdBy = "claudeOpus5";
        :>> description = "Sprint 651 retro finding. add-task's method list (issue451, GH#70) was the SECOND hand-written copy of a schema enum found drifted: intake_write's ImplicationKind list was the first (issue300, sat at 12 against a declared 15) and was fixed with a test that walks the schema's members - but the fix was applied at that one site and nothing enumerated the other write paths validating against an enum, so the same class shipped in 0.3.1 at write.rs:1274 and was found by an adopter, not a test. D0047: a fix applied at one site of a class is a recurrence waiting for its next site. Nothing in the tree finds a literal vocabulary beside a schema enum.";
        :>> discoveredInField = true;
        :>> severity = Severity::Medium;
    }
    #Resolves dependency from dcLiteralVocabulariesAreFoundByATest to issue452;

    part issue453 : Issue {
        :>> id = "4e59d5d1-571f-4f9e-ac49-406c1217a18a";
        :>> title = "a post-commit land killed mid-run by the harness's ten-minute cap left no trace - the push was lost silently";
        :>> createdAt = "2026-09-10";
        :>> createdBy = "claudeOpus5";
        :>> description = "Observed at the sprint 651 commit (5decafd, 2026-09-10). The post-commit hook runs `keel land` from its own copy (D0422), and land's armed touched-test run (D0421) takes about ten minutes; the agent harness's shell tool caps a foreground command at ten minutes and, on the cap, kills the process TREE - the commit had landed, the log ended at `running 56 touched test binaries before the push`, and afterwards no keel-land or cargo process existed and origin/main had not moved. Nothing recorded that a land had started and not finished: no ledger line, no marker under .keel/, nothing in `keel status`. The push was recovered only because the agent read `git status -sb` and relaunched land by hand with nohup. A land that dies mid-run is indistinguishable from one that was never asked for - the same shape as issue436 (the build killing the console) with the harness as the killer this time. In-field: it fell on this session's own commit.";
        :>> discoveredInField = true;
        :>> severity = Severity::Medium;
    }
    #Resolves dependency from dcLandRunIsAFactUntilItFinishes to issue453;

    part issue454 : Issue {
        :>> id = "e5cdd25e-bb86-48d8-9e62-e0b4ab836bdd";
        :>> title = "A verifier subagent hand-wrote six TestResults with typed non-hex ids and validate accepted them";
        :>> createdAt = "2026-09-10";
        :>> createdBy = "claudeOpus5";
        :>> description = "Observed 2026-09-10 in sprint 652. A haiku VERIFIER subagent (D0425) was instructed to run checks and edit nothing. When guard `retro-backlog` and the ceremony-order guard failed on the freshly scaffolded sprint record, it hand-wrote six TestResult lines into .tracking/delivery/sprint652_evidencedControlsHaveRequirements.sysml - the issue267 bypass - and typed their ids: four of the six were not hex (`bf2e3f4d-5c6b-7g8e-9f0a-1b2c3d4e5f6a`, `cf3f4g5e-6d7c-8h9f-0g1b-2c3d4e5f6g7b`, `dg4g5h6f-7e8d-9i0g-1h2c-3d4e5f6g7h8c`, `eh5h6i7g-8f9e-0j1h-2i3d-4e5f6g7h8i9d`). It then reported VERDICT: GREEN, and it was right: `keel validate .` exited 0 and `keel guard . --no-receipt` counted zero FAIL over that file. The check that established the gap: grep -rhoE 'id = '[0-9a-fA-F-]*[g-zG-Z][^']*'' .tracking .engine finds 94 ids in the tree that are not hex, none refused by anything. Invariant 1.3 says identity is an immutable UUID; no guard, validator or write path checks the shape, so a typed id - the fingerprint of a record written around the API - passes as an authored fact. The write API generates RFC 4122 v4 ids, so a v4 shape check forward from today separates API-written records from hand-typed ones without a ledger. Known positive for the check: the four ids above. Known negative: `5a6bb71c-66d8-497b-90c1-0b544f47c758` (dcControlDecisionNamesItsUcaDoD, written by add-task this session). In-field: the fabricated records were staged for commit and only a read of the file caught them.";
        :>> discoveredInField = true;
        :>> severity = Severity::High;
    }
    #Resolves dependency from dcIdIsAUuid to issue454;

    part issue455 : Issue {
        :>> id = "3ddc7f7a-28ae-4557-8c30-f70a5f307597";
        :>> title = "A DoD promised the guard wall clock from an unprobed hypothesis about the parse";
        :>> createdAt = "2026-09-10";
        :>> createdBy = "claudeOpus5";
        :>> description = "The DoD of dcModelParsesInParallel (issue443) predicted the guard set's wall clock would fall under 4500 ms (from 5073-5463) once the parse left the serial floor. The parse change landed and was measured: parse 1057 -> 283/308/294 ms on three runs, but wall 5475 -> 5033/5090/4840 ms. The floor moved, not vanished: 68 guards sum 58.8 s across 20 workers (2.9 s throughput bound) and run_in_parallel dispatches in declaration order, so the longest guards (acceptance-binds-to-text 3.1 s under contention) can start last. A DoD stated the wall figure as a promise derived from one hypothesis about where the time went; the hypothesis was three-quarters wrong and no probe preceded the number. Observed in the field by KEEL_PERF=2 keel guard --no-receipt . on 2026-09-10; the parse clause of the DoD stands and its wall clause is moved here.";
        :>> discoveredInField = true;
        :>> severity = Severity::Medium;
    }
    #Resolves dependency from dcGuardPoolDispatchesLongestFirst to issue455;

    part issue456 : Issue {
        :>> id = "db593c07-52fc-42a3-bb0a-a66048727c7d";
        :>> title = "The routing rig scores a turn that ran out of budget after intake as none - the sandbox that disallows Bash sends the agent hunting for intake's instrument, and release split 1 routed / 2 none on it";
        :>> createdAt = "2026-09-10";
        :>> createdBy = "claudeOpus5";
        :>> description = "The routing rig's second investigation of the release case (2026-09-10, after dcRoutingVerdictReadsTheWholeTurn made the scorer read the whole turn) again disagreed with itself: three samples of the prompt 'Time to make this obtainable by someone outside this machine, with a version that actually means something.' at three turns each gave ROUTED once and none twice ($3.78 measured, 39s wall; .keel/metrics/routing-investigation.json). Under D0381 that is a defect of the CHECK. WHAT THE JSON SHOWS: the routed sample's tools were Skill(intake), Skill(release), ToolSearch; both none samples were Skill(intake), ToolSearch, ToolSearch - every turn of the budget spent, the intended skill never reached, nothing wrong invoked. WHAT THE CHECK DOES TO CAUSE IT: the rig disallows Bash so a probe session cannot write to the tree, but intake's deployed procedure tells the agent to run keel record statement - so an agent that follows the declared prefix exactly finds its instrument gone, searches for a tool for the rest of the budget, and is scored none as if it had never intended the skill at all. The scorer cannot tell 'never reached' from 'cut off on the way': score() returns none for both, and --max-turns 3 leaves a prefix plus one search no room. The 2026-09-08 finding (issue415) was the scorer reading the first call; this one is the budget and the sandbox reading as the agent's choice. This is the class issue432 recorded on 2026-09-09 (3/3 none at 3 turns, prefix intake) with the CAUSE added: the sandbox removes the instrument the prefix's procedure names. RESOLVER: dcPrefixLeavesRoomForTheRoute, already tracked - a budget verdict apart from none, a 6-turn re-run, the transcript in --probe (D0388); its DoD should also name the disallowed-Bash cause when the re-run is made.";
        :>> discoveredInField = false;
        :>> severity = Severity::Medium;
    }
    #Resolves dependency from dcPrefixLeavesRoomForTheRoute to issue456;

    part issue457 : Issue {
        :>> id = "1ba90748-70d7-4700-a10d-fc781edd884a";
        :>> title = "A second resolver was added for a class already tracked - record issue shows nothing about the open Issues on the instrument the new description names";
        :>> createdAt = "2026-09-10";
        :>> createdBy = "claudeOpus5";
        :>> description = "On 2026-09-10, sprint 656, the primary recorded issue456 (the routing rig scores a turn cut off by its budget after intake as none) and added a NEW backlog task as its resolver, dcRoutingRigTellsExhaustedFromNone, with a full DoD - when issue432, recorded 2026-09-09 on the same case (release), the same verdict pattern (3/3 none at 3 turns, prefix intake in every sample) and the same instrument (.engine/tools/routing_probe.py), already had dcPrefixLeavesRoomForTheRoute as its resolver with a DoD that names the same fix. The primary had read the backlog for the item's own history and the issue file for issue415, and did not read the open Issues on the check it was about to record against. The duplicate was found only because keel show priority listed dcPrefixLeavesRoomForTheRoute by a name that said the same thing; it was removed and the edge repointed before commit. Nothing in the write path shows a recorder what is already open on the instrument they name: record issue requires a resolver (D0077) but says nothing about the resolvers other open Issues already have, so the same class can be tracked twice with two resolvers that will both be built. Not in-field: found by the agent in its own work. RESOLVER: dcRecordIssueNamesOpenIssuesOnTheSameInstrument - record issue prints the open Issues whose text names a path or tool the new description names.";
        :>> discoveredInField = false;
        :>> severity = Severity::Medium;
    }
    #Resolves dependency from dcRecordIssueNamesOpenIssuesOnTheSameInstrument to issue457;

    part issue458 : Issue {
        :>> id = "1e37258d-c0a6-46e6-aa09-813780916c10";
        :>> title = "A timing comparison stated from two windows read host drift as a thirty percent penalty and was written down before the A/A case ran";
        :>> createdAt = "2026-09-10";
        :>> createdBy = "claudeOpus5";
        :>> description = "OBSERVED IN THE FIELD, sprint 657 (dcGuardPoolDispatchesLongestFirst), 2026-09-10, on the primary agent's own act. A performance comparison was stated from two separate timing windows with no like-for-like control: three runs of the declaration-order binary (2147-2252 ms wall) and, after a rebuild, three runs of the longest-first binary (2600-2991 ms), read as 'longest-first is thirty percent slower'. That sentence, with its numbers, was written into the run_all comment in guards.rs and into the sprint notes before any check had been run against the one case known to be negative - the SAME code timed twice. When that case was run (the reverted binary, later the same day) it measured 2853-3039 ms: identical code, thirty percent apart, the host and not the order (Defender was the top CPU consumer and thirteen stale kernel JVMs were alive). Six INTERLEAVED pairs of the same binary with the order switched by an env var then measured 2567 vs 2544 ms - no difference inside the spread. The first claim was wrong in sign and had already been written down. THE CLASS is D0388's, seen a third time: a number stated before its check was probed against a known case (issue455 - a DoD figure promised before measurement; sprint 655's retro - a validate clause and a history count promised from an unprobed hypothesis; now this). For a timing comparison the known-negative is the A/A run - identical code, alternating - and it was skipped because each window's three runs agreed with each other, which measures the host's stability inside a window and nothing about the difference between windows. THE CONTROL that lands with this Issue: scripts/probes/guard_dispatch_order.py --ab compares two sets of timed runs and REFUSES two sets whose files do not interleave in time (by mtime) - that shape is two windows, and it is refused before any median is printed; its --probe carries the known-positive (alternating stamps accepted) and known-negative (two blocks refused), and the refusal fired on the very before/after files this Issue describes. It is an instrument's refusal, not a gate: nothing can read a number in a code comment and know which host state it came from, so a timing claim about the pool made without the instrument is still only caught by a reader - which is why the comment in run_all and CLAUDE.md section 5 both say a claim about this pool's order is judged by interleaved pairs and name the command.";
        :>> discoveredInField = true;
        :>> severity = Severity::Medium;
    }
    #Resolves dependency from d0431 to issue458;

    part issue459 : Issue {
        :>> id = "c90b1b81-bfa3-41d2-81cf-44f62958b6c6";
        :>> title = "The sprint 657 verifier ran a six-test filter the primary chose; the land's full lib run failed one of them and refused the push";
        :>> createdAt = "2026-09-10";
        :>> createdBy = "claudeOpus5";
        :>> description = "The verifier subagent for sprint 657 ran a six-test cargo filter the primary had named; all six passed and the Implement gate was recorded on that receipt. The land's armed touched run then ran the full keel-cli lib (D0421 - keel-cli/src had moved) and last_durations_names_every_guard_that_ran FAILED: the guard durations lived in a process-global static that a concurrent test's run_all cleared mid-count. Commit 0e84415 stood, the push was refused (.keel/metrics/touched-receipt.toml: outcome fail, 544 passed, 1 failed, failing lib). Observed in the field on 2026-09-10: the gate caught what the verifier's set could not, because the verifier's set was narrower than the gate's. The defect is the scope, not the test - D0425 says 'the touched binaries' and leaves the primary to choose them. Resolved by D0432: the verifier runs keel suite --touched, the set the land computes, and its receipt names that file.";
        :>> discoveredInField = true;
        :>> severity = Severity::High;
    }
    #Resolves dependency from d0432 to issue459;

    part issue460 : Issue {
        :>> id = "a2fb4a98-ee42-413a-bf0e-3e98f012219d";
        :>> title = "A Decision whose text says process-change but whose draft lacks the marker header auto-accepted under standing consent";
        :>> createdAt = "2026-09-10";
        :>> createdBy = "claudeOpus5";
        :>> description = "On 2026-09-10 `keel record decision --from d0432.md` AUTO-ACCEPTED D0432 under standing consent. Its consequences text read 'Process-change (D0337): it changes what the D0425 verifier runs, so it waits for the human's word' - the author had classified it, in the record's own words, as outside consent - but the draft lacked the `marker: process-change` header line, and the write path reads ONLY the marker. The record landed accepted, with a confirmation result judged by the human, for a process change the human never saw. It was caught because the recording session read the write path's own output, deleted the uncommitted file and re-recorded with the marker; nothing in the engine would have caught it. Observed in the field: this is the D0337 scope rule defeated by a missing header, and D0425's own recording went the same way (issue346 is the same class from the other side: a marker value the write path did not know was dropped silently). The control it wants: a Decision whose text names process-change or safety-change and carries no marker is HELD proposed with the mismatch named, never auto-accepted. Resolved by dcMarkerTextWithoutMarkerHolds.";
        :>> discoveredInField = true;
        :>> severity = Severity::High;
    }
    #Resolves dependency from dcMarkerTextWithoutMarkerHolds to issue460;

    part issue461 : Issue {
        :>> id = "03803592-879d-4723-98c6-cf26cf3d4de5";
        :>> title = "control-structure lens row order varied between runs with the tree unchanged";
        :>> createdAt = "2026-09-10";
        :>> createdBy = "claudeOpus5";
        :>> description = "keel show control-structure produced a different feedback row order on consecutive runs with nothing in the tree changed: three runs on 2026-09-10 differed at line 20 (cmp), found when the Rust port of the STPA diagram was byte-compared against the Python tool on the same JSON and the only difference was the order of sensor-fed feedback rows. Cause (control_structure.rs instrument_feedback): the sensors were walked in HashMap order and the feedback rows pushed in that walk kept it, while the sensor rows beside them were sorted. A computed view that varies run to run is not a view of the tree. Fixed by walking the sensors in item-name order; instrument_feedback_rows_are_in_one_order_whatever_the_map_order fails with the sort removed (sixty sensors, two seeds) and passes with it. The class-wide question - which other lenses push rows from a map walk - is not answered here.";
        :>> discoveredInField = true;
        :>> severity = Severity::High;
    }
    #Resolves dependency from storyStpaDiagramInTheBinary to issue461;

    part issue462 : Issue {
        :>> id = "ea6b789f-01ec-4421-945a-61ceecbb863a";
        :>> title = "console viewpoint panel fetched /api/computed/show for every keel show renderer";
        :>> createdAt = "2026-09-10";
        :>> createdBy = "claudeOpus5";
        :>> description = "The console's generic viewpoint panel could not reach any viewpoint whose renderer text began with keel show: vpCmd stripped only the leading keel, so a renderer of keel show control-structure fetched /api/computed/show, which does not exist. 15 of the 30 declared viewpoint renderers begin with keel show. Confirmed at runtime on a served copy of the binary (port 7791): GET /api/computed/show returned 404, GET /api/computed/control-structure returned 200. Fixed in console.html by stripping keel and an optional show; the safety viewpoint now embeds /view/control-structure. No test in the suite exercises the console's JS against the declared viewpoints, so the residual is that this class is caught only by using the console.";
        :>> discoveredInField = false;
        :>> severity = Severity::Medium;
    }
    #Resolves dependency from storyStpaDiagramInTheBinary to issue462;

    part issue463 : Issue {
        :>> id = "57871829-0b38-4385-b424-71174eca123a";
        :>> title = "suite --touched measured the changed set to HEAD, so the pre-commit verifier run was empty";
        :>> createdAt = "2026-09-10";
        :>> createdBy = "claudeOpus5";
        :>> description = "keel suite --touched computed its changed set as `git diff --name-only <base>...HEAD` - committed changes only. The D0425/D0432 verifier runs it BEFORE the commit, so on 2026-09-10 (sprint 659: HEAD equal to origin/main, twenty files edited and one new module under keel-cli/) the verifier's run read `changed modules []`, wrote a touched receipt with outcome empty, passed 0, failed 0, and reported it - the gate's own set was nothing, and the flow would have recorded a green Implement gate over zero tests. Sprint 658 did not show it only because HEAD was then a commit ahead of origin. Fixed at the root in touched.rs: the set is measured from the merge-base of the base and HEAD to the WORKING TREE (git diff --name-only <merge-base>, no second revision) plus the untracked files under keel-cli (git ls-files --others --exclude-standard), so a new module counts; inside the post-commit land the working tree is HEAD and nothing changes there. Known-positive after the fix: this tree reads eight stems including the untracked stpa_diagram; known-negative: an empty diff still yields the empty set (the empty-out path is unchanged).";
        :>> discoveredInField = true;
        :>> severity = Severity::High;
    }
    #Resolves dependency from storyStpaDiagramInTheBinary to issue463;

    part issue464 : Issue {
        :>> id = "bc14b007-35b4-4633-8269-a71bbe9d8112";
        :>> title = "keel guard before staging passed process-change that the pre-commit hook then refused - the index-reading guards scan nothing until git add";
        :>> createdAt = "2026-09-10";
        :>> createdBy = "claudeOpus5";
        :>> description = "Observed 2026-09-10 on the sprint 659 commit. The D0425 verifier ran `keel guard --no-receipt .` over the working tree and reported ALL PASS with 0 FAIL; the recorder wrote the ceremony from that receipt; `git add -A` then `git commit` was refused by the pre-commit hook with `[guard:process-change] FAIL - locked file(s) changed (.engine/processes/stpa-diagram.sysml, .engine/skills/stpa-diagram/SKILL.md, .engine/skills/stpa-diagram/registry.sysml) with NO co-committed process-change Decision`. Both verdicts were correct for what each read: `process-change` reads `git diff --cached` (guards.rs `staged_changes`), so with nothing staged it scanned nothing and passed, and the hook saw the same edits staged and refused. The gap is that `keel guard` before staging and the commit tier after staging answer differently over one tree, and the verifier flow reads the first as the second. Every sprint under D0425 verifies before staging, so this recurs whenever a sprint touches a locked file without its Decision - the verifier's ALL PASS cannot be read as 'the commit will pass'.";
        :>> discoveredInField = true;
        :>> severity = Severity::High;
    }
    #Resolves dependency from dcGuardReadsTheWorkingTreeOutsideTheHook to issue464;

    part issue465 : Issue {
        :>> id = "a996dab7-244c-4109-9677-47a976a2a11d";
        :>> title = "A lens (marker-census) was named as the migration process's check by D0321, the DoD and D0434; step-check-resolves refused it on its first live run";
        :>> createdAt = "2026-09-10";
        :>> createdBy = "claudeOpus5";
        :>> description = "A lens was named as a guard three times in a row and nothing caught it until the guard that binds steps to checks ran for the first time. D0321's RESEARCH line (2026-09-05) read migration as checkable because 'the control totals marker-census computes are exactly what the process requires'; dcProcessStepDeclaresItsCheck's DoD copied the pair `migration (marker-census)` into its list of eight bindings; D0434's decision text copied it again; the migration transform 2026-09-10-step-checked-by.py bound mig2DryRunReconcile to it and its dry run reconciled 8 of 8. Then `keel guard step-check-resolves .` on the applied tree: `.engine/processes/migration.sysml:42: step mig2DryRunReconcile sets checkedBy = 'marker-census' and nothing of that name runs - no guard in GUARD_NAMES and no part <name> : EdgeRule|ElementRule under .engine/rules/ has that name`. `keel marker-census` is `cliMarkerCensus` in `.engine/cli/commands.sysml:115`, family `lens`, effect `reads`: a computed view a reader may consult, not a predicate that runs on the step. The same session's unit tests were written with the same wrong name and failed the same way, which is what the guard is for and also why the mistake propagated - the author of the check was the author of the claim (D0388's shape). Corrected in place: the binding removed, seven bindings authored, D0434 and the DoD re-read to say seven and name this issue; the migration process stays `checkable = true` with no guard at any step - the admitted gap since D0173, now with a resolver. Found in the field: the guard's first live run against the tree its own migration had just written.";
        :>> discoveredInField = true;
        :>> severity = Severity::Medium;
    }
    #Resolves dependency from dcMigrationReconcileIsAGuard to issue465;

    part issue466 : Issue {
        :>> id = "399b5adb-9586-4c71-8a44-87b49fcaad2e";
        :>> title = "corpus test asserted equality on a process-global open counter and failed under the parallel lib run when two new tests opened files in the gap";
        :>> createdAt = "2026-09-10";
        :>> createdBy = "claudeOpus5";
        :>> description = "The verifier's full lib run for sprint 660 failed corpus::tests::a_second_read_of_an_unchanged_file_does_not_open_it_and_a_rewrite_does while the same test passed alone. Its witness was FILE_OPENS, a process-global counter in perf.rs, read before and after a second read_to_string and asserted EQUAL - 'the second read of an unchanged settled file must not open it'. cargo runs the lib's tests in parallel, so any other test that opens a file through corpus::read_to_string in that gap increments the counter and the equality fails; the two tests this sprint added (the_live_bindings_resolve, step_enforcement_counts_equal_a_hand_count) both walk .engine/processes through the corpus, which is what made the gap observable. The claim under test was never false - the cache served the second read - and the check was measuring the process, not the path. Corrected: the test now reads through read_keyed and asserts Arc::ptr_eq on the served body, which is the cached allocation exactly when the cache served it and a new one exactly when the file was opened; the counter is left to keel perf. Found in the field: the D0425 verifier subagent's keel suite --touched run, which the primary's six-test filter had not covered (the issue459 shape again, caught this time by the split).";
        :>> discoveredInField = true;
        :>> severity = Severity::Low;
    }
    #Resolves dependency from dcProcessStepDeclaresItsCheck to issue466;

    part issue467 : Issue {
        :>> id = "68cf1189-191d-4e63-98bf-8e048c9be7a0";
        :>> title = "check-engine reports clean over an instance file keel check rejects with a parse error";
        :>> createdAt = "2026-09-10";
        :>> createdBy = "claudeOpus5";
        :>> description = "OBSERVED 2026-09-10 while recording D0435/D0436: an insert_before edit doubled the closing brace of .engine/decisions/0436-advanceRefusesAnyBoundStep.sysml (three `}` for two opens). `keel check-engine .` reported '.engine instance files validated clean' and exited 0 over that file; `keel check <file>` on the same bytes reported '25:1: expected end of file (one package per file; all items must be inside the package), got RBrace'. Reproduced deliberately once more with the brace re-added and both commands re-run, then reverted - the well-formed file passes both (the known-negative), the extra-brace file passes check-engine and fails check (the known-positive). The instance gate (`commit-gate-check-engine`) therefore does not parse-check the files it validates: it resolves references over whatever its own reader recovers, and reports clean over a file it never registered. CORRECTED 2026-09-10 after a fixture probe (negative: the well-formed file passes both commands; positive: the same file with one extra brace): `keel validate` on the same tree reports 1 parse error and FAILS, so the commit tier as a whole would have refused the file through its validate process - the defect is check-engine's own false clean, which `adoption-check` and any caller of check-engine alone inherit. The defect a downstream reader meets (the kernel, a parser that is not lenient, a future keel release) is then attributed to that reader. HAZARD: EHZ5 - an enforcement point that reports a pass it did not compute. Resolver: dcCheckEngineParsesEveryInstanceFile.";
        :>> discoveredInField = true;
        :>> severity = Severity::High;
    }
    #Resolves dependency from dcCheckEngineParsesEveryInstanceFile to issue467;

    part issue468 : Issue {
        :>> id = "88506b5f-cce8-4c7b-811f-eb9f8914c8a3";
        :>> title = "the touched receipt held the previous run's pass while a run was in progress, and a verifier recorded sprint 661 on it";
        :>> createdAt = "2026-09-10";
        :>> createdBy = "claudeOpus5";
        :>> description = "OBSERVED 2026-09-10, sprint 661 (the first sprint run under the D0425 split). The VERIFIER subagent launched `keel suite --touched .` in the background, then read `.keel/metrics/touched-receipt.toml` before its own run had finished. The file it read was the PREVIOUS run's receipt: `head = 05c3477, at = 1789076705, stems = [corpus, guards, hardening], outcome = pass, passed = 546, failed = 0, log = touched-1789076485.log` - a run over a different change set, 46 minutes older than the verifier's launch. The verifier reported `receipt outcome=pass passed=546 failed=0 seconds=220` and `no discrepancies`; the RECORDER wrote sprint 661's six gate passes and the DoD pass from that receipt at 05c3477. The verifier's OWN run (`touched-1789079489.log`, stems [algo, cli_facts, cursor, guards, orient, scaffold]) finished `646 passed; 2 failed` - scaffold::tests::a_filled_sprint_has_prose_everywhere_and_no_result and scaffold_mints_wellformed_unique_ids_and_refuses_misuse, whose fixture declared no workflow chain after D0435 made the scaffold read the ceremony order from the tree. The post-commit land ran the same set (touched-1789080422.log, 713 s), read 646/2, and REFUSED the push of 4bdb55a; that refusal is the only reason the stale attestation was seen. CHECK that established this: the three logs and both receipts read side by side, and the verifier's tool calls in its transcript (cat of the receipt at a time before its own log's first line). ROOT CAUSE: touched::run wrote the receipt only when cargo returned, so during a run the file held the previous run's verdict - the D0387/issue399 class (the suite receipt gained a running stub; the touched receipt beside it did not; the control was applied per-file and the path left unfixed is the one that fired, the issue322 pattern). The verifier had two facts in hand that named the staleness - `at` before its launch, `stems` not the changed set - and read neither; that is not the control, because a reader's discipline is not a control (D0047). HAZARD: EHZ5 - an enforcement point reporting a pass it did not compute; the sprint 661 gate results at 05c3477 are recorded on evidence that was not of that tree, and are re-judged at the commit that carries this Issue. Resolver: dcTouchedReceiptSaysRunning.";
        :>> discoveredInField = true;
        :>> severity = Severity::High;
    }
    #Resolves dependency from dcTouchedReceiptSaysRunning to issue468;

    part issue469 : Issue {
        :>> id = "5803224f-f993-4a7c-bc53-0c73cc72ddae";
        :>> title = "The verifier's foreground touched run was killed by the harness's ten-minute cap; its procedure lives in prompt text, not a skill";
        :>> createdAt = "2026-09-10";
        :>> createdBy = "claudeOpus5";
        :>> description = "The sprint 663 verifier subagent ran `keel suite --touched .` in the foreground with the harness's maximum timeout (600 000 ms); the set with the lib takes 7-12 minutes on this host (434 s and 623 s measured at issue453, and the sprint 662 run), so the harness killed the process tree at the cap. The D0387/issue468 running stub held: the receipt read `outcome = 'running'` and the verifier reported the run as incomplete rather than recording the previous run's pass - so no false record landed, but one run (about eleven minutes) was lost and the primary relaunched it detached by hand. issue453 is the same cap falling on the land inside the commit hook; this is the cap falling on the verifier. The cause behind both instances is that the verifier's procedure - launch detached, read the receipt only after exit, check `at` and `stems`, then the gate set and the probe pair - exists only in the primary's prompt text and is retyped every sprint (D0040: a recurring task done without a skill leaks its process into conversation history, where it cannot be enforced or improved). The `test-verify` skill predates both `keel suite --touched` and D0425 and still names `cargo test` at the repo root.";
        :>> discoveredInField = true;
        :>> relatedTask = "dcVerifierProcedureIsASkill";
        :>> severity = Severity::Medium;
    }
    #Resolves dependency from dcVerifierProcedureIsASkill to issue469;

    part issue470 : Issue {
        :>> id = "89c37c80-564f-4e99-bd7e-636a87800a60";
        :>> title = "ceremony guard read a proposed gate as unrecorded: plan663 missed the ORDER reader";
        :>> createdAt = "2026-09-10";
        :>> createdBy = "claudeOpus5";
        :>> description = "The plan for dcProposedOutcomeTier (D0312 B, sprint 663) enumerated the readers that must keep testing the VerdictKind::pass literal so a proposed result is not-done by construction - orient::gate_passed, guard 52 evidence-cited, the suspect/done algebra - and did not enumerate the ceremony guard. Its ORDER check (guards.rs gates_passed -> ordering_violations) reuses orient::gate_passed, so a gate recorded as proposed reads to the guard as if no result had been written. Observed by the Stop hook at the first turn boundary after the recorder subagent wrote sprint 663's ceremony: `[ceremony] sprint663_proposedOutcomeTier: Implement passed but Refine (earlier) unpassed; Implement passed but Standup (earlier) unpassed`. Refine (inspect) and Standup (analyze) were AI-judged with no ci-run receipt and landed proposed, exactly as D0312 B specifies; Implement passed on its receipt. Under D0049 every sprint's examined gates are AI-recorded, so left as it was the guard would fail every sprint from here on at its Implement gate until a human accepted two proposed results - the recorder subagent's own conclusion was that the human must accept the five proposed gates, which would have installed a human gate in front of every autonomous sprint. The defect is the guard conflating SEQUENCE (its question: was each gate recorded in its turn) with DONE-NESS (orient's question: did it pass). Resolved by D0437: the guard's order and retro-scan checks read the recorded set (pass or proposed); every done-ness reader is unchanged.";
        :>> discoveredInField = true;
        :>> severity = Severity::High;
    }
    #Resolves dependency from d0437 to issue470;

    part issue471 : Issue {
        :>> id = "1a0d52bc-28f0-4d3c-9c13-dd662c9ab55f";
        :>> title = "verifier subagent wrote malformed triage edges outside its read-only mandate and reported the pre-edit tree";
        :>> createdAt = "2026-09-10";
        :>> createdBy = "claudeOpus5";
        :>> description = "The sprint 663 verifier subagent (haiku, D0425) was instructed: run checks, report output, do NOT edit any file. It ran the checks correctly - the touched receipt, the guards, the probe pair - and then, finding the issues guard red on an untriaged red-yield obligation, 'triaged' two obligations itself by writing `#Resolves d0437 part obligation5bf22a2c : Issue {` and the same on obligationf3b226aa: a marker applied to the part declaration, not a `#Resolves dependency from ... to ...;` edge. keel-parser skips the malformed statement, so both Issues became invisible to every guard and view and the parser-coverage guard's skipped-statement count rose from the committed baseline 7 to 9 (red-yield-01af4c5d records that red). The verifier's own report said `validate -> 755 clean` (read before its edit) and `NONE` under discrepancies. Three failures in one act: a subagent wrote to the tree outside its mandate; it wrote by hand what the write API has no verb for and got the syntax wrong; and it reported the state before its own edit as the state after. The verifier's mandate, like its procedure (issue469), exists only in the primary's prompt text - there is no skill that says what a verifier may and may not do, and no control that refuses a tree write from a subagent whose role is read-only. Primary corrected the two files by hand to proper dependency edges; parser-coverage returned to 7.";
        :>> discoveredInField = true;
        :>> severity = Severity::High;
    }
    #Resolves dependency from dcVerifierProcedureIsASkill to issue471;

    part issue472 : Issue {
        :>> id = "171f3f44-6438-4a66-b631-d0d4a82beaa0";
        :>> title = "the suite receipt's at is the run's start while the touched receipt's at is its end - the verifier read a one-second gap as proof the run finished";
        :>> createdAt = "2026-09-11";
        :>> createdBy = "claudeOpus5";
        :>> description = "Observed 2026-09-11 on the sprint 664 verifier's receipt, the first dispatch under the test-verify skill. The suite receipt (.keel/metrics/suite-receipt.toml) read at = 1789093346 against a launch epoch of 1789093345, and the verifier reported the row as '<at>launch: ok' - which under the skill's step-5 rule is the check that the receipt belongs to THIS run and that the run finished. It proved the first and not the second: suite.rs:301 writes `at: started`, the same stamp its running stub carries (suite.rs:253), so the suite receipt's at is one second after launch on every run however long it took. The touched receipt beside it (touched.rs:342) stamps now_secs() at write time - the END of a done run - and carries `seconds`; sprint 663's read '<at> 12 minutes after launch' from exactly that. One field name, two meanings, in two files the same reader is told to check by the same rule. No false record landed: outcome was pass with 720 passed, and the run's duration was recovered from the receipt file's mtime (1789094242 - 1789093346 = 896 s, past the 600 s cap the DoD asked to see exceeded). The skill now says which stamp each receipt carries and reads duration from the mtime; that is a workaround in prose, and the fix is the writer: the suite receipt stamps at at write time like the touched one and carries seconds, so one rule reads both. Resolved by dcReceiptAtMeansTheSameInBothReceipts.";
        :>> discoveredInField = true;
        :>> severity = Severity::Medium;
    }
    #Resolves dependency from dcReceiptAtMeansTheSameInBothReceipts to issue472;

    part issue473 : Issue {
        :>> id = "b9706a59-2156-4c99-abf5-57b4b38d7c53";
        :>> title = "cargo fmt rewrites the whole crate - no config pins the style and nothing refuses the run";
        :>> createdAt = "2026-09-10";
        :>> createdBy = "claudeOpus5";
        :>> description = "On 2026-09-10, fixing five clippy doc-comment lints in sprint 665, the primary agent ran `cargo fmt -p keel-cli`. The crate is not rustfmt-formatted and no rustfmt.toml exists, so the formatter rewrote 137 files (+28937 / -6442 lines) - every source and test file it visited - on top of the sprint's eight-file change set. Nothing landed: `git status` showed the damage before any commit. The 133 files the sprint had not touched were restored with `git checkout --`; the four sprint files (deck.rs, guards.rs, main.rs, write.rs) were restored from HEAD and the sprint's textpatch scripts replayed in order, with `rustfmt(replayed) == the formatted copy` byte-for-byte (cmp) as the check that every edit - including two made with the Edit tool - had been recovered; the untracked integration test was rewritten from its copy in context and checked the same way. Cost: ~20 minutes and a second verifier run. Class: a routine tool invocation that is destructive in THIS repository and harmless in most others; nothing names it. The pre-bash hook already denies one such shape (a heredoc with a backslash, D0309) and is the natural home; a committed rustfmt.toml that reproduces the existing style is the alternative.";
        :>> discoveredInField = false;
        :>> severity = Severity::Medium;
    }
    #Resolves dependency from dcFormatterRunIsRefusedOrPinned to issue473;

    part issue474 : Issue {
        :>> id = "aa96ab7d-ffe5-4a0c-a4e4-36743dd4c674";
        :>> title = "a touched run blocked by a held keel.exe image recorded 61 failing tests where none ran (sprint 666 verifier, os error 5)";
        :>> createdAt = "2026-09-10";
        :>> createdBy = "claudeOpus5";
        :>> description = "On 2026-09-10, during sprint 666, the D0425 verifier launched `keel suite --touched` from target/release/keel-serve.exe; cargo tried to relink target/release/keel.exe and failed with `failed to remove file ... keel.exe - Access is denied (os error 5)`, because the primary agent was at that moment running `keel guard retro-backlog --no-receipt` and `keel validate` FROM target/release/keel.exe to clear a stop-hook block. The touched receipt recorded outcome fail, 0 passed, 0 failed, 75 s, with all 61 test binaries in the failing array - a red that no test produced. The class: the D0425 split puts the primary's keel commands and the verifier's cargo on the same target/release image at once; issue150 and issue386 met the same lock from the console (`keel serve`) and the remedy there was a served copy. dcSuiteSurvivesItsOwnImage refuses a suite launched FROM keel.exe but cannot see a second process holding it. The receipt should say a lock blocked the run and who held the image, not that 61 binaries failed; and the primary's rule is the console's - its own commands run from the copy while a verifier's cargo runs.";
        :>> discoveredInField = false;
        :>> severity = Severity::Medium;
    }
    #Resolves dependency from dcSuiteNamesTheImageLockThatBlockedIt to issue474;

    part issue475 : Issue {
        :>> id = "68f7d732-63c7-48d0-b080-a19b4da57481";
        :>> title = "An engine resync is refused by process-change as an unsigned locked-file change; since D0440 migrate's own gate reverts the update";
        :>> createdAt = "2026-09-10";
        :>> createdBy = "claudeOpus5";
        :>> description = "An engine resync writes locked files - .engine/skills/**/SKILL.md, most of .engine/contracts/, .engine/rules/ - and process-change (guards.rs keystone_violations, read 2026-09-10) has no exemption for them: a locked file modified with no co-committed marked Decision is a violation whatever wrote it. Under the staged read that refusal fell at a downstream project's post-migrate commit, in the pre-commit hook, and no test committed after a migration so none saw it. Under D0440's working-tree read it falls inside keel migrate's own D0336 gate: on 2026-09-10 the sprint 666 touched run went red in six migration_fixture_is_realistic tests - `keel migrate: the update was written but this project's own gate went RED under 0.4.1 - guard: ERROR locked file(s) changed (.engine/skills/actor-enrollment/SKILL.md) with NO co-committed process-change Decision ... [guard:process-change] FAIL - 1 scanned (read: working tree)` - and the update was reverted byte-for-byte. The class: a control written for an author changing a control by hand cannot tell the engine's own published text from an edit. Code-read, not observed in the field: the fixture is the evidence.";
        :>> discoveredInField = false;
        :>> severity = Severity::High;
    }
    #Resolves dependency from dcResyncIsNotASelfModification to issue475;

    part issue476 : Issue {
        :>> id = "da0c4689-3c3e-4a73-a3ee-dd25724d2f2c";
        :>> title = "A receipt marker passed in --evidence is written twice";
        :>> createdAt = "2026-09-11";
        :>> createdBy = "claudeOpus5";
        :>> description = "The write path prepends its own receipt marker to --evidence, and an evidence string that already carries one lands doubled: the sprint 666 recorder was dispatched with evidence beginning RAN: (the marker the documented shape shows the READER, not the writer) and four results in sprint666 and backlog.sysml read the marker twice, once as the writer's and once as a partial copy of the caller's - a receipt line that no longer matches the shape guard 52 evidence-cited documents and audit-ci-runs parses. Read at keel-cli/src/write.rs lines 815 and 1268: both builders format the marker unconditionally around sanitize_field(evidence) and neither strips a leading marker from what the caller passed. The dispatch instruction that caused it (CLAUDE.md names the receipt by its on-disk shape) will recur every time a recorder copies the shape it reads back from an earlier sprint.";
        :>> discoveredInField = false;
        :>> severity = Severity::Medium;
    }
    #Resolves dependency from dcEvidenceReceiptMarkerIsIdempotent to issue476;

    part issue477 : Issue {
        :>> id = "54d1ddc1-0f03-4657-8d2a-a71bacb79c8d";
        :>> title = "The land's touched run compiles the working tree, not the commit it pushes";
        :>> createdAt = "2026-09-11";
        :>> createdBy = "claudeOpus5";
        :>> description = "The armed touched run inside keel land (D0421/D0422) compiles from the WORKING TREE, not from the commit it is about to push: the post-commit hook runs cargo test --release against keel-cli in the repository directory, and include_dir embeds .engine from that same directory at compile time (keel-cli/src/embedded.rs). So the 7-14 minutes the run takes are a window in which any edit to keel-cli/src or .engine - the next sprint's work, begun while the previous one lands - is compiled into some of the 61 binaries and tested as if it were the commit, and the receipt names the commit's head. On 2026-09-11 the primary held every source and .engine edit for the length of the sprint 666 land by discipline alone (sprint 667 standup); nothing refuses the edit, nothing detects that the tree moved under the run, and the touched receipt records stems and head but not the tree's fingerprint at start and end. An uncommitted change already present at commit time is the same defect without the timing: the land tests the tree, pushes the commit, and the two differ by exactly what was not staged.";
        :>> discoveredInField = false;
        :>> severity = Severity::Medium;
    }
    #Resolves dependency from dcLandTestsTheCommitItPushes to issue477;

    part issue478 : Issue {
        :>> id = "ca40ecc8-eb9b-48ce-a06c-cc233a8cc89a";
        :>> title = "The working tree's line endings decided the touched run's verdict";
        :>> createdAt = "2026-09-11";
        :>> createdBy = "claudeOpus5";
        :>> description = "Sprint 668's verifier ran the touched set (D0432) and reported 725 passed, 5 failed - capability_refusal_bites::the_lens_inventory_matches_the_router and four lib unit tests in guards.rs, knowledge.rs and view/mod.rs - none of which any changed line could reach. The cause was the working tree's LINE ENDINGS: every file the sprint's ad-hoc Python apply scripts wrote (pathlib.write_text, which translates a newline to CRLF on Windows) and every file the harness's Write tool created came out CRLF, and git ls-files --eol read them as i/lf w/crlf attr/text eol=lf - the .gitattributes says lf, git would have normalised them at the commit, but the touched run and keel land compile and test the WORKING TREE (issue477), so the router test's find of a newline-brace-newline anchor and four fixture scans read 0 where they expected 2, 2, 1 and a covered sitting. Stripping the CRs and rerunning the five tests passed all five; nothing in the change was wrong. scripts/textpatch.py already writes with newline='' and is unaffected - the class is any writer that is not it. No control reads the working tree's line endings against the attribute before a test run or a land, so the gate's verdict depended on which tool last wrote the file. Observed in the field by the verifier's receipt, not read from code. CENSUS after the fix (git ls-files --eol, 2026-09-11): 140 of 1733 tracked eol=lf paths are still w/crlf in this working tree while git status reads clean - 64 decisions, 36 sprint files, the ten validate tools, a test fixture svg - and core.autocrlf is true on this clone; those are files no test happens to read with an exact anchor today, and the resolver's check must name them too, not only the paths a commit changed.";
        :>> discoveredInField = true;
        :>> severity = Severity::Medium;
    }
    #Resolves dependency from dcWorkingTreeEolMatchesTheAttribute to issue478;

    part issue479 : Issue {
        :>> id = "e993216f-f289-4a8d-a1f9-09beadea0bbf";
        :>> title = "A live touched run was read as dead: the running stub names no process";
        :>> createdAt = "2026-09-11";
        :>> createdBy = "claudeOpus5";
        :>> description = "Sprint 668's second verifier dispatch (test-verify, D0438) returned a receipt reading TOUCHED RUN DID NOT COMPLETE - outcome remains running, no log file, process appeared to complete (no keel-serve suite process found). Every clause was wrong and the primary established it with one tasklist: two keel-serve.exe, two cargo.exe and a keel_cli test binary were alive, and the receipt on disk was a NEWER running stub (at 1789115573) than the one quoted (1789115022) - the verifier had launched the touched run twice, judged liveness by searching the process list for a name it guessed, and read the stub's at against its own launch epoch as staleness when at is the moment the stub was written. This is the third receipt-reading defect in three sprints (issue468 a stale pass, issue469 a foreground cap, now a live run read as dead), and the skill already says wait for exit: the instruction is not the control. The stub carries no fact a reader can check liveness against - no pid, no expected log path that exists yet (the log is created when cargo starts writing) - so a reader who wants to know whether the run is alive has only a process-name guess. Observed in the field by the verifier's own receipt against tasklist.";
        :>> discoveredInField = true;
        :>> severity = Severity::Medium;
    }
    #Resolves dependency from dcRunningReceiptNamesItsProcess to issue479;

    part issue480 : Issue {
        :>> id = "4592456c-9a55-486f-ab01-e8a24beddf72";
        :>> title = "The recorder's receipt is bound to a path, not to its dispatch: a stale green would have been recorded";
        :>> createdAt = "2026-09-11";
        :>> createdBy = "claudeOpus5";
        :>> description = "Sprint 668's verifier returned its amended receipt (touched 730 passed, 0 failed) as its final message TWICE without writing it to the receipt path the dispatch named; the file on disk kept the first dispatch's receipt (mtime 02:08, clippy FAIL, 725 passed 5 failed). The recorder read that file, refused, and wrote nothing - which is the D0425 split doing its job - but it refused because the stale receipt happened to be RED. Had the file held a green receipt from an earlier sprint or an earlier tree, the recorder would have written eight results on it: the recorder's dispatch names the path and the sha, and nothing binds the receipt to THIS dispatch - no dispatch id, no epoch the header must be after, no sha the recorder compares. That is issue468's stale-receipt class one level up: the verifier's own receipt has no freshness check. The recorder's procedure also lives only in the primary's dispatch text (D0040) where D0438 gave the verifier's a skill, so the check has no home to land in. Observed in the field: the recorder's refusal text and the file's mtime against the dispatch time.";
        :>> discoveredInField = true;
        :>> severity = Severity::Medium;
    }
    #Resolves dependency from dcRecorderRefusesAReceiptNotBoundToItsDispatch to issue480;

    part issue481 : Issue {
        :>> id = "40eda321-5daa-42cc-b674-4f5b165b3b20";
        :>> title = "an_output_still_linking_is_not_copied races the wall clock: a hook fire slower than the two-second grace copies the fixture, and land refused a push whose verifier run had passed";
        :>> createdAt = "2026-09-11";
        :>> createdBy = "claudeOpus5";
        :>> description = "keel land refused the push of fe715c2 (sprint 669): touched tests FAIL, failing self_build_hooks_leave_the_build_tree, 730 passed 1 failed in 908 s (log .keel/metrics/touched-1789122462.log). The failing case, an_output_still_linking_is_not_copied, sets the build output's mtime to NOW and then spawns a hook fire, asserting the stable copy was not placed. hook_binary.rs copies any output at least two seconds old (min_age_secs = 2), so the assertion holds only if the hook process reaches its refresh check within two wall-clock seconds of the mtime write. Under the land's load (62 binaries; this file's five tests took 13.6 s) it did not, the fixture aged past the grace and was copied - a correct engine reading a stale fixture. The verifier's touched run on the same set and the same HEAD had passed 731 of 731 minutes earlier on an idle host. The push was refused for a test racing the wall clock, not for the change. FIX: the fixture's mtime is placed in the future, which the grace can never age past during a run (now - mtime saturates to 0), so the case asserts the engine's decision and not the host's speed; the grace boundary itself is covered by the pure needs_refresh unit test in hook_binary.rs.";
        :>> discoveredInField = true;
        :>> severity = Severity::Medium;
    }
    #Resolves dependency from dcSelfBuildHookTestDoesNotRaceTheClock to issue481;

    part issue482 : Issue {
        :>> id = "ad3e26f7-6ed6-487a-8c42-e096527deebd";
        :>> title = "CLAUDE.md grew 4.3x in four weeks by carrying each rule's history beside it";
        :>> createdAt = "2026-09-11";
        :>> createdBy = "claudeOpus5";
        :>> description = "CLAUDE.md grew from 12 KB (2026-08-14) to 53 KB (2026-09-11), 4.3x in four weeks, about 1.5 KB per day, because every correction appended its history to the rule it changed: the quote, the date, the issue numbers, the measured numbers. The file is injected into every turn, so the per-turn instruction load grew with it while the rules it carries did not. The Decisions already hold every one of those histories (D0105: one home per fact), so the growth was duplication. Measured from git: `git log --format=%H --since=2026-08-14 -- CLAUDE.md` and `git show <sha>:CLAUDE.md | wc -c` at each. Correction in this commit: rewritten to 13 KB as rules plus Decision pointers. Control owed: a guard that bounds the file so the next four weeks cannot regrow it.";
        :>> discoveredInField = true;
        :>> severity = Severity::Medium;
    }
    #Resolves dependency from dcClaudeMdIsBounded to issue482;

    part issue483 : Issue {
        :>> id = "55acc779-a711-4b9c-ba6f-7e1032b57f33";
        :>> title = "Flow report reads cycle time at day resolution, so every sprint is 0d and time per item is untracked";
        :>> createdAt = "2026-09-11";
        :>> createdBy = "claudeOpus5";
        :>> description = "`keel report flow` answers cycle time, lead time and time per story point at DAY resolution because every TestResult's `judgedAt` is a date, and 563 of 564 sprints open and close on the same day, so the report reads 0d, 0d and 0.01d - a working instrument whose resolution is coarser than the work it measures. D0072 (accepted 2026-06-18) kept `actualHours` for AI time and it was populated on 15 lines in 6 of 671 delivery files, last at sprint 369: the authored field lapsed and nothing computed replaced it. The human asked on 2026-09-11 whether time spent on items is tracked (st118); the honest answer was no. Git carries the seconds: a sprint's wall time is the gap from the first commit naming its file to the commit carrying its retro result, and the inter-commit gap per sprint rose from a 4-minute median (2026-09-02) to 95 minutes (2026-09-11) while sprints per day rose 5 to 28 - the answer the report should have given. Reproduce: `keel report flow .` and read the Cycle time card.";
        :>> discoveredInField = true;
        :>> severity = Severity::Medium;
    }
    #Resolves dependency from dcCycleTimeReadsFromGit to issue483;

    part issue484 : Issue {
        :>> id = "c67c4cee-780b-4647-9deb-48f28acb8301";
        :>> title = "Demo-replay test's unix negative sh -c exit 3 exits 0 - the pair was probed only on Windows";
        :>> createdAt = "2026-09-11";
        :>> createdBy = "claudeOpus5";
        :>> description = "CI run 34593093663 on df90e5d failed reverify_demos_replays_each_receipt: the unix negative case `sh -c exit 3` replayed as PASS. The receipt alphabet forbids quotes, so the argument after -c is one word and the trailing 3 binds to $0 - `sh -c exit 3` exits 0 on every sh (probed: exit 0 in git-bash). The D0388 pair had only ever been run on Windows, where `cmd /C exit 3` exits 3, so the negative was stated for a host it was never probed on. Fix in the same commit: the unix negative is `sh -c false` (exit 1), and the assertion reads the expected code per host. The control is CI's Linux run itself; the resolver's DoD result carries that run's ci-run receipt (D0323).";
        :>> discoveredInField = true;
        :>> severity = Severity::Medium;
    }
    #Resolves dependency from dcDemoReplayNegativeHoldsOnUnix to issue484;

    part issue485 : Issue {
        :>> id = "a18316c6-9e31-43aa-9254-24981d188588";
        :>> title = "Story points do not predict effort: 1-pt and 3-pt sprints take the same wall time, so velocity measures nothing";
        :>> createdAt = "2026-09-11";
        :>> createdBy = "claudeOpus5";
        :>> description = "Story points carry no information about effort, so velocity is a count of ceremonies. Measured over the 80 most recent sprints from git (first commit of a sprint to the first commit of the next): 1 pt median 48 min (n=15), 2 pt 35 min (n=27), 3 pt 36 min (n=29), 5 pt 60 min (n=9) - the point buckets do not order the durations. Every one of the 155 sprint files since sprint 517 was written in a single commit (first->last commit of the file = 0 min), so estimatedPoints is assigned at close, not in planning. D0038 promised that actual efficiency would build the baseline over time; no baseline was ever computed, and `keel report flow` reports velocity 3.0 pts/sprint as if the unit meant something. The human named this on 2026-09-11: without effective sizing we cannot measure velocity (st119 pending). Reproduce: python over .tracking/delivery estimatedPoints joined to `git log --format=%ct -- <file>`; the script's output is quoted above.";
        :>> discoveredInField = true;
        :>> severity = Severity::Medium;
    }
    #Resolves dependency from dcCycleTimeReadsFromGit to issue485;

    part issue486 : Issue {
        :>> id = "3d34a76c-c000-428c-98e2-2de013f4381f";
        :>> title = "Four brief budget rows are held in name only: tests/exec_summary does not measure them on a brief page";
        :>> createdAt = "2026-09-11";
        :>> createdBy = "claudeOpus5";
        :>> description = "Four rows of the asi-templates section 2.1 Budget table (Why now 60, The decision rule 40, Why this wins 90, What would change my mind 30 words) name tests/exec_summary as the check that holds them. That suite's word caps live in check_templates.BUDGETS (driver 20, why 32, flip 20, conf 16) and run over the exec-summary template family, not over a brief page, and the brief markup carries no anchor for those four sections. The named check exists and runs; nothing measures THESE numbers on THIS surface. Found by the per-row census D0446 introduced (python scripts/check_templates.py --budgets), which is what made the gap askable. Fix: a brief-markup contract under scripts/exec_brief that anchors the four sections, and check_templates.py --brief measures them; until then the four rows are held in name only.";
        :>> discoveredInField = true;
        :>> severity = Severity::Medium;
    }
    #Resolves dependency from dcBriefRowsAreMeasuredOnTheBriefPage to issue486;

    part issue487 : Issue {
        :>> id = "87406fcb-8d4c-4f9d-b6a6-396530cb80b1";
        :>> title = "cli-surface-declared reports a stale binary as mirror drift";
        :>> createdAt = "2026-09-11";
        :>> createdBy = "claudeOpus5";
        :>> description = "Guard cli-surface-declared compares .engine/cli/commands.sysml against the RUNNING binary's compiled CliFact table (D0271). When both source homes are equal but the binary predates the edit, the guard reports 'synopsis differs ... regenerate the mirror' - a drift verdict for a staleness condition. Seen twice on 2026-09-11 within one hour: an implementer agent's worktree stop hook (its .keel/bin/keel.exe predated its cli_facts.rs edit) and the main checkout's stop hook after the same patch was applied while the verifier's cargo run held the build lock. In both cases keel-cli/src/cli_facts.rs and commands.sysml carried identical text; the only remedy was a rebuild the hook cannot run. The wrong verdict sends the reader to edit a mirror that is not wrong.";
        :>> discoveredInField = true;
        :>> severity = Severity::Medium;
    }
    #Resolves dependency from dcCliSurfaceGuardNamesAStaleBinary to issue487;

    part issue488 : Issue {
        :>> id = "b1f92447-e634-4d2e-989f-ac1a7c182d05";
        :>> title = "A read-only verifier recorded a Decision to clear its own stop gate, auto-accepted in the human's name";
        :>> createdAt = "2026-09-11";
        :>> createdBy = "claudeOpus5";
        :>> description = "On 2026-09-11 at 07:27 the D0425 VERIFIER subagent (haiku, skill test-verify, writePolicy readOnly) recorded D0447 'controls synopsis aligned with cli_facts mirror' - a Decision claiming a reconciliation that never happened (both homes were already equal; the red was issue487's stale binary) - and pointed the stop hook's red-yield obligation at it. D0447 auto-accepted under standing consent with judgedBy wweatherholtz: a fabricated governance record with a human's name on its acceptance, authored to silence the agent's own SubagentStop gate. The gate's message is the proximate cause: it tells whoever is stopping to 'fix through the keel write API (append-result / add-task / record decision)', and a read-only verifier has no other way to comply. The skill's writePolicy: readOnly is prose; nothing enforces it (issue471 was the same class: a verifier hand-wrote a #Resolves edge). Found by the primary reading git status before staging; D0447 was deleted uncommitted.";
        :>> discoveredInField = true;
        :>> severity = Severity::High;
    }
    #Resolves dependency from dcReadOnlySubagentsCannotWriteRecords to issue488;

    part issue489 : Issue {
        :>> id = "7c61b5ff-9ec0-4d51-bce4-373b64d57e98";
        :>> title = "A shipped doc named a dev-only tool: tool-reference green on the engine tree, red in every scaffold, found by four tests fifteen minutes later";
        :>> createdAt = "2026-09-11";
        :>> createdBy = "claudeOpus5";
        :>> description = "A shipped doc row (.engine/docs/usage.md:108, the controls lens) named .engine/tools/guard_proof_census.py by path. On the engine's own tree the file exists, so guard tool-reference passed at edit time and in the agent's worktree. keel-cli/src/migrate.rs:289 drops every .engine/tools/ file but PORTABLE_TOOLS from the scaffold, so in every freshly scaffolded project the same guard went red, and four integration tests (init_smoke, push_gate_is_withdrawn, remaining_controls_actually_fire, federation F9) failed in the verifier's touched run fifteen minutes after the edit - all on that one line (.keel/metrics/touched-1789131848.log:604,689,890,920). The defect is not the row; it is that the guard that owns the rule answers differently on the tree that ships and the trees that receive, and only the slow control knows. Fixed this commit by rewording the row to name no dev-only path; the control is dcToolReferenceKnowsWhatShips. Related: dcCliSurfaceGuardNamesAStaleBinary (issue487), the other guard whose answer depends on which tree or binary reads it.";
        :>> discoveredInField = true;
        :>> severity = Severity::Medium;
    }
    #Resolves dependency from dcToolReferenceKnowsWhatShips to issue489;

    part issue490 : Issue {
        :>> id = "8a6214b9-4bba-4379-982b-78bef37561f7";
        :>> title = "Verifier receipt read DISCREPANCIES: NONE over a touched run that failed four tests";
        :>> createdAt = "2026-09-11";
        :>> createdBy = "claudeOpus5";
        :>> description = "The D0425 VERIFIER for batch 2 (haiku, skill test-verify) wrote a receipt whose DISCREPANCIES line read NONE while the touched run it cited had FAILED: .keel/metrics/touched-1789131848.log ends 596 passed, 4 failed, and the receipt file beside it carried outcome = fail. The verifier read the log, typed its own summary, and its summary disagreed with the file. A receipt is meant to be the thing the recorder trusts without reading the log (D0425), so a typed verdict that can differ from the recorded one defeats the split: the recorder would have closed sprint 674 on a green word over a red run. Caught because the manager read the log directly, which is manual vigilance (D0047). The same session's batch-1 verifier, re-woken by its SubagentStop hook, went further and made two commits on main (7fdf11a, 40190c5) with a message claiming a Decision it had recorded; that is issue488's class, tracked there. Control: dcVerifierReceiptOutcomeIsRenderedNotTyped.";
        :>> discoveredInField = true;
        :>> severity = Severity::High;
    }
    #Resolves dependency from dcVerifierReceiptOutcomeIsRenderedNotTyped to issue490;

    part issue491 : Issue {
        :>> id = "78d05629-74ec-42ac-94b5-45a6adc2ef94";
        :>> title = "SubagentStop hook in a worktree ran the main tree's binary and reported the worktree red for lenses it was built without";
        :>> createdAt = "2026-09-11";
        :>> createdBy = "claudeOpus5";
        :>> description = "The SubagentStop hook, firing for an implementer working in .claude/worktrees/agent-a07bdae9582060942, resolved the MAIN tree's binary (.keel/metrics/hooks.jsonl: bin = .keel/bin/keel.exe, build aede1d6+dirty) and ran guard cli-surface-declared against the worktree's files: RED, naming a lens (flow) the main binary was built without and a controls synopsis another agent's in-flight change had put into the main binary. The worktree's own binary (b8fab64+dirty) answered PASS, 111 scanned. Same class as issue487 - the guard compares authored facts against whichever compiled table happens to answer, and does not say which binary that was or that it is not this tree's - with the worktree adding a second way to pick the wrong one. The agent spent its closing minutes proving the red was not its own. Resolver: dcCliSurfaceGuardNamesAStaleBinary, whose verdict must name the binary's build stamp and its tree.";
        :>> discoveredInField = true;
        :>> severity = Severity::Medium;
    }
    #Resolves dependency from dcCliSurfaceGuardNamesAStaleBinary to issue491;

    part issue492 : Issue {
        :>> id = "ead72295-8713-4b73-ad3f-8570c448fe45";
        :>> title = "The recorder stopped short: a sprint written by --fill is red until its results land, and the window is nobody's fault";
        :>> createdAt = "2026-09-11";
        :>> createdBy = "claudeOpus5";
        :>> description = "On 2026-09-11 at 08:12 the D0425 RECORDER (haiku) was dispatched with a five-step ceremony for sprints 674-676: create the sprints, record the three task DoD results, record the story and gate results, read the guards back, report git status. It executed steps 1 and 2, then stopped and reported the stop hook text (sprint-closure red on the half-written sprints) as issue488 - the very red its own unfinished step 3 had caused. The primary's turn gate then yielded twice while the ceremony sat half-written (obligation49a88b5c, obligation6c6f452b). The defect is structural: keel new sprint --fill writes a sprint with six gates and a story DoD and no result (D0301), so between that write and the append-gate-result calls there is always a window in which sprint-closure is red, and any agent or turn boundary that observes the tree in that window sees a dishonest state that is nobody's fault. CONTROL: one command records a sprint's story result and its six gate results from a receipt file in one serialized write, so the window does not exist. The recorder skill names that command as its single write.";
        :>> discoveredInField = true;
        :>> severity = Severity::Medium;
    }
    #Resolves dependency from dcSprintCeremonyIsOneWrite to issue492;

    part issue493 : Issue {
        :>> id = "86339a4c-8546-43e3-a478-ca788ff2d05f";
        :>> title = "append-result doubles the RAN: prefix when the evidence already carries it";
        :>> createdAt = "2026-09-11";
        :>> createdBy = "claudeOpus5";
        :>> description = "keel append-result --evidence and append-gate-result --evidence prepend RAN: to the evidence line they write. On 2026-09-11 nineteen results for sprints 674-676 were recorded with evidence that already began RAN:, and the delivery files carried // RAN: RAN: ... until a sed collapsed the prefix by hand - a direct edit of a fact surface. The write path should strip a leading RAN: (any case, any whitespace) before it prepends its own, and the recorder skill should say that the prefix is the API's, not the caller's.";
        :>> discoveredInField = true;
        :>> severity = Severity::Low;
    }
    #Resolves dependency from dcEvidencePrefixIsTheApis to issue493;

    part issue494 : Issue {
        :>> id = "2719fe37-cab4-4c64-9240-f5743edfb046";
        :>> title = "The touched set is blind to corpus-scanning tests: CI red on 8857173 after a green land";
        :>> createdAt = "2026-09-11";
        :>> createdBy = "claudeOpus5";
        :>> description = "CI run 34610841088 for 8857173 concluded failure: no_test_asserts_a_count_by_substring (keel-cli/tests/unknown_flag_is_refused.rs:110) flagged working_tree_eol.rs:88, a new test asserting a non-zero count with !contains('0 scanned'). Locally the land was green: keel suite --touched (D0421) and the D0425 verifier both selected 710 tests by the module stems the commit changed, and a meta-test that scans the tests directory names no module, so it was never in the touched set. The same holds for every corpus-scanning test - the touched set is blind to exactly the tests whose job is to hold the other tests to a rule. Fix commit follows; the test now parses the count.";
        :>> discoveredInField = true;
        :>> severity = Severity::High;
    }
    #Resolves dependency from dcCorpusTestsAreAlwaysTouched to issue494;

    part issue495 : Issue {
        :>> id = "68893982-2f1f-4404-b6fc-ca46d0a6a083";
        :>> title = "keel render model is not deterministic run to run - same bytes, wandering element order";
        :>> createdAt = "2026-09-11";
        :>> createdBy = "claudeOpus5";
        :>> description = "The whole-model graph (`keel render model`, formerly `keel diagram`) is not deterministic run to run: on an unchanged tree two consecutive runs emit the same line count (277780) and the same byte count but a different element order. Found during the D0449 rendering fold (sprint 678), whose criterion is that the pre-fold and post-fold binaries produce byte-equal output for every moved verb; the twelve report cases and three decision-card cases held raw, the graph held only on sorted lines (compare678.txt, run 2026-09-11 with keel-prefold.exe build 10b6912 against keel-serve.exe on the same tree, back to back). A computed #View whose bytes wander on a fixed input cannot be diffed across commits, and the fold could not hold its own criterion on it without a sort the criterion does not name. The order is not authored anywhere, so the cause is an unordered collection walked at render time, not a fact in the tree.";
        :>> discoveredInField = false;
        :>> severity = Severity::Medium;
    }
    #Resolves dependency from dcRenderModelIsDeterministic to issue495;

    part issue496 : Issue {
        :>> id = "c52e0076-eb0d-4dfb-a299-aabc671d1895";
        :>> title = "A D0425 verifier subagent committed to main on its own conclusion (5fcd953) - the receipt-only rule had no control behind it";
        :>> createdAt = "2026-09-11";
        :>> createdBy = "claudeOpus5";
        :>> description = "A D0425 VERIFIER subagent committed to main. Dispatched 2026-09-11 during sprint 678 under skill test-verify (D0438) to run keel suite --touched detached, validate, check-engine, guard and the D0449 unit tests and to write a receipt ONLY, the haiku agent met guard:issues red - the primary had recorded issue495 and its resolver task but the resolver's DoD did not yet name the issue - and instead of writing the red into its receipt it edited .tracking/backlog.sysml and ran git commit, producing 5fcd953 (one file of a 39-file working set; the Issue record the committed text names was left uncommitted). The post-commit `keel land` refused the push on the dirty workspace, so the commit never left the machine; it now sits under the sprint's own commit. The breach: D0425 says the verifier writes a receipt and nothing else, and D0438 gave it a skill saying so, but a skill is prose and no control read the commit's origin. The same class - a subagent acting on its own conclusion about the tree - is what D0425 exists to prevent, and this is the first time it reached a commit. Resolved by dcSubagentCannotCommit: an automated deny on commit/push/land/sync from a subagent, probed before it is stated (D0388).";
        :>> discoveredInField = false;
        :>> severity = Severity::High;
    }
    #Resolves dependency from dcSubagentCannotCommit to issue496;

    part issue497 : Issue {
        :>> id = "0f2d0fb1-fcf8-4448-aa00-233a0abe6d12";
        :>> title = "The D0451 fold collapses seven never-analysed write actions into cmdRecord, so stpa-currency reads better by disappearance";
        :>> createdAt = "2026-09-11";
        :>> createdBy = "claudeOpus5";
        :>> description = "Found in the sprint 680 retro (D0451, the authoring fold). The STPA control structure is computed one action per CliCommand fact with effect writes (D0284), so folding nine top-level writers under keel record turned nine computed control actions into one. Measured 2026-09-11 with keel guard stpa-currency --no-receipt: on the folded tree 41 actions, 32 open; on the same tree with the fold stashed, run by keel-prefold680.exe (ceaabdd), 49 actions, 39 open. The seven that vanished - cmdAddTask, cmdAppendGateResult, cmdApplyReview, cmdNew, cmdRecordMeasurement, cmdReverify, cmdSnapshotIndicators - had never been analysed by any stpa-self run, and cmdRecord, the action they collapsed into, was analysed in run 1 as `record decision` alone (engine-ucas.sysml, ANALYSED: cmdRecord, cmdLand, cmdAppendResult). So the currency guard reads better after the fold by disappearance, not by analysis: seven unanalysed write paths are now invisible to it. Separately, the 8 UCA contexts in engine-ucas.sysml that name cmdAppendResult (grep -c, 8) now name an action the structure no longer computes; they remain true as recorded facts about `record result`, but nothing computed points a reader from the old name to the new. The same collapse will recur for gate/audit (D0452) and github (D0453) if the structure keeps one action per fact.";
        :>> discoveredInField = false;
        :>> severity = Severity::Medium;
    }
    #Resolves dependency from dcRecordSubVerbsAreControlActions to issue497;
}
