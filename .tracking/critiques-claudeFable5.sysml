// Per-actor critiques records for claudeFable5 (issue210/srDcPerActorWriteTargets): new records
// route here so concurrent contributors never conflict at a shared append anchor.
package CritiquesClaudeFable5 {
    private import EngineElement::*;
    private import EngineWork::*;
    private import EngineVerification::*;
    private import EngineRelationships::*;

    // ── srK06aDelegatedRecording Core-3 (sprint 421: the last two never-examined SRs) ─────────────

    verification srK06aCompl1 : Test { :>> id = "1441d301-9935-4865-a582-35ec22ca5769"; :>> title = "srK06aDelegatedRecording x completeness"; :>> createdAt = "2026-08-22"; :>> createdBy = "claudeFable5"; :>> method = VerificationMethod::critique; :>> lens = CritiqueLens::completeness; :>> critiquedBy = CriticKind::aiModel; :>> procedureText = "ATTACK (what the clause does NOT cover): (1) the statement covers acceptance and confirmation records but the delegation is DECLARED only for decisionAcceptance - a delegated sitting review or DoD confirmation flip is practiced (the sprint-420 DoD flip itself) yet no [confirmationRecord] class exists in the policy; the guard demands quotes only on dNNNNAccept events, so a quote-less delegated DoD confirmation would pass silently. That asymmetry is the SAME shape D0192 just closed for acceptances, one level down. (2) The gesture allowance (text containing deck/console) is a loophole the review gate already names: a fabricated gesture citation passes the substance check exactly as a fabricated quote would - stated, accepted, same trust boundary. FOUND: gap (1) is real and recurrable; tracked as issue224 with the policy-entry extension as its resolver."; }
    part srK06aCompl1R1 : TestResult { :>> id = "504bc028-8cfb-4dbc-8952-3d80a85a2ca1"; :>> outcome = VerdictKind::fail; :>> judgedAgainst = "c116a61"; :>> judgedAt = "2026-08-22"; :>> judgedBy = "claudeFable5"; }
    #Verify dependency from srK06aCompl1 to srK06aDelegatedRecording;

    verification srK06aCorr1 : Test { :>> id = "409cae7a-0852-4528-8772-1535ffb9a019"; :>> title = "srK06aDelegatedRecording x correctness"; :>> createdAt = "2026-08-22"; :>> createdBy = "claudeFable5"; :>> method = VerificationMethod::critique; :>> lens = CritiqueLens::correctness; :>> critiquedBy = CriticKind::aiModel; :>> procedureText = "ATTACK (does what exists do what the statement says): the delegation clause's three conditions (verbatim quote, named judge, cited delegation) map to enforcement as follows - quote: delegatedAcceptanceSubstanceRule, negative-probed RED then green this sprint; named judge: the write layer's judged_by requirement plus confirmationAuthenticityRule's Person check; cited delegation: NOT independently checked (the policy declaration exists, but a record need not name d0192 to pass). Two of three conditions are enforced, the third is convention. The statement's 'declared per attestation class' half IS true for the class it names. PASS with the third-condition residual stated - it is substance-adjacent, not authenticity-critical, since the quote and judge carry the evidentiary load."; }
    part srK06aCorr1R1 : TestResult { :>> id = "353382e7-3185-40e5-8cfa-1fc212433b44"; :>> outcome = VerdictKind::pass; :>> judgedAgainst = "c116a61"; :>> judgedAt = "2026-08-22"; :>> judgedBy = "claudeFable5"; }
    #Verify dependency from srK06aCorr1 to srK06aDelegatedRecording;

    verification srK06aTest1 : Test { :>> id = "d97c1df6-2426-4d03-b28a-ca7db878616c"; :>> title = "srK06aDelegatedRecording x testability"; :>> createdAt = "2026-08-22"; :>> createdBy = "claudeFable5"; :>> method = VerificationMethod::critique; :>> lens = CritiqueLens::testability; :>> critiquedBy = CriticKind::aiModel; :>> procedureText = "ATTACK (falsifiability): the quote-substance clause is negative-testable and WAS negative-tested (the zz-probe decision turned the guard RED with the d0192 message, removal turned it green); the declared-per-class clause is checkable by reading one TOML table; the human-held-channel arm inherits srK06's original probes (kind refusal at three endpoints). The inherently untestable core srK06 carried - distinguishing WHO typed a name - remains untestable BY DESIGN and is now stated as the accepted cost inside the requirement's own rationale rather than left as an implied guarantee. PASS: every clause is either tested, mechanically checkable, or explicitly declared untestable with the trade recorded."; }
    part srK06aTest1R1 : TestResult { :>> id = "91ed7c1b-5c3b-40fe-8e56-fdf76e8c7fd0"; :>> outcome = VerdictKind::pass; :>> judgedAgainst = "c116a61"; :>> judgedAt = "2026-08-22"; :>> judgedBy = "claudeFable5"; }
    #Verify dependency from srK06aTest1 to srK06aDelegatedRecording;

    // srK06a EXERCISED: the guard substance check ran against the live model and a planted negative.
    verification srK06aExercise1 : Test { :>> id = "c6d4ac1b-b6be-4dc1-ace9-ae4dcfaa43c6"; :>> title = "srK06aDelegatedRecording exercised via the confirmation-authenticity guard"; :>> createdAt = "2026-08-22"; :>> createdBy = "claudeFable5"; :>> method = VerificationMethod::test; :>> procedureText = "RUN 1 (negative): a temporary accepted Decision (dProbe) whose acceptance event carried no quoted span and no gesture citation - keel guard reported confirmation-authenticity FAIL, 1 violation, message naming the d0192 recording delegation. RUN 2 (positive): probe removed - confirmation-authenticity PASS over 192 scanned including the real D0192 OPTION A acceptance, which satisfies the very check it created. Unit test delegated_records_must_quote_or_cite_a_gesture pins the boundary (verbatim span passes, apostrophe artifact fails, deck/console gestures pass). Sprint 420, session transcript quotes both guard outputs."; }
    part srK06aExercise1R1 : TestResult { :>> id = "1f1d7587-0040-4036-ad27-f91308092618"; :>> outcome = VerdictKind::pass; :>> judgedAgainst = "c116a61"; :>> judgedAt = "2026-08-22"; :>> judgedBy = "claudeFable5"; }
    #Verify dependency from srK06aExercise1 to srK06aDelegatedRecording;

    // ── srK16OutwardPublishGated Core-3 (examined-never half of the same pending pair) ────────────

    verification srK16Compl1 : Test { :>> id = "8be0ab08-9b9b-4e84-afad-adfb1e5aab08"; :>> title = "srK16OutwardPublishGated x completeness"; :>> createdAt = "2026-08-22"; :>> createdBy = "claudeFable5"; :>> method = VerificationMethod::critique; :>> lens = CritiqueLens::completeness; :>> critiquedBy = CriticKind::aiModel; :>> procedureText = "ATTACK (which outward channels the statement does NOT name): the statement enumerates release publish, tag-triggered build, and trunk landing. NOT enumerated: (1) the artifact deck/report publishes to claude.ai - outward by any reading, yet ungated by design (they carry VIEWS, not the model; a stale view harms nobody because the CLI is authority, D0093); (2) the Smartsheet inbox writes - outbound DATA, but inbound OBLIGATIONS, gated by the record-then-verify-then-mark-processed loop rather than a tree gate. Both are boundary crossings a stricter reading would cover, and both are defensible as-is because nothing that leaves through them is TRUTH. The statement's scope - artifacts whose content claims to BE the shipped system - is the right cut. PASS with the two adjacent channels named so a future reviewer sees they were considered, not missed."; }
    part srK16Compl1R1 : TestResult { :>> id = "2b8814e9-5468-4225-be8b-138b8ef9eb61"; :>> outcome = VerdictKind::pass; :>> judgedAgainst = "c116a61"; :>> judgedAt = "2026-08-22"; :>> judgedBy = "claudeFable5"; }
    #Verify dependency from srK16Compl1 to srK16OutwardPublishGated;

    verification srK16Corr1 : Test { :>> id = "049c7d6a-0dd9-48e3-bca0-6bce2452ddd7"; :>> title = "srK16OutwardPublishGated x correctness"; :>> createdAt = "2026-08-22"; :>> createdBy = "claudeFable5"; :>> method = VerificationMethod::critique; :>> lens = CritiqueLens::correctness; :>> critiquedBy = CriticKind::aiModel; :>> procedureText = "ATTACK (do the named controls enforce the named property): release publish - the workflow's gate job is a hard dependency of the publish job (sprint 409, probed both ways: green published, planted-red built nothing); trunk landing - keel land gates the MERGED tree before retrying a rejected push (D0129), and CI's audit-history re-derives verdicts over every pushed range so nothing remote assumes a local hook ran (K15/D0179); pre-push behind-check refuses a stale push (sprint 415). Each control cites live probe evidence in its own sprint record. PASS: the statement's 'exact tree being shipped' clause is the load-bearing phrase and the merged-tree gate is what discharges it."; }
    part srK16Corr1R1 : TestResult { :>> id = "63ee8f9d-6d3d-4f9b-9fbe-f1b2d95d149b"; :>> outcome = VerdictKind::pass; :>> judgedAgainst = "c116a61"; :>> judgedAt = "2026-08-22"; :>> judgedBy = "claudeFable5"; }
    #Verify dependency from srK16Corr1 to srK16OutwardPublishGated;

    verification srK16Test1 : Test { :>> id = "080673af-ea2f-45d5-a432-474c92ccf0eb"; :>> title = "srK16OutwardPublishGated x testability"; :>> createdAt = "2026-08-22"; :>> createdBy = "claudeFable5"; :>> method = VerificationMethod::critique; :>> lens = CritiqueLens::testability; :>> critiquedBy = CriticKind::aiModel; :>> procedureText = "ATTACK (falsifiability): the requirement is negative-testable end to end and HAS been - the planted-red release run built nothing and published nothing, visibly (sprint 409's flip-2 evidence, the strongest form: the system was made to try to violate the requirement and refused). Residual: the test is EXPENSIVE (a real CI round-trip per probe), so drift detection rests on keel controls' hazard mapping (ehz9) and CI's own green rather than routine re-probing - acceptable while the workflow file is under doc-sync and the release gate's removal would surface as a recorded violation of THIS requirement. PASS."; }
    part srK16Test1R1 : TestResult { :>> id = "b2c596b6-43cc-4f32-b4f1-971590652a8a"; :>> outcome = VerdictKind::pass; :>> judgedAgainst = "c116a61"; :>> judgedAt = "2026-08-22"; :>> judgedBy = "claudeFable5"; }
    #Verify dependency from srK16Test1 to srK16OutwardPublishGated;
    verification issue223Disp1 : Test { :>> id = "092af5ce-5119-4970-b585-3d5741615094"; :>> method = VerificationMethod::confirmation; :>> disposition = DispositionKind::act; :>> procedureText = "AI-dispositioned under the D0165 delegation (their words: 'auto accept issues by your authority'). fixed in sprint 419 - fork decisions render per-option sign buttons; exercised live by D0192's and D0198's cards."; }
    part issue223Disp1R1 : TestResult { :>> id = "e1e123fa-ed40-4b28-9cc4-63012ae5cd7d"; :>> outcome = VerdictKind::pass; :>> judgedAgainst = "a2a3884"; :>> judgedAt = "2026-08-22"; :>> judgedBy = "claudeFable5"; }
    #Dispositions dependency from issue223Disp1 to issue223;
    verification issue224Disp1 : Test { :>> id = "814b2514-cab3-4397-990f-a02d3f304b7b"; :>> method = VerificationMethod::confirmation; :>> disposition = DispositionKind::act; :>> procedureText = "AI-dispositioned under the D0165 delegation (their words: 'auto accept issues by your authority'). resolver dcConfirmationRecordDelegation chartered; D0198 records the design fork and is queued for signature."; }
    part issue224Disp1R1 : TestResult { :>> id = "afa02eb5-1f75-458f-97e7-0237baf9043c"; :>> outcome = VerdictKind::pass; :>> judgedAgainst = "a2a3884"; :>> judgedAt = "2026-08-22"; :>> judgedBy = "claudeFable5"; }
    #Dispositions dependency from issue224Disp1 to issue224;
    verification issue225Disp1 : Test { :>> id = "ca391cdf-bf67-4ad1-bcc3-06fee552bc62"; :>> method = VerificationMethod::confirmation; :>> disposition = DispositionKind::act; :>> procedureText = "AI-dispositioned under the D0165 delegation (their words: 'auto accept issues by your authority'). fixed in sprint 422 - the proptest strategy filters through the lexer's own reserved-word predicate; regression pinned."; }
    part issue225Disp1R1 : TestResult { :>> id = "ccb89e06-9827-4de4-857a-d645a490cf70"; :>> outcome = VerdictKind::pass; :>> judgedAgainst = "a2a3884"; :>> judgedAt = "2026-08-22"; :>> judgedBy = "claudeFable5"; }
    #Dispositions dependency from issue225Disp1 to issue225;
    verification issue226Disp1 : Test { :>> id = "a6305e6c-5925-4db3-a91a-ac7945170301"; :>> method = VerificationMethod::confirmation; :>> disposition = DispositionKind::act; :>> procedureText = "AI-dispositioned under the D0165 delegation (their words: 'auto accept issues by your authority'). fixed in sprint 423 - the unit asserts the ownership guard, the stale contract claim deleted, D0199 queued."; }
    part issue226Disp1R1 : TestResult { :>> id = "6a54664c-4a38-4ece-8e3b-6be6d03adc7a"; :>> outcome = VerdictKind::pass; :>> judgedAgainst = "a2a3884"; :>> judgedAt = "2026-08-22"; :>> judgedBy = "claudeFable5"; }
    #Dispositions dependency from issue226Disp1 to issue226;
    verification issue229Disp1 : Test { :>> id = "b2bdaaa8-b6a7-4866-ad95-048bb1603d96"; :>> method = VerificationMethod::confirmation; :>> disposition = DispositionKind::act; :>> procedureText = "AI-dispositioned under the D0165 delegation. fixed in sprint 427 - land warns on held items, guard 47 bounds claim dates."; }
    part issue229Disp1R1 : TestResult { :>> id = "e610a526-12a6-466b-ad0d-f03a04656ab5"; :>> outcome = VerdictKind::pass; :>> judgedAgainst = "71f6453"; :>> judgedAt = "2026-08-23"; :>> judgedBy = "claudeFable5"; }
    #Dispositions dependency from issue229Disp1 to issue229;
    verification issue231Disp1 : Test { :>> id = "b536522c-e46a-40b2-a470-9aa6d543d544"; :>> method = VerificationMethod::confirmation; :>> disposition = DispositionKind::act; :>> procedureText = "AI-dispositioned under the D0165 delegation. fixed in sprint 428 - the parser ratchet is live and negative-probed."; }
    part issue231Disp1R1 : TestResult { :>> id = "451ba096-05ac-4311-b88e-ac9176f31f36"; :>> outcome = VerdictKind::pass; :>> judgedAgainst = "71f6453"; :>> judgedAt = "2026-08-23"; :>> judgedBy = "claudeFable5"; }
    #Dispositions dependency from issue231Disp1 to issue231;
    verification issue230Disp1 : Test { :>> id = "955618b0-2eb2-461e-b811-a56afa73e8a0"; :>> method = VerificationMethod::confirmation; :>> disposition = DispositionKind::act; :>> procedureText = "AI-dispositioned under the D0165 delegation: resolver dcAdvisoryInstrumentation is chartered on the frontier; the design touches the frozen D0193 ledger contract and will carry its own decision when executed."; }
    part issue230Disp1R1 : TestResult { :>> id = "e94e742f-f839-4fa1-8504-bc02f798db65"; :>> outcome = VerdictKind::pass; :>> judgedAgainst = "71f6453"; :>> judgedAt = "2026-08-23"; :>> judgedBy = "claudeFable5"; }
    #Dispositions dependency from issue230Disp1 to issue230;
    verification issue232Disp1 : Test { :>> id = "946f97ec-e690-445d-ad46-bfb20affa24f"; :>> method = VerificationMethod::confirmation; :>> disposition = DispositionKind::act; :>> procedureText = "AI-dispositioned under the D0165 delegation. fixed same-day - shallow-clone skip + CI full history."; }
    part issue232Disp1R1 : TestResult { :>> id = "4c154186-5a3d-48a4-876a-df14567f603b"; :>> outcome = VerdictKind::pass; :>> judgedAgainst = "7ef4443"; :>> judgedAt = "2026-08-23"; :>> judgedBy = "claudeFable5"; }
    #Dispositions dependency from issue232Disp1 to issue232;
    verification issue233Disp1 : Test { :>> id = "ee99f343-4c13-4e31-831c-75409b6f9c8d"; :>> method = VerificationMethod::confirmation; :>> disposition = DispositionKind::act; :>> procedureText = "AI-dispositioned under the D0165 delegation. fixed in sprint 429 - only the tapped option highlights."; }
    part issue233Disp1R1 : TestResult { :>> id = "1344fd11-53e6-4391-b4d0-8a7586ac1223"; :>> outcome = VerdictKind::pass; :>> judgedAgainst = "7ef4443"; :>> judgedAt = "2026-08-23"; :>> judgedBy = "claudeFable5"; }
    #Dispositions dependency from issue233Disp1 to issue233;
    verification issue234Disp1 : Test { :>> id = "5da385c3-631e-462a-ad34-5cc276459a2c"; :>> method = VerificationMethod::confirmation; :>> disposition = DispositionKind::act; :>> procedureText = "AI-dispositioned under the D0165 delegation. fixed in sprint 429 - decision cards render their own deciding context."; }
    part issue234Disp1R1 : TestResult { :>> id = "a45cfcb6-c8c9-4e3f-9dc2-6ae972e477ea"; :>> outcome = VerdictKind::pass; :>> judgedAgainst = "7ef4443"; :>> judgedAt = "2026-08-23"; :>> judgedBy = "claudeFable5"; }
    #Dispositions dependency from issue234Disp1 to issue234;
    verification issue237Disp1 : Test { :>> id = "c84d2d68-07bf-44ca-a161-7415965a1e90"; :>> method = VerificationMethod::confirmation; :>> disposition = DispositionKind::acceptRisk; :>> procedureText = "AI-dispositioned under D0165. The tracked hollow-pass case - a task marked done against a non-resolving SHA - IS caught by orient invalidEvidence and CI audit-history (the controls that own this threat); an UNREFERENCED garbage-SHA TestResult computes nothing and is inert. Adding a commit-gate SHA-resolvability check would gate on network/remote reachability, which K15 tree-derivability forbids. The residual (an orphan inert result) is accepted with the coverage stated; dcDanglingResultAtGate holds the reconsideration if a referenced case ever escapes."; }
    part issue237Disp1R1 : TestResult { :>> id = "c1181c60-a398-4869-865f-e9bd4a1718ec"; :>> outcome = VerdictKind::pass; :>> judgedAgainst = "e14fbfb"; :>> judgedAt = "2026-08-24"; :>> judgedBy = "claudeFable5"; }
    #Dispositions dependency from issue237Disp1 to issue237;
}
