// KNOWLEDGE RECORD (D0196) - the adoption/portability/elicitation/drift panel and what it overturned.
package KnowledgeAdoptionTruthPanel20260824 {
    private import EngineElement::*;
    private import EngineVerification::*;

    verification kAdoptionTruthPanel : Test {
        :>> id = "3b1e2c47-6a5d-4f8e-9c21-7d4e5a8f0b93";
        :>> title = "Panel: adoption, portability, elicitation and why reports drift from truth - nine lenses, unanimous OBJECT against the brief";
        :>> createdAt = "2026-08-24"; :>> createdBy = "claudeFable5";
        :>> method = VerificationMethod::analyze;
        :>> procedureText = "REPLICATION (D0196). PROCESS: adversarialPanelReview (D0187). TRIGGER: the human asked six questions - portable feedback elicitation, process transfer, onboarding that selects processes, an AI skill that helps pick them, whether input becomes Statements then UserStories (noting that pulling latent needs out of a user is critical for the average user), and discoverability - plus a seventh that mattered most: 'it feels like we are still regularly out of sync with what is being reported and what the truth is. why?' ARTIFACT: docs/reviews/adoption-and-truth-brief-2026-08-24.md, ten measured ground-truth rows (G1-G10), four proposed drift mechanisms (D1-D4), seven candidate improvements (C1-C7). ROSTER: nine parallel independent lenses (2 pessimists, 2 optimists, 3 pedants, reducer, SE), each instructed to verify against the REPOSITORY and never against the brief. RESULT: NINE OF NINE OBJECT - the brief was materially wrong and the panel corrected it. WHAT WAS OVERTURNED: (1) G10/D1 (two catalogues disagree, unreconciled) FALSIFIED by five lenses - keel activation prints all 23 declared processes and labels the guard-less 12 '[always] asserts no guard - nothing to switch off', its active set is exactly the palette's 11, activation.toml declares exactly those 11, and a regression test declared_processes_is_every_file_not_only_the_guard_bearing_units REQUIRES the sets to differ; the candidate that would have merged them (C2) would have BROKEN that test and regressed issue149, whose recorded conclusion was 'THE DEFECT IS THE SURFACE, NOT THE MECHANISM'. The true residual is one-directional under-reporting by keel process only. (2) G8 (97 percent unsourced) MISMEASURED by three lenses - the population is Need/SystemRequirement/Issue/Decision, so work items are not in it at all; ~323 of 619 predate D0166 (accepted 2026-08-20) and could not cite a Statement type that did not exist; 72 percent of the denominator is Issues and Decisions that structurally have no human utterance; and the tool prints its own floor caveat which the brief stripped. Post-mechanism sourcedness is ~15 percent, and the ACTIONABLE fact is different: intake has recorded nothing since 2026-08-21 across four days and four panels, and the human's own six questions were never intaken. (3) D3's premise (no gate can read conversational output) FALSIFIED - serve.rs already parses the session jsonl for both roles; D0151's concession is about hooks as wired, not machine-readability. (4) C7 CUT by three lenses - its motivating instance (issue238) was already closed structurally by making the referenced artifact exist on every path (sprint442), which is the general lesson: when a claim about a surface is false, generate the surface, never add an artifact class for the claim. (5) C6 CUT as the worst item - 'two surfaces answering the same question' is not machine-decidable, and adding a detector to a system that already detects more than it triages makes the felt problem worse. WHAT THE PANEL FOUND THAT THE BRIEF MISSED: (a) THE REFRAMING (SE): D1, D2 and D4 are not three mechanisms but three violations of ONE accepted invariant - nConsoleNeverMisleads (N-C2, human-accepted 2026-08-16) already requires absence to be distinguishable from information about absence and stale never shown as current, but its only satisfying requirement is scoped to the HTML console while CLI/JSON is the declared authority; the answer to question 7 is not 'add a control' but 'an invariant you already signed is bound to the wrong surface' (issue239). (b) THE COMMIT GATE WAS DISARMED (mechanisms lens, confirmed directly): core.hooksPath = nul, so no local git hook ran all session while I repeatedly said 'the hook passed'; keel hardening reported present=true fail-closed, orient printed no warning, controls reported uncoveredHazards=[] - because wiredness is computed as 'the config value is non-empty', a proxy for reachability (issue240). (c) A CORE GUARD CAN BE CAPTURED (operations lens, reproduced live): adding one assert constraint line to a guard-less process file demoted core stale-gate-prose to that process's switchable property and its run became 'PASS - 0 scanned, 1 warning'; the CLI's own remediation text ADVISES the edit; and audit-adherence - the D0209 clause-1 gate built this same session for exactly this class - reads only .engine/rules/ so it cannot see it, nor an activation.toml narrowing (issue242). (d) A MUST-REQUIREMENT VIOLATION PASSED AS GREEN (SE): 12 of 23 processes cannot be listed/shown/exported, violating accepted must srPortModularProcessUnit, while three critiques dated 2026-08-21 passed it with zero findings - two citing a live run of the very command - and tier-satisfaction reports 103/103; a false green inside the verification substrate (issue241). (e) EVERY NEW PROJECT INHERITS THIS ONE'S ADOPTION (ROI lens, confirmed by diff): a fresh keel init produces a byte-identical activation.toml plus inherited unit ids, so it reports 'declared manifest: yes' for a declaration it never made, falsifying CLAUDE.md's own adoption guarantee (issue243). (f) DETECTED-BUT-UNREAD (reducer), the mechanism with the most evidence and the sharpest answer to question 7: keel guard prints ALL PASS while emitting 80 warnings across 10 guards, one of which is a live shipped unacted-on contradiction - tag v0.2.0 points at e2c812f but its Release item records 425145d; the fix is subtractive, surface what is already detected (issue244). (g) THE ELICITATION SKILL IS UNCATALOGUED (three lenses): business-architecture already runs the design dialogue and has authored 11 Briefs, 15 Personas, 69 UseCases, 75 Needs, but has no process definition so it is in no catalogue and transferable by nothing - and process-skill is one-directional so nothing notices - while authoring Needs from utterances never recorded, which is both the cause of the unsourced population and the D0157 wider-than-the-demand risk; so the answer to question 5 is a WIRING change to an existing skill, not a fourth interview surface (issue245). (h) D5, PROSE COUNTS DRIFT (four lenses): CLAUDE.md and guards.md say 45 forward guards where 48 run; activation.toml still cites a file D0141 deleted and init copies the ghost into every project; the brief itself said 30 skills where there are 37 and cited issues #1-#6 where the channel is #2-#7 - the drift class committed inside the document diagnosing it (issue246). SINGLE-SHIP ANSWER (reducer, unopposed): point process_cmd::rows() at the already-tested activation::declared_processes() - one call site, closes the portability finding, and subtractive (it removes a surface's ability to disagree rather than adding a control to notice that it did). KEY LEARNING: the brief asked 'which new controls close these gaps' and the panel's answer was that four of seven candidates were redundant with shipped machinery, two were actively harmful, and the real defects were an accepted invariant scoped too narrowly, a detector whose predicate was a proxy, a false green in the verification layer, and 80 unread warnings - i.e. the drift is not under-detection but under-reading and under-scoping. STANDING CAVEAT: all nine lenses share one model lineage (dcHeterogeneousCritics parked by D0210), so this panel claims CONVERGENCE, not independence. ARTIFACTS: docs/reviews/adoption-and-truth-brief-2026-08-24.md; issues 239-246 with resolvers.";
    }
    part kAdoptionTruthPanelR1 : TestResult {
        :>> id = "9f7c04ab-5e18-4c62-b3d9-1a205e63cf47";
        :>> outcome = VerdictKind::pass;
        :>> judgedAgainst = "HEAD";
        :>> judgedAt = "2026-08-24";
        :>> judgedBy = "claudeFable5";
        :>> notes = "Unanimous OBJECT against the brief; eight findings recorded as issue239-issue246, each triaged to a resolver. Two findings indict controls shipped earlier the same day.";
    }
    dependency from kAdoptionTruthPanel to adversarialPanelReview;
    dependency from kAdoptionTruthPanel to d0187;
    dependency from kAdoptionTruthPanel to d0196;
    dependency from kAdoptionTruthPanel to d0210;
}
