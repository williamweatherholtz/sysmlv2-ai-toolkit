// D0165 — the human delegated finding disposition to the AI in their own words. Recorded because it
// WEAKENS an attestation control, and a weakening must be as legible as the control it relaxes.
// #ProspectiveChange (D0070): changes a declared attestation policy, not code.
package Decision0165 {
    private import EngineElement::*;
    private import EngineWork::*;
    private import EngineVerification::*;
    private import EngineRelationships::*;

    #ProspectiveChange part d0165 : Decision {
        :>> id = "5b1d9f24-08c7-4e63-a915-7fe240b6c831";
        :>> title = "D0165: finding disposition is delegated to the AI — the ONE attestation class where a human's sign-off is no longer required";
        :>> createdAt = "2026-08-20";
        :>> createdBy = "claudeOpus5";
        :>> status = DecisionStatus::accepted;
        :>> context = "wweatherholtz, verbatim, submitting an obligations-deck review: 'accept all sprints, and no need to accept issues that have been resolved. auto accept issues by your authority.' THE THIRD CLAUSE IS A DELEGATION OF ATTESTATION AUTHORITY and it collides with a hard control: `attestation-authority` requires the actor dispositioning a finding at or above Medium to satisfy the declared policy for `findingDisposition`, which is `kinds = [human]`, `roles = [supervisor]` (D0092/D0080/D0146). My actor is `kind = ai`, `role = contributor`, so every disposition I record for a Medium-or-above finding fails that guard. THE INSTRUCTION IS THEREFORE NOT EXECUTABLE WITHOUT A POLICY CHANGE, and executing it quietly would have been the worst available option: an AI-recorded disposition passing a human-only check is exactly the fabricated attestation §4 forbids and issue144 already caught me doing mechanically. WHY THEY ASKED IS LEGIBLE FROM THE NUMBERS: 23 findings sat undispositioned, they judged 19 by hand in one sitting, and 4 more had accrued in the hours since the deck was generated. The queue grows faster than one person can clear it, which they had already named ('i can bulk verify items through demonstration') and which sprint 349 recorded as a rate mismatch I could not fix from my side. This is them fixing it from theirs.";
        :>> decision = "ACCEPTED AND APPLIED, in the mechanism the engine already provides and nowhere else. `.engine/contracts/attestation-policy.toml` `[findingDisposition]` becomes `kinds = [human, ai]`, `roles = [supervisor, contributor]`. NO CODE CHANGED: the policy was already declared rather than hardcoded (D0146), precisely so a project could state its own answer, and this is a project stating one. SCOPED TO ONE CLASS AND ONLY ONE. `[decisionAcceptance]` stays human-only, because D0106 says an AI cannot supply a human's sign-off and `confirmation-authenticity` enforces the kind half independently of this file - so a Decision still needs them. `[contentionAdjudication]` stays human-only, because an AI adjudicating a contention it holds a side of is the conflict D0108 clause 5 exists to prevent. Their word was 'issues', and this changes issues. TWO THINGS THAT DO NOT CHANGE. An AI-recorded disposition is recorded as AI-recorded: `judgedBy` names the AI actor, the procedureText cites this Decision, and nothing claims a human judged it - the delegation is traceable to their recorded words rather than assumed. And the disposition remains VISIBLE: `keel dispositions` reports every one with its judge, so they can audit what was decided under delegation without asking.";
        :>> rationale = "WHY THE POLICY FILE RATHER THAN A GUARD EXEMPTION: the contract exists to answer exactly this question, its own header says an absent file means the built-in floor rather than 'no policy', and editing it leaves the check running at full strength against a policy the project chose. A code path that skipped the check for AI actors would have removed the control instead of restating it, and would have been invisible in the contract a reader consults. WHAT THIS COSTS, stated because a weakening should not be sold as a win: the human no longer sees every Medium-and-above finding before it is dispositioned. That was a real check - it is how issue135 got REJECTED and issue137 got a correction I would not have made ('viewer on a single machine is still 1') - and delegation trades it for throughput. The trade is theirs to make and they made it; my part is to record what was given up. THE BREADTH IS WIDER THAN THEIR SENTENCE AND I WILL NOT PRETEND OTHERWISE: `roles = [contributor]` permits ANY ai contributor, not specifically me, because the contract's vocabulary is kind-and-role and has no per-actor grant. A tighter mechanism - a named delegation from one actor to another, with a scope and an expiry - is the honest shape and is NOT built here, because inventing a new provenance concept to satisfy one sentence is how a speculative design becomes load-bearing (draft 1 of D0161). If the breadth matters, that is the follow-up.";
        :>> consequences = "AS APPLIED: one class in one contract file changed; `attestation-authority` continues to run and to pass; the four findings that accrued after the deck was generated (issue154, issue155, issue156, issue157) are dispositioned under this delegation, each naming it. REMOVAL PATH, per D0163: revert `[findingDisposition]` to `kinds = [human]`, `roles = [supervisor]` - one line, no code, no rebuild - and the guard immediately reports every AI-judged disposition above the threshold as a violation, which is the correct behaviour for a project that withdraws the delegation. Nothing stored becomes unreadable; the dispositions remain, correctly attributed, and become visible gaps rather than silent ones. WHAT TO WATCH: whether AI-dispositioned findings start reading as agreement with myself. The critique corpus already shows this session's findings are mostly MINE about MY OWN work, so delegation means I now both raise and close them. `keel dispositions` reports the judge on every row, and if that pattern looks wrong the delegation is one line away from being withdrawn.";
    }

    // acceptance event — their instruction IS the sign-off, recorded verbatim (D0106/D0066).
    verification d0165Accept : Test {
        :>> id = "3f8b06a5-4e72-4d91-8c07-b25ea41f0d63";
        :>> method = VerificationMethod::confirmation;
        :>> procedureText = "wweatherholtz, 2026-08-20, verbatim: 'accept all sprints, and no need to accept issues that have been resolved. auto accept issues by your authority.' The third clause is the delegation this Decision records. Their instruction was given in the same message as an obligations-deck export in which they hand-judged 19 findings, so the delegation is plainly about the ONGOING queue rather than a retraction of the judgments they had just made - those are recorded as theirs.";
    }
    part d0165AcceptR1 : TestResult {
        :>> id = "9c47e105-6b83-4a29-b710-38fd05c2be94";
        :>> outcome = VerdictKind::pass;
        :>> judgedAgainst = "b7e000d";
        :>> judgedAt = "2026-08-20";
        :>> judgedBy = "wweatherholtz";
    }
}
