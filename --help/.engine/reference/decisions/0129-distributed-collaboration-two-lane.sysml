// D0129 (PROPOSED — NOT YET ACCEPTED) — Operate keel as an asynchronous remote mostly-AI team:
// two-lane integration, ancestry-preserving merges, true provenance, claimed work, actor enrollment.
// Acceptance is a separate explicit human gate (method=confirmation, D0106): flip status + add the
// d0129Accept event on sign-off. On acceptance, d0014 (main-only/no-branches) becomes superseded.
// Marked #ProspectiveChange (D0070): work chartered under the prior process stays valid.
package Decision0129 {
    private import EngineElement::*;
    private import EngineWork::*;
    private import EngineVerification::*;
    private import EngineRelationships::*;

    #ProspectiveChange part d0129 : Decision {
        :>> id = "b58c7125-4d5c-4f0c-997f-dfbb17b0e0ee";
        :>> title = "D0129: distributed collaboration — two-lane integration, ancestry-preserving merge, true provenance, claimed work, actor enrollment";
        :>> createdAt = "2026-08-12";
        :>> createdBy = "claudeOpus5";
        :>> status = DecisionStatus::accepted;
        :>> context = "The human directed (2026-08-12) that keel will be operated within ~a week by an ASYNCHRONOUS REMOTE team that is nearly all AI: several agent sessions on different machines, supervised by different humans in different timezones, with no shared runtime and no shared database — the git remote is the only coordination medium. Every prior decision assumed a single agent on the human's own machine committing directly to main (d0014 states its scope explicitly: 'this solo+AI project'). A two-lane research pass (external prior-art + internal code audit, both 2026-08-12) established the following, each VERIFIED against code rather than inferred. (1) EXISTENTIAL — orient is machine-dependent under the current workflow: `done` requires a passing TestResult whose judgedAgainst SHA still RESOLVES (orient.rs:494-531, via git cat-file at orient.rs:123); post-commit pushes fire-and-forget and never fetch (.githooks/post-commit:8-9), so with several pushers rejection is constant and the natural remedy (pull --rebase) rewrites local SHAs; the rewriting machine still resolves them as loose objects and reports GREEN while every other clone reports invalidEvidence and re-lists finished work as ready. The remote today permits BOTH squash and rebase merge and main has NO branch protection. (2) SILENT CORRUPTION — two agents offline both mint the next decision number by directory scan (write.rs:929-942); different slugs mean different filenames, so git reports NO conflict, both land, and duplicate `package DecisionNNNN` declarations are silently merged (registry.rs:52-53). No guard among the seventeen detects a duplicate id or name. gen_uuid mixes only clock+PID+in-process counter with NO host component (write.rs:63-99). (3) FALSE PROVENANCE DEFEATS A SECURITY GUARD — seven serve.rs sites default author/judged_by to the human 'wweatherholtz' (304,331,357,384,409,483,1313), record decision does the same (main.rs:967), five paths default to the unregistered 'keel-cli' (main.rs:910,935,1121,1151); separately capture_user.py registers EVERY enrolled actor as `: Person` with no kind question, so an onboarding AI is registered as a human. Either path lets an AI satisfy confirmation-authenticity (D0106/issue059), which exists precisely to stop an AI fabricating human acceptance. (4) THE GATE EVAPORATES OFF THIS MACHINE — pre-commit hardcodes an absolute conda path and a Windows binary name (.githooks/pre-commit:17-21); elsewhere it either prints 'guards skipped' (pre-commit:66-68) or aborts .engine commits, teaching SKIP_VALIDATE=1; only pre-commit/post-commit are installed, so `git merge` (pre-merge-commit) is UNGATED — the conflict-resolution commits this workflow generates are the ones with no local check; .gitattributes normalizes only *.sh, leaving *.sysml at each machine's core.autocrlf mercy. (5) DUPLICATE WORK — the ready frontier is one global list with no owner or claim (orient.rs:33-45). (6) UNDECLARED GATE VOCABULARY — of the markers guards consume, only #View is declared: #Capability (15 files), #DerivedFrom (22), #Covers (6), #Dispositions (10), #ProcessDefect (5) exist nowhere as `metadata def`, yet #DerivedFrom is load-bearing for the hard-blocking requirement-rootedness guard (guards.rs:386-398); markers are not type-checked, so a misspelled marker validates CLEAN and silently blinds that guard. (7) D0108 ALREADY STATES THE RIGHT CONTRACT (owner-of-record, additive-only, supersede-don't-overwrite, human adjudicates) and is convention-only: absent from the seventeen guards (guards.rs:885-886) and the eight declared rules (rules.sysml:14-132), enforced by CLAUDE.md prose plus a reminder hook; and no command records an Issue at all, so the adjudication path D0108 mandates has no implementation.";
        :>> decision = "Adopt a distributed operating model, superseding d0014. (A) TWO-LANE INTEGRATION, routed by change class, not contributor discretion (the human's explicit choice of 2026-08-12 over PR-for-everything and direct-to-trunk-for-everything): RECORD/EXECUTE contributions — verification results, claims, ceremony gates, new items and typed edges — land on the trunk through a GATE-ON-MERGED-TREE loop (fetch, integrate trunk, run the FULL gate against the resulting tree, push; retry on rejection with bounded back-off), gated by the guards plus the per-sitting review; CHANGE contributions (schema, process, workflow, gate, rule, or the MEANING of a computed view) and deliverable source are proposed as a separately reviewable unit, gated by CI, reviewed by an actor OTHER than the author, carrying the human acceptance the change path already requires. (B) ANCESTRY-PRESERVING INTEGRATION IS MANDATORY: fast-forward or merge commit only; squash-merge, rebase-merge, history rewriting and force-push are disabled on the remote for shared refs and never performed locally on commits carrying recorded evidence. (C) HONEST EVIDENCE UNDER PARTIAL SYNC: computed views distinguish 'anchor absent from this clone' (unsynchronized) from 'anchor unresolvable' (invalid) and never count the former as work-not-done; orientation reports its own divergence from the remote. (D) PROVENANCE IS NEVER DEFAULTED: acting identity comes from an explicit per-machine binding or argument, write paths REFUSE when it is unstated, no default ever names a human or an unregistered actor, and actor KIND is stated explicitly at enrollment — never inferred, never Person-by-default. (E) WORK IS CLAIMED: a claim is an authored fact (actor, item, time, commit) whose liveness is COMPUTED, with mutual exclusion supplied by the remote accepting exactly one of two concurrent claims, and stale claims expiring to release the claim but never the recorded facts. (F) CONTENTION IS ADJUDICATED, NOT PRECEDENCE-RESOLVED: conflicting conclusions are recorded as a tracked Issue in one sanctioned step and resolved by a recorded human adjudication. (G) TWO NEW PROCESSES, each with its deploying skill (D0059): actor ENROLLMENT (identity, kind, role, registration, machine binding, gate verification) — distinct from and prior to the existing `introduction` process, which onboards a fresh PROJECT rather than establishing WHO is acting — and DISTRIBUTED COLLABORATION (sync, claim, work, land, escalate, close). (H) THE GATE BECOMES PORTABLE AND HONEST: no machine-specific paths, probe for the toolchain, cover merge commits, declare text normalization in the repository, and FAIL LOUDLY rather than passing silently when a check cannot run. SEQUENCE: the five mechanical day-one items (ancestry-preserving config + hooks, duplicate-identity guard, collision-resistant ids, identity binding, portable gate) land first because without them the team corrupts the model in week one; claiming, the landing loop, enrollment, the adjudication path and the authority queue follow.";
        :>> rationale = "The through-line is that keel is ALREADY well-positioned and every gap sits in one place. The hard architectural calls are right: UUID identity means records can be sharded across files with no semantic consequence; results are append-only by construction (write.rs:351); the temporal clock is git ancestry, so timezones are already a non-issue (D0013); and compute-don't-store means there is no shared mutable state to lock — which is exactly what sank the lock-server MBSE tools (Teamwork Cloud-class products still lose writes across surfaces). D0108 already states the correct coordination contract. So this is NOT a distributed-architecture redesign; it is MECHANIZING a doctrine already accepted, which is D0047's own rule (manual vigilance is not a control) applied to D0108, and it is why the day-one set is small edits to existing code and config rather than new subsystems. On (B): this is a CONSEQUENCE of the evidence model, not a style preference — evidence anchored to a SHA cannot survive an integration step that mints new SHAs, and the resulting divergence is invisible (green locally, not-done everywhere else), which is the worst available failure for a system whose entire claim is that state is computed. Prior art agrees on the shape: Gerrit invented Change-Id precisely because SHAs die on rebase, git-notes needs notes.rewriteRef for the same reason. On (A) ALTERNATIVES: (i) PR-for-everything — REJECTED: hours of review latency in front of contributors recording dozens of atomic facts an hour, for no assurance the guards and the per-sitting review do not already give, and under that load review degrades into rubber-stamping, which launders unreviewed work as reviewed; (ii) direct-to-trunk-for-everything — REJECTED: abandons independent review exactly where AI failure concentrates and where one error reaches every contributor at once, and LLM judges measurably favour their own output, so an author's self-review is not review (the same principle already encoded as critic-independence, D0080); (iii) CHOSEN — route by change class, which cuts along the taxonomy the engine ALREADY routes by (CLAUDE.md 3), evidence the boundary is intrinsic rather than invented. Note this is routing over change classes and does NOT revive the per-skill API-enforced writePolicy that D0096 superseded. On (E): a claim is authored while its liveness is computed, so it fits CLAUDE.md 2.6 rather than excepting it; and git's non-fast-forward rejection IS a compare-and-swap (the --force-with-lease flag was originally spelled --cas), so mutual exclusion needs no lock server — the one coordination primitive available when the remote is the only shared medium turns out to be sufficient. On (D): provenance is not tidiness — it is the substrate every honesty guard reads, and a guard bypassable by an omitted parameter does not fail loudly, it quietly stops meaning anything. On the SEQUENCE: the ordering is by blast radius under concurrency (silent corruption and false attribution first, throughput second), and it deliberately defers the naming-scheme migration and any real merge queue until evidence warrants them (the retry-livelock threshold for append-mostly text repos is unmeasured; instrument it as an indicator rather than pre-building). CRITERIA: truthfulness-of-computed-state x honesty-of-attribution x least-new-machinery x friction-below-a-spreadsheet (D0054).";
        :>> consequences = "Records Needs nComputedStateMachineIndependent / nIntegrationEvidencePreserving / nProvenanceTrue / nConcurrentAuthoringSafe / nNoDuplicateWork / nUniformGate / nContentionVisible / nAsyncHumanOversight / nActorEnrollment / nAuthorityFollowsRecordedKind, three Personas (remoteAiContributor, asyncSupervisor, uninitiatedContributor) and thirteen UseCases in .tracking/business/distributed-collaboration.sysml, satisfied by twenty SystemRequirements in .tracking/requirements/distributed-collaboration-requirements.sysml. ON ACCEPTANCE d0014 flips to superseded (its main-only/no-branches model is replaced by two-lane integration; its rationale was explicitly solo-scoped). Adds two processes + two deploying skills (actor-enrollment, distributed-collaboration). Raises tracked Issues for each verified defect: the two confirmation-authenticity bypasses (defaulted actor; AI registered as Person), the missing duplicate-identity guard, the undeclared marker vocabulary, the non-portable and merge-blind local gate, and the unmechanized D0108 contract — each requiring a permanent guard per D0047, not a silent patch. REQUIRES a human-signed schema change LATER to link an actor to a Role (schema/core is frozen; `part def Role` currently has zero instances) — deliberately not bundled. DEPENDS ON keelReleaseProcess (D0128) for version parity: without published pinnable versions there is nothing for contributors to pin to. NOT ADOPTED here: a merge queue, a naming-scheme migration, and any second coordination store outside the model (forge discussion that never lands as model facts would be shadow truth, contra D0018). This Decision is PROPOSED; acceptance is a separate explicit human gate (D0106) and this AI has not recorded one.";
    }

    // d0129 supersedes d0014 (main-only / no-branches — a SOLO-scoped decision). The supersede
    // back-reference is computed; d0014's status flips to superseded ON ACCEPTANCE of this Decision.
    #Supersede dependency from d0129 to d0014;

    // acceptance event (D0121 review-queue sign-off; D0066/D0106 — human-judged, not fabricated)
    verification d0129Accept : Test { :>> id = "16097b74-7ddb-4864-957c-40d00b1bb3e7"; :>> method = VerificationMethod::confirmation; :>> procedureText = ""; }
    part d0129AcceptR1 : TestResult { :>> id = "4557ffb9-8dcb-4f4a-b40c-4e867859b5de"; :>> outcome = VerdictKind::pass; :>> judgedAgainst = "196dec4"; :>> judgedAt = "2026-08-13"; :>> judgedBy = "wweatherholtz"; }
}
