// D0140 — Supersedes D0139 clauses (E) and (G) ONLY. #Verify and #DerivedFrom are RETAINED with
// kernel-verified justification; the base-first rule itself is untouched and reaffirmed.
// #ProspectiveChange (D0070): work authored under D0139's reading stays valid.
package Decision0140 {
    private import EngineElement::*;
    private import EngineWork::*;
    private import EngineVerification::*;
    private import EngineRelationships::*;

    #ProspectiveChange part d0140 : Decision {
        :>> id = "8a4f2c7e-91d3-4b60-a5e8-3f7c018d64b2";
        :>> title = "D0140: #Verify and #DerivedFrom are justified last resorts, not unjustified dialect — D0139(E)/(G) superseded";
        :>> createdAt = "2026-08-14";
        :>> createdBy = "claudeOpus5";
        :>> status = DecisionStatus::accepted;
        :>> context = "D0139 clause (E) instructed migrating #Verify to base `verify` and #DerivedFrom to base derivation; clause (G) left the #DerivedFrom target to be measured. Both rested on an audit I performed with `keel check`, the PERMISSIVE rust parser, which is not a conformance oracle (issue097). A three-critic panel commissioned by the human — antagonist, protagonist, and a dispassionate technical-correctness critic, run as three independent contexts — reached UNANIMITY by three separate routes that clause (E) must not be executed. THE DECISIVE FACT (issue098), verified first-hand against the kernel: `objective r;` DECLARES a nested member and does NOT reference. `verification def V { subject s; objective zzz; }` with nothing named zzz PASSES, while the controls correctly FAIL — `part p : NoSuchTypeAnywhere` fails and `satisfy r by zzz3` fails with 'Couldn't resolve reference to Element'. So the kernel does resolve references and `objective` simply does not take one. The shape recorded since June 2026 at relationships.sysml:7-9 as 'the only valid verification shape', restated in the syntax notes and named as the migration target, IS NOT A RELATIONSHIP. Migrating onto it would have left all 456 verification links silently non-existent while BOTH toolchains reported clean — worse than the syntax error issue097 caught, because that form is valid and nothing would have failed. THE SCALE MAKES IT WORSE, not better: the reference-bearing forms (`objective :>> r`, `objective :> r`) require a REQUIREMENT-TYPED target, and 309 of 456 #Verify edges target `part Decision` (work.sysml:41), so even the working form cannot absorb 68% of them. THE #DerivedFrom HALF is closed by the repo's own recorded constraint rather than new evidence: all 37 edges run Decision/Story/UseCase -> Need, 37/37 CROSS-METACLASS, and element.sysml:48-53 already records under D0055 that cross-metaclass specialization is impossible. ALSO CORRECTED: my recorded control totals were inflated 35% by counting prose mentions as edges — 613/91/91 recorded against 456/37/42 actual (issue099).";
        :>> decision = "(A) D0139 clause (E) is SUPERSEDED: #Verify is NOT migrated. It is RETAINED as a justified last resort. (B) D0139 clause (G) is SUPERSEDED: #DerivedFrom is NOT migrated and is RETAINED on the same basis. (C) The recorded JUSTIFICATION is what changes their status, and it is now on file, kernel-verified: for #Verify, no base construct expresses a verification-to-target link — `objective` declares rather than references, no standalone `verify` form parses, and 68% of the edges target a metaclass that cannot be a requirement objective; for #DerivedFrom, every edge is cross-metaclass and `:>` cannot cross metaclasses. (D) D0139's BASE-FIRST RULE (clauses A, B, C, F) is UNTOUCHED AND REAFFIRMED. This Decision is the rule operating correctly, not an exception to it: clause (B) requires a custom marker to carry a recorded justification naming the base constructs considered and why each fails, and these two markers now have exactly that. They cease to be unjustified dialect and become documented last resorts. (E) D0139 clause (D) — process-to-controls via `assert constraint` — STANDS, kernel-confirmed valid, and remains scheduled. (F) The corrected control totals are 456 (#Verify), 37 (#DerivedFrom), 42 (#DependsOn), and future censuses are COMPUTED rather than grepped (dcMarkerCensusView), because a corpus containing prose about itself inflates its own count. (G) NO MIGRATION of any marker proceeds until keel-parser can READ the target construct: the lexer tokenizes 22 keywords and knows nothing of `port`, `connect`, `constraint`, `assert`, `metadata`, `occurrence`, `item`, `objective` or `subject`, and `skip_item` discards silently, so a conversion landing first would make ~1,500 edges parse clean and vanish while five hard guards reported green. (H) relationships.sysml:7-12 and the syntax notes are corrected so neither presents the objective shape as an edge.";
        :>> rationale = "The base-first rule was right and the two migrations it named were wrong, and it matters that those are separate claims. A rule that says 'prefer base constructs, and justify any custom one' is vindicated when a custom construct turns out to be justified — that is the rule discriminating correctly, which is the whole point of having it rather than a blanket preference. What would have been indefensible is executing a migration BECAUSE a rule pointed that way, after the evidence for the target had collapsed. THE DEEPER LESSON, and the reason this Decision exists rather than a quiet backlog edit: 'valid syntax' and 'expresses the relationship' are different questions, and only the second one mattered. The June spike tested the first and its result was recorded as though it answered the second; I then repeated the same error in issue097's mechanism after correctly overturning its syntax claim. Any future claim that construct X can replace edge Y must demonstrate that X RESOLVES A REFERENCE to the target — tested with a deliberately undeclared name, which is the cheapest possible discriminator and would have caught this in June. ON THE HUMAN'S FRAMING, recorded because the record must not mislead: the acceptance characterises the direction as 'far too much bespoke metadata … let's rip it out', and this Decision RETAINS two markers with 493 edges between them. That is not a contradiction of their intent but it is a narrowing of it, and it was stated plainly before acceptance: the bespoke-instead-of-inherent problem is real and larger than the markers, but it lives in provenance carried as ~3000 untyped strings, Test-to-TestResult coupled by a name suffix, Process modelled as a part with behaviour in strings, and Rule predicates in string mini-languages — none of which are markers. ALTERNATIVES: (i) execute (E) as accepted — REJECTED, it destroys the verification spine silently, which is the one failure mode this project is built to prevent; (ii) migrate only the 147 requirement-targeting #Verify edges — REJECTED for now, it splits one relation across two mechanisms so every consumer must handle both, and the 68% remainder still needs the marker, so the custom surface does not shrink; revisit only if `Decision` is ever remodelled; (iii) remodel `Decision` as a requirement to make objectives applicable — REJECTED, a Decision is not a requirement, and bending a correct metaclass to fit a migration inverts the priority; (iv) CHOSEN.";
        :>> consequences = "D0139(E) and (G) are superseded; (A)(B)(C)(D)(F) of D0139 stand. dcMigrateVerifyToBase and dcMigrateDerivedFromToBase are superseded as work items — they instructed a harmful change and must not be executed. issue098 and issue099 resolve. relationships.sysml:7-12 corrected (it is in frozen schema/core, so this carries the §2.5 sign-off via the human's acceptance of this Decision); sysmlv2-syntax-notes.md gains the DECLARES-vs-REFERENCES distinction and the undeclared-name discriminator, so the next author can settle the question in one kernel cell. The three panel spikes (`_spike_objective_binding.py`, `_spike_objective_ref.py`, `_spike_objective_targets.py`) plus `_spike_base_algebra.py` are committed, so every claim here is reproducible on a clean clone — the gap the panel flagged as item 12. Marker inventory unchanged at 17. The custom surface does not shrink through this Decision; it shrinks through the items D0139(D) and the leanness sweep cover, which is where the human's concern actually applies. Acceptance state is carried by `status` plus the d0140Accept event.";
    }

    // The two migration items instructed a change that would silently delete 493 edges. Superseded, so
    // resolution stays COMPUTED — never a prose "cancelled" note (§1.4, D0077).
    #Supersede dependency from d0140 to dcMigrateVerifyToBase;
    #Supersede dependency from d0140 to dcMigrateDerivedFromToBase;

    verification d0140Accept : Test { :>> id = "6c3e8a41-7d92-4f05-b8c6-1e02947fd3a8"; :>> title = "Human acceptance of d0140"; :>> createdAt = "2026-08-14"; :>> createdBy = "claudeOpus5"; :>> method = VerificationMethod::confirmation; :>> procedureText = "wweatherholtz, 2026-08-14, verbatim: 'absolutely accept. This is exactly the smell I've been smelling, along witht he solution. Far too much bespoke metadata instead of relying on real inherent conenction types in sysmlv2. Let's rip it out. Proceed through all, with my implicit acceptance. I'll review properly once the whole pass is finished. Great work so far.' SCOPE OF THIS ATTESTATION, stated precisely so it is not read as more than it is: this is a PASS-LEVEL acceptance covering the panel's verdict and the work it authorises, given after being shown the unanimous finding, the kernel evidence, and the explicit statement that #Verify and #DerivedFrom are RETAINED rather than removed. It is NOT a per-clause attestation of each Decision authored during the pass, and the human said they will review properly once the pass is finished. The tension between 'let's rip it out' and this Decision's retention of two markers was raised BEFORE acceptance, not after."; }
    part d0140AcceptR1 : TestResult { :>> id = "f19b7d20-4c63-4e8a-9051-2ad836be7c94"; :>> outcome = VerdictKind::pass; :>> judgedAgainst = "ec7d548"; :>> judgedAt = "2026-08-14"; :>> judgedBy = "wweatherholtz"; }
}
