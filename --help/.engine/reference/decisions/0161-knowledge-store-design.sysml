// D0161 — PROPOSED, FOURTH DRAFT. The human asked whether a feature can be UPDATED and UNPLUGGED after
// implementation. Updating was already covered; unplugging was not, for any feature in this engine. So
// rollback is now part of the design and part of its acceptance test.
//
// Draft history, kept because the pattern is the point: draft 1 designed a store for ingesting external
// documents and the human called it low value. Draft 2 redesigned it as a retrieval index over the
// existing model — and silently contradicted three of the eight steps of D0153's ACCEPTED process, which
// they found by asking whether creating the knowledge graph could be a process. Draft 3 amended the
// process instead, making the corpus a parameter. Draft 4 adds the removal path. Every one of the four
// was coherent on its own and wrong in relation to something else, and every correction came from a
// one-line question rather than from my own review.
// #ProspectiveChange (D0070): amends an accepted process definition and names its store location.
package Decision0161 {
    private import EngineElement::*;
    private import EngineWork::*;
    private import EngineVerification::*;
    private import EngineRelationships::*;

    #ProspectiveChange part d0161 : Decision {
        :>> id = "b8407e15-3c69-4d2a-9016-5ea7f3c04b9d";
        :>> title = "D0161: `knowledgeGraphMemory` v2 — the corpus becomes a PARAMETER, `.knowledge/` is the store location D0153 never named, and the feature is REMOVABLE by construction";
        :>> createdAt = "2026-08-18";
        :>> createdBy = "claudeOpus5";
        :>> status = DecisionStatus::accepted;
        :>> context = "THREE DRAFTS, AND EACH TIME THE HUMAN'S ONE-LINE QUESTION FOUND THE DEFECT. Draft 1 designed `.knowledge/` as a store for ingesting EXTERNAL documents — a third model with its own schema, computed identity and a JSONL corpus — and they said 'hmm. low value?'. Draft 2 redesigned it as a RETRIEVAL INDEX over the model that already exists, which was right about the target: keel's own reasoning is already authored, measured at 162 Decisions each carrying both context and rationale, 67 Need statements, 88 SystemRequirement rationales, 144 Issue descriptions, and 1540 typed edges, with the traversal half already built and shipping. THEN THEY ASKED WHETHER CREATING THE KNOWLEDGE GRAPH COULD BE A PROCESS, EXPECTING IT TO CHANGE GOING FORWARD. IT ALREADY IS ONE, and has been since D0153 was accepted: `.engine/processes/knowledge-graph-memory.sysml` declares an eight-step Process with a registered skill at `.engine/skills/knowledge-graph-memory/SKILL.md`, and the hard `process-skill` guard keeps the two bound. WHICH MEANS DRAFT 2 HAD A DEFECT I HAD NOT SEEN: its out-of-scope clause put 'ingesting external documents' and 'recall injection into the harness prompt path' outside the design, and those are not out-of-scope items — they are STEP 4 AND STEP 6 OF AN ACCEPTED PROCESS. Draft 2 therefore proposed a store that three of the eight steps could not produce, while claiming to implement the Decision that specifies them. A design may amend a process; it may not quietly disagree with one.";
        :>> decision = "PROPOSED, TWO PARTS, ONE ACCEPTANCE. PART 1 — AMEND THE PROCESS, `knowledgeGraphMemory` v2. THE CORPUS BECOMES A DECLARED PARAMETER with two cases, because the eight-step spine is correct for both and only the populate step actually differs. (a) A DOCUMENT CORPUS: step 4 extracts against the closed vocabulary and identity is COMPUTED from type plus normalised name, exactly as D0153 fixed it, because re-extraction must converge with no matching service. (b) AN ALREADY-TYPED MODEL: there is nothing to extract, so step 4 BINDS instead — entities are the existing items, relations are the existing typed edges, and identity is the minted UUID those items already carry. Step 3 changes with it: 'one table per fact shape' becomes 'bind each fact shape to the corpus's existing type, or declare a table for it where none exists'. Step 6 (injection into the harness prompt path) becomes TIER-CONDITIONAL rather than mandatory: a corpus the human queries directly needs a command, not a prompt hook, and requiring the hook made a CLI-only capability read as unfinished. STEPS 1, 2, 7 AND 8 ARE UNCHANGED AND ARE THE REASON TO VERSION RATHER THAN FORK: questions before vocabulary before anything, the closed ontology, the deliberate multi-hop trap, and the recorded failure axes are identical for both corpora. PART 2 — NAME THE STORE, which D0153 specifies and never locates. `.knowledge/questions/*.sysml` holds declared Question items; `.knowledge/lexicon/*.sysml` holds declared Alias items mapping the words a human uses to the elements that answer them. Both SysML, both human-owned, so the marker, attribute-vocabulary and edge-endpoint guards already apply. For keel's own corpus the model IS the graph: no entities, relations or answer text are stored. TWO COMPUTED VIEWS, never authored: `keel why <term>` (seed on names, displayLabels and aliases; traverse; return the reasoning with provenance AND with any FAILING critique against what it reached) and `keel knowledge question-coverage` (for each declared Question, whether seeding finds an entity and traversal reaches an answer). ACCEPTANCE IS STEP 7's OWN TRAP TEST, unchanged: a declared question whose answer requires chaining elements that share no words. PART 3 - THE FEATURE MUST BE REMOVABLE, AND THE REMOVAL MUST BE TESTED. The human asked how this gets unplugged if they dislike it once built, and the engine had no answer for any feature, so this Decision supplies one at three levels. (i) DATA LEVEL, needing no switch and no code path: the feature's entire input is human-authored Questions and Aliases under `.knowledge/`. Delete them and `keel why` has no seeds and question-coverage has no questions, so both report NOTHING DECLARED and the gate stays green. A feature whose only input is authored facts is unplugged by removing the facts, which is the cheapest rollback available and the reason to prefer this shape over one with machine-extracted state. (ii) PROCESS LEVEL: `knowledgeGraphMemory` asserts no constraint today, so `keel deactivate knowledge-graph-memory` correctly refuses it (issue149) - it is not switchable. This Decision gives the process an `assert constraint` on its question-coverage control, which makes it a UNIT and therefore deactivatable like agile-workflow or doc-sync, with `keel activation` reporting it. That is the difference between a process that happens to be unused and one the project has DECLARED it does not run (D0138). (iii) COMMAND LEVEL: removing `keel why` itself is an ordinary §3a CHANGE with doc-sync riding along, stated here so it is not left implicit. ACCEPTANCE THEREFORE HAS A SECOND CLAUSE: the rollback is EXERCISED, not described - delete `.knowledge/`, show both commands reporting nothing declared, show 36 guards still green, and show `keel deactivate knowledge-graph-memory` succeeding and `keel activation` reporting it INACTIVE.";
        :>> rationale = "WHY VERSION ONE PROCESS RATHER THAN DECLARE A SECOND: forking would duplicate six of eight steps, and a duplicated step is dual truth — the thing §1 and D0105 exist to prevent. It would also cost a second registered skill under the `process-skill` guard, so the fork is not even cheaper. The corpus is the only real variable, so it belongs in the process as a parameter, and the process keeps one home. WHY THIS ANSWERS THE HUMAN'S ACTUAL CONCERN, which was that this will change: making it a process is not paperwork here, it is the mechanism. A process change is marked `#ProspectiveChange` or `#SafetyChange` on its Decision, which makes that Decision a VERSION BOUNDARY the engine already computes against — `keel governing-version <item>` reports which version governed any recorded piece of work, and `keel reprocess-candidates` computes what needs redoing when a change is flagged safety-relevant, while issue068 guarantees work correct under an older version is never retro-failed. So the next change to how the graph is built is a CR that bumps a version, and every answer already recorded stays attributable to the version that produced it. THAT PROPERTY IS WORTH MORE HERE THAN ANYWHERE ELSE, because a knowledge index is judged by its answers and an answer is only as good as the method that built it. WHY THE ANSWER MUST CARRY ITS CRITIQUES: this session recorded 201 critique results, 127 of them failing, several against the very rationale fields `keel why` would return. Returning that prose as settled truth would launder findings the model already holds. THE HONEST LIMIT: this makes the corpus ANSWERABLE, not CORRECT. `keel why` faithfully returns what was written, including what was written badly.";
        :>> consequences = "IF ACCEPTED: an amended process definition (purpose plus steps 3, 4 and 6), a doc-sync obligation on the bound skill in the SAME commit, a small directory with two human-owned item types, and two computed views. NO new model, NO schema/core change, NO exception to any invariant, and /api/scope untouched — draft 1 needed two invariant exceptions and this needs none, for the same stated purpose. THE DOCUMENT-CORPUS BRANCH IS NOT OUT OF SCOPE, it is the other case of the same parameter, unbuilt here because keel's own corpus is already typed; a downstream project with documents runs branch (a) of the same process without a second Decision, which is the whole point of parameterising rather than forking. THE LEXICON BECOMES A MAINTAINED ARTIFACT: an alias pointing at a superseded element must be reported rather than silently answered, which the existing supersede edges make computable. IF REJECTED: the reasoning stays in 162 files retrievable by grep, AND D0153's process keeps three steps that can only be run against a corpus this repository does not have — so a rejection should say whether the process is amended anyway, because that defect exists independently of whether `.knowledge/` is ever built. EXPLICITLY DEFERRED, not out of scope: recall injection into the harness prompt-submit path (step 6, tier-conditional and not needed for a CLI capability) and any tier-2 or tier-3 store. WHAT THE ROLLBACK CLAUSE COSTS AND WHY IT IS WORTH IT: giving the process an asserted constraint means its guard is now switchable, so a project that deactivates it also stops the question-coverage check - which is correct, since a project not running the process should not be measured against it, and is exactly what D0138 means by adoption being declared rather than inferred. THE GENERAL GAP THIS EXPOSES, larger than this Decision and not fixed by it: no feature in this engine states its removal path, and the only reason this one now does is that the human asked. That belongs in the decision-authoring process as a required clause rather than as a habit, and it is recorded as such rather than left to me to remember.";
    }

    // acceptance event (D0121 review-queue sign-off; D0066/D0106 — human-judged, not fabricated)
    verification d0161Accept : Test { :>> id = "9d4fbec8-8b89-4159-ae51-4f5883260aec"; :>> method = VerificationMethod::confirmation; :>> procedureText = "ACCEPT - submitted in the obligations deck review of 2026-08-20 (verdict recorded with no per-item note)"; }
    part d0161AcceptR1 : TestResult { :>> id = "fa17959c-362c-438e-a74d-f70529920536"; :>> outcome = VerdictKind::pass; :>> judgedAgainst = "b7e000d"; :>> judgedAt = "2026-08-20"; :>> judgedBy = "wweatherholtz"; }
}
