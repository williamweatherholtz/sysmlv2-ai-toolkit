// D0133 — Every metadata marker a guard or view consumes is DECLARED, and validation REJECTS an
// undeclared or misspelled marker. A frozen-schema change (§2.5), signed off 2026-08-13.
// Marked #ProspectiveChange (D0070): items authored under the prior arrangement stay valid.
package Decision0133 {
    private import EngineElement::*;
    private import EngineWork::*;
    private import EngineVerification::*;
    private import EngineRelationships::*;

    #ProspectiveChange part d0133 : Decision {
        :>> id = "c7a0e35b-9d84-4b12-8f6a-30e91d7cb452";
        :>> title = "D0133: declare the guard-consumed marker vocabulary and reject undeclared markers";
        :>> createdAt = "2026-08-13";
        :>> createdBy = "claudeOpus5";
        :>> status = DecisionStatus::accepted;
        :>> context = "issue077. The engine's typed-edge algebra is expressed partly through metadata markers (`#Verify dependency from a to b;`), and guards plus computed views key on them — but the markers were never DECLARED and were never type-checked. Measured 2026-08-13 across every marker used in a real syntactic position: `#Verify` 456 uses, `#CharteredBy` 260, `#Resolves` 93, `#DependsOn` 44, `#DerivedFrom` 37, `#ProspectiveChange` 30, `#Dispositions` 21, `#ProcessDefect` 18, `#Measures` 12, `#Supersede` 11, `#Informs` 11, `#JustifiedBy` 8, `#Capability` 7, `#View` 5, `#Covers` 4 — while the DECLARED set was only eight (CharteredBy, DependsOn, OrderingOnly, ProspectiveChange, Resolves, SafetyChange, Supersede, View). NINE real markers were undeclared, including the two most load-bearing: `#Verify`, which tier-satisfaction, sr_verified_pct and the verification-trace guard all key on, and `#DerivedFrom`, which the HARD requirement-rootedness guard keys on. CONSEQUENCE: because markers were not checked, a MISSPELLED marker validated clean and silently removed that item from whatever control depended on it — and a blind guard reports PASS, not a violation. Verified by negative test rather than argued: replacing one `#DerivedFrom` with `#DerivdFrom` left `keel validate` reporting '277 tracking file(s) validated clean' while requirement-rootedness silently lost sight of that edge. A typo in `#Verify` would report a DELIVERED requirement as unverified — the same wrong-picture failure as issue082, arriving by a different route. This scales badly with contributor count (D0129): any contributor's slip disables a control for that item with no signal to anyone, including in review.";
        :>> decision = "(A) DECLARE the nine missing markers in `.engine/schema/core/relationships.sysml`, each with a comment naming what it links and which control consumes it: Verify, DerivedFrom, Capability, Dispositions, Covers, ProcessDefect, Measures, Informs, JustifiedBy. (B) ENFORCE with a new HARD guard `marker-vocabulary` (23 guards; 18 hard + 5 warning-only): every marker used in a real syntactic position must be declared, or the commit fails. Hard rather than warning because the check is exact set-membership against declared names, not a heuristic — there is no legitimate ambiguity for it to mis-call, unlike the prose-matching guards which are deliberately warning-level. (C) The scan STRIPS SysML string literals before looking, because `procedureText` fields legitimately discuss markers (`#Marker dependency from a to b`, `#Kind dependency`, `#Changes dependency`); without that, those three prose examples alone would produce nine false violations on a hard gate. Comment lines are skipped for the same reason. (D) The declared-marker set is read from the SCHEMA (`metadata def` lines in `.engine/schema` and `.engine/workflows`), not hardcoded in Rust, so a downstream project declaring its own markers is checked against its own vocabulary.";
        :>> rationale = "The engine already treats undeclared vocabulary as a defect elsewhere — `keel check-engine` rejects an unresolved TYPE reference, and the actors guard rejects an unregistered actor id — so markers were the one naming axis with no referential integrity at all, and it happened to be the axis the guards themselves depend on. That is the worst place for the gap: a wrong type name fails loudly, whereas a wrong marker name fails SILENTLY and takes a control with it. ALTERNATIVES: (i) warning-level first, per the D0102 promote-once-low-noise pattern — REJECTED here because that pattern exists for HEURISTICS, and this check is exact; a warning would also leave the silent-blinding window open, which is the entire harm; (ii) teach the parser to model `metadata def` and validate markers inside `keel validate` — a cleaner long-term home and left open, but it means parser + registry changes for a check a text scan performs exactly today, and D0112's direction is to move checks OUT of heavyweight layers, not in; (iii) drop the marker idiom for native edges — REJECTED, the pilot grammar has no native form for these relations, which is why the marker idiom exists (see the syntax notes); (iv) CHOSEN — declare + enforce exactly, with string-literal stripping as the one necessary subtlety. FROZEN-SCHEMA JUSTIFICATION: this edits schema/core, which is frozen, and was signed off explicitly (declaredMarkersSchemaSignOff, 2026-08-13); the change is purely ADDITIVE — nine declarations, no existing type touched — so nothing authored under the prior arrangement becomes invalid.";
        :>> consequences = "Adds nine `metadata def` declarations to `.engine/schema/core/relationships.sysml` and the `marker-vocabulary` hard guard, taking the enforced set to 23 (18 hard + 5 warning-only). issue077 resolves. A misspelled marker now fails the commit with the file, line and the offending name instead of silently blinding a control. The declared set is schema-sourced, so downstream projects that declare their own markers are checked against their own vocabulary rather than keel's. CLAUDE.md §5 is doc-synced; the guard-list prose was also de-brittled, replacing the ordinal chain ('A SEVENTEENTH guard…') that had to be renumbered on every addition and would otherwise drift. NOT ADOPTED: moving marker validation into the parser/registry — a cleaner eventual home, recorded as open rather than done. Acceptance state is carried by `status` plus the d0133Accept event and is not restated here.";
    }

    verification d0133Accept : Test { :>> id = "0e2d6a19-4c7f-4b83-9a15-8d6e2f04b7c1"; :>> title = "Human acceptance of d0133 (frozen-schema change)"; :>> createdAt = "2026-08-13"; :>> createdBy = "claudeOpus5"; :>> method = VerificationMethod::confirmation; :>> procedureText = "wweatherholtz authorized this FROZEN-SCHEMA change (§2.5) and accepts d0133. The authorization is recorded in full as declaredMarkersSchemaSignOff (.tracking/sittings/sitting03-review.sysml), attested 2026-08-13 with 'accept on all counts' in response to an enumerated list whose FIRST named item was this frozen-schema sign-off; the scope authorized there names the same nine markers declared here (#Verify, #DerivedFrom, #Capability, #Dispositions, #Covers, #ProcessDefect, plus #Measures/#Informs/#JustifiedBy found by the complete scan) and the same risk accepted: that markers were untyped, so a misspelling validated clean and silently blinded the depending control."; }
    part d0133AcceptR1 : TestResult { :>> id = "5f83b0c4-2e71-4d69-b0af-1c94e7a52d38"; :>> outcome = VerdictKind::pass; :>> judgedAgainst = "8df2822"; :>> judgedAt = "2026-08-13"; :>> judgedBy = "wweatherholtz"; }
}
