// D0145 — Complete D0142's sweep: delete the hollow risk.sysml and the orphaned RiskLevel enum.
// A FROZEN-CORE change (§1.5) carrying explicit human sign-off.
// #ProspectiveChange (D0070): work chartered under the prior schema stays valid.
package Decision0145 {
    private import EngineElement::*;
    private import EngineWork::*;
    private import EngineVerification::*;
    private import EngineRelationships::*;

    #ProspectiveChange part d0145 : Decision {
        :>> id = "b41f7c28-5d90-4e13-a6c2-7f0b3e594182";
        :>> title = "D0145: delete the dead risk schema D0142 left behind";
        :>> createdAt = "2026-08-15";
        :>> createdBy = "claudeOpus5";
        :>> status = DecisionStatus::accepted;
        :>> context = "FOUND while deriving `keel migrate`'s removal set from the schema diff, which required enumerating exactly what D0142's leanness sweep deleted. The sweep removed `Risk`, `Mitigation` and `DesignElement` and left four pieces of residue in and around its own commit. (1) `.engine/schema/core/risk.sysml` was HOLLOW: its file header and package `doc` string still described `Risk`, `Mitigation` and the relationship between them — 'a Risk is reduced by a Mitigation; a materialized Risk becomes an Issue' — while all three types were gone, and its only remaining content was `enum def RiskStatus`, referenced by nothing. (2) `RiskLevel` in `element.sysml` was orphaned identically, its only consumers having been `Risk`'s likelihood/impact/residual attributes. (3) `architecture.sysml`'s header comment still listed `DesignElement`. (4) `sysmlv2-syntax-notes.md` still listed `EngineRisk` among the packages to import. THE PATTERN IS THE ONE D0144 EXISTS FOR, one layer down: the sweep removed each type and corrected the consumer in front of it without enumerating the rest. This is the second such miss found inside D0142's own work — the first was the four stale `query.py` citations retired in sprint 279 — and dead schema described by prose that contradicts it is worse than either alone, because a reader trusts frozen core more than any other surface. Recorded as issue108, and deliberately NOT bundled into the migration-tool sprint that found it: a `schema/core` deletion belongs in its own sprint with its own gate rather than riding in unexamined.";
        :>> decision = "(A) DELETE `.engine/schema/core/risk.sysml` entirely, and delete `enum def RiskLevel` from `element.sysml`. (B) Correct `architecture.sysml`'s header to stop naming `DesignElement`, and `sysmlv2-syntax-notes.md` to stop listing `EngineRisk` as importable. (C) Delist `risk.sysml` from all three python schema lists (`_schema_files.py`, `validate_all.py`, `validate_workflows.py`) in the same change, since a preload list naming a deleted file fails loudly and correctly. (D) `keel migrate` gains a `REMOVED_ENUMS` blocker for `RiskLevel` — and deliberately NOT for `RiskStatus`, which is the asymmetry a downstream project cannot see from outside: `RiskLevel` lived in `element.sysml`, which the engine SHIPS and `engine-resync` OVERWRITES, so a project assigning `RiskLevel::high` breaks the moment it migrates; `RiskStatus` lived in `risk.sysml`, which the engine no longer ships at all, and resync never deletes a file it does not ship, so a project that has it simply keeps it and blocking would refuse a migration over a type the project still owns.";
        :>> rationale = "This does not extend D0142, it COMPLETES it. D0142's accepted decision was to remove dead schema, under the repo's own recorded rule at rules.sysml:63-66 — `OrderingRule` was removed with the explicit instruction 're-add it THEN, with an instance'. `RiskStatus` and `RiskLevel` are exactly that: enums with no def to serve and no instance to justify them. Leaving them is the state the panel's finding (b) named as worse than having no rule, because a rule the project wrote for itself and then stopped applying is still cited as if enforced. VERIFIED BEFORE DELETING, not after: zero references to `RiskLevel`, `RiskStatus` or `EngineRisk` anywhere in `.tracking` or `.engine` outside the historical records that describe the residue itself. ALTERNATIVES: (i) keep the enums and fix only the misleading prose — REJECTED by the human, and correctly, since it leaves dead schema the repo's own rule says to remove; (ii) restore `Risk` and `Mitigation` with a real instance, treating a risk register as wanted — a legitimate option the human was offered and declined, and one that remains available at any time under the same 're-add it THEN' rule; (iii) CHOSEN. THE KERNEL WAS RUN, non-negotiably: the last two schema deletions in this pass each broke a reference the Rust validator accepted (`#View item def ICD` and the `Release` retarget), so `validate_schema.py` was run against the change and returned 15/15, and the conformance lane returned 473/473 with no construct rejected.";
        :>> consequences = "`schema/core` loses one file and one enum. Marked #ProspectiveChange (D0070): work chartered under the prior schema stays valid, since nothing referenced either name. DOWNSTREAM: a project migrating past this vintage is BLOCKED with advice if it assigns `RiskLevel::`, and is untouched if it uses `RiskStatus::` — see (D). This is the first change to honour the rule that each conversion sprint contributes its own migration step while it still knows what it changed; from outside, both enums look identically deleted, and only the sprint making the change knows they are not.";
    }

    verification d0145Accept : Test { :>> id = "9c3a5e71-2b48-4f06-8d1e-6a90b74c2f53"; :>> title = "Human acceptance of d0145 (frozen-core sign-off, §1.5)"; :>> createdAt = "2026-08-15"; :>> createdBy = "claudeOpus5"; :>> method = VerificationMethod::confirmation; :>> procedureText = "wweatherholtz, 2026-08-15. Asked explicitly whether to delete the dead risk schema, and given the alternatives inline: keep the enums and fix only the docs, or restore Risk/Mitigation with a real instance. The question stated exactly what would be deleted (risk.sysml, RiskLevel), the two doc corrections, and the verification that neither name is referenced anywhere. Selected: 'Delete the dead schema'. This is the frozen-core sign-off §1.5 requires, given on this specific change rather than inferred from a standing instruction to proceed."; }
    part d0145AcceptR1 : TestResult { :>> id = "e7d20a94-8c61-4b3f-95a7-1f8e0c4d6b27"; :>> outcome = VerdictKind::pass; :>> judgedAgainst = "29bceaa"; :>> judgedAt = "2026-08-15"; :>> judgedBy = "wweatherholtz"; }
}
