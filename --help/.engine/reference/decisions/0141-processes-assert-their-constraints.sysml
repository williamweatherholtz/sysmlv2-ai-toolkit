// D0141 — The six process definitions now ASSERT the constraints they enforce, and process-units.toml
// is retired. The process-def change record D0070's keystone lock requires.
// #ProspectiveChange (D0070): work chartered under the prior process text stays valid.
package Decision0141 {
    private import EngineElement::*;
    private import EngineWork::*;
    private import EngineVerification::*;
    private import EngineRelationships::*;

    #ProspectiveChange part d0141 : Decision {
        :>> id = "2f7c9a35-6b81-4e04-93da-5c18e7b02f96";
        :>> title = "D0141: process definitions assert their own constraints; process-units.toml retired";
        :>> createdAt = "2026-08-14";
        :>> createdBy = "claudeOpus5";
        :>> status = DecisionStatus::accepted;
        :>> context = "D0139 clause (D) — accepted, and reaffirmed by D0140 — directs that process-to-controls move from `.engine/contracts/process-units.toml` into the model as base SysML v2 `assert constraint`. Applying it CHANGES SIX PROCESS DEFINITION FILES, which D0070's keystone hard lock requires be recorded as a process-change Decision in the same commit. This Decision is that record. It is an APPLICATION of an already-accepted direction, not a new one: nothing here decides anything D0139(D) did not already decide. The guard caught the omission on the first commit attempt, which is the lock doing precisely its job — I had treated the change as a code refactor and it is also a process-definition edit.";
        :>> decision = "(A) Each of the six process files gains `assert constraint <member> : <ConstraintDef>;` on the PART that enforces the control — ceremony and sprint-coverage on `standupGate`, retro-backlog on `retroTrack`, priority-inversion and verification-trace on `refineLink`, the five decision-authoring controls on `decisionAuthoring`, and one each on `issueResolution`, `elementCritique`, `renderView`, `docSync`. Fourteen asserts, matching the fourteen process-bound guards exactly. (B) `.engine/rules/guard-constraints.sysml` declares each as a `constraint def`, named in the camelCase form of the guard name. (C) `.engine/contracts/process-units.toml` is DELETED with no tombstone. (D) A process unit remains keyed by FILE; its guards are the UNION of asserts across the parts in that file.";
        :>> rationale = "Attaching each assert to the step that enforces it, rather than to a file-level list, was forced by the model and turned out better than the thing it replaced: `agile-workflow.sysml` holds 21 Process/ProcessStep parts and NO single root Process, so there was nowhere for a file-level assert to live. The result says which phase carries which control, which the TOML could not express at all. The conversion is behaviour-preserving, demonstrated rather than argued: `keel activation` output is byte-identical before and after (6 units, same guard counts), and all four D0138 safety properties were re-run on a fresh `keel init` project — including the adversarial `active = []`, which still hard-fails on a duplicate id, so core-guard immunity survives. One property got STRONGER: a typo in a constraint name is now an unresolved constraint TYPE caught by `check-engine`, where under the TOML a misspelled guard name was caught only because a guard happened to check a name list. That is D0139's portability argument made concrete — the model itself refuses the error. ALTERNATIVES: (i) keep the TOML and document the preference — REJECTED by D0139 already, and the typo result shows the model check is not merely tidier but stronger; (ii) invent a root `Process` part per file to carry a file-level assert — REJECTED, it would add a part that models nothing in order to preserve the TOML's flat shape; (iii) key units by part name rather than file — REJECTED, it would change the `keel activate <name>` interface for no gain.";
        :>> consequences = "Six process definitions changed; `.engine/rules/guard-constraints.sysml` added; process-units.toml deleted. `activation.rs` reads units from the model via `units_from_model`, and three of its tests were rewritten off the TOML fixture with a fourth added to pin the camel-to-kebab rule the mapping now depends on. Doc-sync: the activation module header, a dead-reference error message, and guards.md's adoption section. Marked #ProspectiveChange (D0070) so work chartered under the prior process text stays valid — no sprint is invalidated, since the asserts add enforcement metadata and change no step's actionText, trigger or produced artifact. Acceptance is carried by `status` plus the d0141Accept event, whose scope is stated there precisely.";
    }

    verification d0141Accept : Test { :>> id = "5b0e2c74-8a19-4f3d-b26c-07e4915ad8f1"; :>> title = "Human acceptance of d0141"; :>> createdAt = "2026-08-14"; :>> createdBy = "claudeOpus5"; :>> method = VerificationMethod::confirmation; :>> procedureText = "Covered by wweatherholtz's PASS-LEVEL acceptance of 2026-08-14, verbatim: 'absolutely accept. This is exactly the smell I've been smelling, along witht he solution. Far too much bespoke metadata instead of relying on real inherent conenction types in sysmlv2. Let's rip it out. Proceed through all, with my implicit acceptance. I'll review properly once the whole pass is finished.' SCOPE, stated so this is not read as more than it is: this Decision DECIDES NOTHING NEW. It records the process-definition edit that applying the already-accepted D0139(D) necessarily makes, because D0070's keystone lock requires a co-committed process-change Decision for any such edit. The direction was accepted twice over — in D0139 with its own attestation, and again in the pass-level acceptance quoted here. The human stated they will review the whole pass when it is finished."; }
    part d0141AcceptR1 : TestResult { :>> id = "c8a63f19-2740-4e5b-95d8-1b0fe27c34a2"; :>> outcome = VerdictKind::pass; :>> judgedAgainst = "5b1aea4"; :>> judgedAt = "2026-08-14"; :>> judgedBy = "wweatherholtz"; }
}
