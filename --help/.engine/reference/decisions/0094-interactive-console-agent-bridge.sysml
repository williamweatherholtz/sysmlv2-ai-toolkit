// =====================================================================
// D0094 — interactive console + agent-bridge: `sysmlv2 serve` (tokio+axum, localhost), the human's
// ACTING surface (extends D0093's read/oversight lens). Three tiers, built straight through, ONE truth
// (read via the view computations, write only via the write API — never a second store): (1) a live
// READ console (recent decisions/processes/test-results + orient/reports/graph + a read-only AI<->user
// INTERACTION-HISTORY view rendering the Claude Code session transcripts, linked to the decisions they
// produced); (2) DETERMINISTIC actions (report/render/disposition); (3) an AGENT-BRIDGE that spawns
// Claude Code headless (`claude -p --output-format stream-json`) and STREAMS its work to the UI over
// SSE — critique a process, investigate a finding, draft a report. The agent runs under the engine's
// EXISTING discipline (skills + write API + guards + >=Medium human-disposition); the permission policy
// does NOT change because the surface changed; the UI exposes obvious review/override hooks.
// Accepted 2026-06-23 by wweatherholtz ("Accept, tweak something" -> interaction-history + Keel naming
// folded -> "that was the tweak. proceed").
// =====================================================================
package Decision0094 {
    private import EngineElement::*;
    private import EngineWork::*;
    private import EngineVerification::*;
    private import EngineRelationships::*;

    // D0070: introduces the acting-surface doctrine + new server capability (prospective; built via milestones).
    #ProspectiveChange part d0094 : Decision {
        :>> id = "94a5b6c7-1d6e-4f70-a829-516273849594";
        :>> title = "D0094: interactive console + agent-bridge (`sysmlv2 serve`; the human's acting surface)";
        :>> createdAt = "2026-06-23";
        :>> createdBy = "wweatherholtz";
        :>> status = DecisionStatus::accepted;
        :>> context = "D0093 gave the human a READ/oversight HTML lens but DEFERRED in-browser action + authoring ('option C, revisit'). This is that revisit, expanded: an interactive console (`sysmlv2 serve`) to (a) surface decision-CONTEXT + improvement-INSIGHT at a glance — recent decisions (rationale/alternatives), processes-in-use, test results, AND a full AI<->user INTERACTION HISTORY — and (b) ACT on the model, crucially DRIVING THE AGENT ('critique this process', 'investigate the merits of a low-value critique', 'draft a new report'). A claude-code-guide investigation CONFIRMED Claude Code is drivable headless from a server (`claude -p --output-format stream-json --include-partial-messages`): live event streaming (NOT polling), scoped tool allowlists, loads CLAUDE.md (setting_sources=project), resumable sessions, per-invocation cost (total_cost_usd). The interaction transcripts already exist on disk (~/.claude/projects/<cwd>/*.jsonl).";
        :>> decision = "Build `sysmlv2 serve` — a LOCALHOST interactive console (tokio + axum), ONE truth (read via the view computations; write ONLY via the write API; never a second store), three tiers built STRAIGHT THROUGH. (1) READ CONSOLE: live computed views — recent decisions (context/rationale/alternatives), processes-in-use, test results, the orient dashboard, reports, the model graph; PLUS a read-only AI<->user INTERACTION-HISTORY view that RENDERS the Claude Code session transcripts (~/.claude/projects/<cwd>/*.jsonl) cross-LINKED to the commits/decisions they produced — NOT copied into .tracking (transcripts are Claude Code's artifact; the console is a lens, compute-don't-store, section-2.1). SSE-live. (2) DETERMINISTIC ACTIONS: instantiate a report, render a view, record a disposition (server -> `sysmlv2` / the write API). (3) AGENT-BRIDGE: UI actions spawn Claude Code headless (`claude -p --output-format stream-json`), STREAMING the agent's work to the UI over SSE. The agent runs under the engine's EXISTING DISCIPLINE — the same skills, write API, guards, and the >=Medium-human-disposition rule (D0079/D0092); the PERMISSION POLICY DOES NOT CHANGE because the surface changed (human directive). The UI exposes OBVIOUS REVIEW/OVERRIDE hooks (see the agent's work, accept/finding/override via apply-review, re-run); the agent does NOT auto-commit — commits + acceptance stay the human's explicit gate (D0016). serveAgentBridge sets a per-action cost/turn CAP + a concurrency limit. AUTH (human directive): the agent-bridge pipes to the LOCALLY-AUTHENTICATED `claude` CLI — the user's Claude subscription / ENTERPRISE session — and MUST NOT set ANTHROPIC_API_KEY (setting it overrides the subscription and forces pricier per-token API-rate billing). The CLI is an OPTIONAL runtime dep; tiers 1-2 degrade gracefully without it.";
        :>> rationale = "The dual-surface invariant (D0093) HOLDS + EXTENDS: CLI = authority/automation (AI), HTML = the human's lens — now an ACTING lens (read + deterministic + agent-launch) — still ONE truth (write API + guards), the agent still disciplined, the human still supervises/overrides; authoring stays the AI's (the human triggers + reviews, never hand-authors .sysml). ALTERNATIVES: (A CHOSEN) tokio+axum console + agent-bridge via the `claude` CLI stream-json (human-chosen runtime + the research-confirmed mechanism). (B) read-only console — REJECTED (the human wants to ACT + drive the agent). (C) hand-rolled sync server — REJECTED by the human (async makes SSE/subprocess streaming far easier; the dep is acceptable for a TOOLING layer, not the authority/parser). (D) Python/TS Agent SDK server with an ANTHROPIC_API_KEY — REJECTED (human directive): stay Rust-native AND avoid API billing; an API key OVERRIDES the subscription + meters per-token at pricier API rates (Opus ~$5/$25 per M), whereas piping to the locally-authenticated `claude` CLI uses the user's ENTERPRISE seat. Shell out to the CLI; never set ANTHROPIC_API_KEY. (E) a special restricted UI permission sandbox — REJECTED by the human ('we don't need to change our permissions policy because we're changing the UI'): same discipline regardless of surface + obvious review/override hooks. SECURITY: localhost-only bind; agent writes go through the guards + the >=Medium human-disposition gate; the agent never auto-commits; per-action cost/turn cap; cost metered (stream-json total_cost_usd). CRITERIA: one-truth(no second store) x agent-stays-disciplined x human-supervises+overrides x Rust-native x streaming-not-polling x stepwise-shippable.";
        :>> consequences = "NEW workspace dependencies: tokio + axum (the serve binary path only). The locally-authenticated `claude` CLI is an OPTIONAL runtime dep for the agent-bridge (tier 3) — it uses the user's Claude subscription/enterprise session; the server MUST NOT set ANTHROPIC_API_KEY (that forces API-rate billing). NOTE: Anthropic's billing for headless `claude -p` is IN FLUX (a June-2026 move to a separate API-rate Agent-SDK credit pool was announced then PAUSED; there is a history of `claude -p` mis-billing as API) — so the per-action cost CAP + the no-API-key rule are the guardrails, and the auth path is revisited if Anthropic's policy settles differently. Milestones (backlog, chartered by d0094, built STRAIGHT THROUGH): serveReadConsole (tokio/axum localhost server + an embedded self-contained frontend [include_str!, the cytoscape precedent] + the live read console incl. the interaction-history view; SSE-live) -> serveActions (deterministic report/render/disposition via the server) -> serveAgentBridge (UI -> `claude -p` stream-json -> SSE; critique/investigate/draft; review+override via apply-review; per-action cost/turn cap + concurrency limit; no auto-commit). doc-sync per milestone: CLAUDE.md (the ACTING-surface extension of the dual-surface invariant, section 2), usage.md (`serve`), the viewpoint registry (a console viewpoint). This makes the engine a SELF-IMPROVEMENT COCKPIT: decision-context + disciplined agent work (critique/investigate/augment) + review/override, at a glance. Pairs with the engine's name (Keel, D0095).";
    }

    verification d0094Accept : Test { :>> id = "94a5b6c7-1d6e-4f70-b829-516273849594"; :>> method = VerificationMethod::confirmation; :>> procedureText = "wweatherholtz attests acceptance of d0094 (interactive console + agent-bridge: `sysmlv2 serve` tokio+axum localhost, three tiers — read console incl. a read-only interaction-history view linked to decisions, deterministic actions, and an agent-bridge that streams headless Claude Code to the UI via SSE under the engine's existing discipline with review/override hooks; one truth; no auto-commit; localhost-only) by selecting 'Accept, tweak something' then folding the interaction-history view + the Keel naming and saying 'that was the tweak. proceed' on 2026-06-23."; }
    part d0094AcceptR1 : TestResult { :>> id = "94a5b6c7-1d6e-4f70-c829-516273849594"; :>> outcome = VerdictKind::pass; :>> judgedAgainst = "6e8bb7a"; :>> judgedAt = "2026-06-23"; :>> judgedBy = "wweatherholtz"; }
}
