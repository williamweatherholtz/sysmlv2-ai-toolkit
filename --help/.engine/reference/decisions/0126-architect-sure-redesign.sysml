// D0126 (PROPOSED — NOT YET ACCEPTED) — Architect Sure — viewer redesign: drafting-register identity, browse-first discovery, computed displayLabel
// Recorded via `keel record decision` (D0105 RMWX axis; issue054). Acceptance is a separate explicit
// human gate (method=confirmation, D0106): flip status + add the d0126Accept event on sign-off.
package Decision0126 {
    private import EngineElement::*;
    private import EngineWork::*;
    private import EngineVerification::*;
    private import EngineRelationships::*;

    part d0126 : Decision {
        :>> id = "a76acbcc-413a-4fa9-998f-067499e5bf9b";
        :>> title = "Architect Sure — viewer redesign: drafting-register identity, browse-first discovery, computed displayLabel";
        :>> createdAt = "2026-07-16";
        :>> createdBy = "wweatherholtz";
        :>> status = DecisionStatus::accepted;
        :>> context = "A live run of the viewer surfaced three concrete human-factors failures: (1) the Focus box demands a SysML identifier the user cannot know before exploring, forcing a detour into keel's own architecture just to find a starting element — there is NO browse/discover path and NO endpoint listing all items; (2) the UI is saturated with parenthetical process noise ('(N-18)', '(D0124)', 'uses keel's...') that labels for the system, not the user; (3) elements render by their raw 'name' identifier, not a human display name — even though 'title' is an authored attribute on every element (1872 titles) and 'displayLabel' is a schema-DECLARED computed view (element.sysml §2.3) that was never actually built. /api/slice already returns title; the viewer ignores it. The user requested a frontend-design/human-factors pass and named the product 'Architect Sure'. The 'Drafting register' visual direction was chosen from three previewed options.";
        :>> decision = "Redesign the viewer as 'Architect Sure' on the 'Drafting register' identity (systems-engineering blueprint instrument: deep slate-blue drafting ground, curated per-type hue palette replacing the name-hash colours, hairline rules, IBM Plex Sans/Mono + Space Grotesk headlines). THREE substantive changes beyond aesthetics: (a) BROWSE-FIRST DISCOVERY — a left 'register' rail lists all substantive items (excludes the ~5000 Test/TestResult verification items by default) by display name, filterable by type-chip + text + date; backed by a new computed keel endpoint /api/index; you never type an identifier to start (serves nViewerExplorableGraph + nViewerTemporalState/srViewerDatePredicates). (b) DISPLAYLABEL — build the long-declared computed displayLabel view (title if authored, else name; type-aware) in keel and surface it on every endpoint + label everything by it; backfill titles where missing. NO new stored field (title stays authored, displayLabel stays computed, §2.3). (c) TEXT CULL — remove process-parenthetical noise from the primary surface; rationale moves to hover/info; secondary tools (encode/critique/in-program-edit) move behind progressive disclosure so the default view is the model, not a control panel.";
        :>> rationale = "Authoring/usage friction is the #1 risk (D0054); a viewer you must already know the model to use inverts its purpose. Browse-first + display names attack that directly. displayLabel is not new scope — it is a declared view we owe (§2.3); implementing it is completing the architecture, not extending it. Excluding Test/TestResult from the register keeps discovery about the architecture, not verification bookkeeping (they remain reachable via their parent's detail). The typed-hue palette replaces name-hashing that produced meaningless random colours. Recording this as one governing Decision charters the follow-on delivery sprints (keel index+displayLabel, then the viewer redesign) and keeps the work rooted (D0064 decision-driven) rather than freelanced.";
        :>> consequences = "Downstream (create then): keel — a displayLabel computation surfaced on item/slice/index; a new /api/index computed view (substantive items, with displayLabel/type/date). Viewer — new register rail + filters, typed palette, Plex/Space-Grotesk type, detail sheet by title, text cull, progressive disclosure of secondary tools, 'Architect Sure' brand. Risk: /api/index over a large model must stay fast (exclude Tests, cache per-fingerprint like other views). Titleless substantive items get flagged for backfill. This is proposed; acceptance + per-sitting review remain the human gate.";
    }

    // acceptance event (D0121 review-queue sign-off; D0066/D0106 — human-judged, not fabricated)
    verification d0126Accept : Test { :>> id = "c0ed1535-f73e-4c49-97bd-d3c12938fdcb"; :>> method = VerificationMethod::confirmation; :>> procedureText = "rationale isn't because of usage friction, it's because this is simply the main use case and value case for this software. So, it kind of is friction-related, but it can't be measured as 'friction' imo if a feasible workflow isn't even present"; }
    part d0126AcceptR1 : TestResult { :>> id = "2d4f3c63-fef9-4d8b-a93a-9578505b21c4"; :>> outcome = VerdictKind::pass; :>> judgedAgainst = "9326a17"; :>> judgedAt = "2026-07-17"; :>> judgedBy = "wweatherholtz"; }
}
