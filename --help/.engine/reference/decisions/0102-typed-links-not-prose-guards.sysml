// =====================================================================
// D0102 — typed links, not prose: two D0047 corrections from the A2 critique campaign. (1) A Decision that
// governs/descopes a requirement must carry a TYPED edge to it, not name it only in prose (issue052: D0100
// descoped sr19's clustering but was sr19-linked only in prose, so the SR silently overclaimed) — a new
// `decision-requirement-link` guard (WARNING-level, human-chosen) flags an accepted Decision that names a
// Need/SystemRequirement in its text without a typed edge. (2) A finding's DISPOSITION must clear its
// target's critique-suspicion: critique_suspect flagged any element with a fail critique regardless of an
// ACCEPT-RISK/DISMISS disposition (d0098 stayed suspect after issue050 was accept-risk'd) — realized by a
// TYPED link from a finding Issue to its source critique (#DependsOn), so the disposition is traceable.
// Accepted 2026-06-25 by wweatherholtz (chose 'Warning first' + 'Yes — fix it too').
// =====================================================================
package Decision0102 {
    private import EngineElement::*;
    private import EngineWork::*;
    private import EngineVerification::*;
    private import EngineRelationships::*;

    part d0102 : Decision {
        :>> id = "02a1b0c1-4102-42a3-ab5c-516273849702";
        :>> title = "D0102: typed links not prose — decision-requirement-link guard (warning) + critique_suspect honors dispositions";
        :>> createdAt = "2026-06-25";
        :>> createdBy = "wweatherholtz";
        :>> status = DecisionStatus::accepted;
        :>> context = "The A2 critique campaign surfaced two instances of the same defect class — a governing/explanatory relationship recorded only in PROSE, not as a TYPED edge, so it is invisible to the computed views + can silently drift. (1) issue052: D0100 descoped sr19ServeWhiteboxBoundary's AI-clustering boundary mode, but named sr19 only in D0100's prose — no typed edge — so sr19 stayed marked verified while its statement overclaimed a capability that was deliberately not built; a reader of sr19 alone could not trace the descope. (2) The critique_suspect computation (D0086) flags any element whose critique's latest result is `fail`, with NO regard for the finding's DISPOSITION — so after issue050 (the d0098-correctness finding) was ACCEPT-RISK'd, d0098 stayed perpetually 'suspect', because the finding Issue is connected to its source critique only by prose, giving the computation no typed path from the fail critique to its accept-risk verdict. Per D0047, a recurrable defect found mid-work becomes a permanent automated control, not vigilance.";
        :>> decision = "(1) NEW `decision-requirement-link` guard (WARNING-level — human chose 'Warning first'): for each ACCEPTED Decision, scan its authored text (context/decision/rationale/consequences) for EXACT Need/SystemRequirement element names (token-boundary match, low false-positive); if the Decision names a requirement but has NO typed edge between them (satisfy/verify/allocate/dependency/:>/#DependsOn/#Supersede/#DerivedFrom/#Resolves/#CharteredBy), emit a WARNING (visible in `keel guard` every commit + a runnable list) — NOT a hard violation (it does not block the commit). Promotable to a hard honest-state gate once it proves low-noise on the real model. (2) `critique_suspect` (D0086) HONORS dispositions: a `fail` critique no longer induces suspicion on its target when its finding Issue is dispositioned ACCEPT-RISK or DISMISS — realized by a TYPED `#DependsOn` edge from the finding Issue to its source critique Test (`#DependsOn dependency from <issueNNN> to <critiqueTest>`), so the computation has a typed path from the fail critique -> finding -> disposition. The element-critique convention adds this link when a critique fails; issue050's link is backfilled. Both fixes embody the principle: a governing/derivation relationship between model elements is a TYPED EDGE, never prose-only.";
        :>> rationale = "ALTERNATIVES: (1a) hard-gate the decision-requirement link immediately — DEFERRED (the human chose warning-first; exact-name prose matching can false-positive on a contextual mention that does not govern, so prove precision before blocking). (1b) leave it to vigilance / the doc-sync skill — REJECTED (D0047: vigilance is not a control). (2a) clear critique_suspect by appending a passing re-critique after accept-risk — REJECTED (DISHONEST: the issue is real + consciously accepted, not fixed; a pass would claim it is gone). (2b) match finding-to-critique by prose (issue title/description names the element) — REJECTED (fragile + it is the very prose-not-typed antipattern this decision corrects). (2c) CHOSEN — a typed #DependsOn finding->critique edge + critique_suspect honors accept-risk/dismiss through it. CRITERIA: honesty (never fake a pass; surface real state) x typed-not-prose (computable + driftless) x friction (warning-first, no flood) x D0047 (automated control, not vigilance).";
        :>> consequences = "New WARNING guard `decision-requirement-link` (run within `keel guard`; emits warnings, 0 violations — non-blocking) + `keel decision-links` runnable list (via view::decision_requirement_prose_links). critique_suspect_set updated to skip a fail critique whose finding Issue (#DependsOn-linked to the critique) is dispositioned accept-risk/dismiss; issue050 backfilled with `#DependsOn issue050 -> d0098CorrectnessCritique` -> d0098 clears critique_suspect. The element-critique skill convention: when a critique fails + raises a finding Issue, add the typed #DependsOn issue->critique link. Applying the new warning guard surfaces existing prose-only decision->requirement references (a burndown). doc-sync: CLAUDE.md §5 (the new warning guard + critique_suspect honoring dispositions) + the element-critique skill (the finding->critique link convention). No change to the honest-state HARD gate set (the link guard is a warning), so no hard-gate semantics shift; critique_suspect is a non-gating burndown signal, so honoring dispositions refines a diagnostic, not a commit gate.";
    }

    verification d0102Accept : Test { :>> id = "02a1b0c1-4102-42a3-bb5c-516273849702"; :>> method = VerificationMethod::confirmation; :>> procedureText = "wweatherholtz attests acceptance of d0102 (a decision-requirement-link WARNING guard flagging prose-only decision->requirement references; critique_suspect honoring accept-risk/dismiss dispositions via a typed finding->critique #DependsOn link) via the explicit choices 'Warning first' + 'Yes — fix it too' on 2026-06-25, after issue052 + the d0098 critique_suspect quirk surfaced the prose-not-typed defect class."; }
    part d0102AcceptR1 : TestResult { :>> id = "02a1b0c1-4102-42a3-cb5c-516273849702"; :>> outcome = VerdictKind::pass; :>> judgedAgainst = "9864d5f"; :>> judgedAt = "2026-06-25"; :>> judgedBy = "wweatherholtz"; }
}
