// CLI COMMAND FACTS (D0271) - every dispatched verb and every `show` lens as an authored fact, so
// 'these are variations of one idea' is queryable (family), 'a status command must not write' is testable
// (effect), and a rename can be a declared state (stability). Deferred by D0271 until the lens ruling,
// ruled by D0273, unauthored until issue344. THE HOME: keel --help renders from the Rust mirror
// (cli_facts.rs) and guard `cli-surface-declared` holds that mirror and the dispatch equal to THIS file
// both ways, so a fact added here without a dispatch arm, or an arm without a fact, is a violation.
package EngineCliFacts {
    private import EngineElement::*;
    private import EngineCli::*;

    // ---- governance ----
    part cliAccept : CliCommand { :>> id = "e7c41499-b231-4539-95aa-1f289a725824"; :>> title = "keel accept"; :>> createdAt = "2026-09-02"; :>> createdBy = "claudeOpus5"; :>> name = "accept"; :>> family = "governance"; :>> effect = CliEffect::writes; :>> stability = CliStability::stable; :>> invocation = "<decision> (--words TEXT | --note TEXT) --by <person> --date YYYY-MM-DD"; :>> synopsis = "record a human's acceptance of a proposed Decision; refused for an AI actor"; }
    part cliReject : CliCommand { :>> id = "e9cb7123-337b-417b-8444-9c27ef44d774"; :>> title = "keel reject"; :>> createdAt = "2026-09-08"; :>> createdBy = "claudeOpus5"; :>> name = "reject"; :>> family = "governance"; :>> effect = CliEffect::writes; :>> stability = CliStability::stable; :>> invocation = "<decision> (--words TEXT | --note TEXT) --by <person> --date YYYY-MM-DD"; :>> synopsis = "record a human's rejection of a proposed Decision; the same channel rules as accept"; }
    part cliJudgeSet : CliCommand { :>> id = "9fdf3e64-e575-47cb-9dc6-fbb8521f3fe3"; :>> title = "keel judge-set"; :>> createdAt = "2026-09-11"; :>> createdBy = "claudeOpus5"; :>> name = "judge-set"; :>> family = "governance"; :>> effect = CliEffect::writes; :>> stability = CliStability::stable; :>> invocation = "<.tracking file> (--words TEXT | --note TEXT) --by <person> --date YYYY-MM-DD [--verdict pass|fail] [--fail <test>,..] [--all]"; :>> synopsis = "record a human's verdict on the sampled proposed results of one file - one result and one quote receipt per item (D0443); accept's channel rules under confirmationRecord"; }
    part cliOverride : CliCommand { :>> id = "9d17e046-dc9d-4110-9047-f6c8d1e5b204"; :>> title = "keel override"; :>> createdAt = "2026-09-02"; :>> createdBy = "claudeOpus5"; :>> name = "override"; :>> family = "governance"; :>> effect = CliEffect::writes; :>> stability = CliStability::stable; :>> invocation = "<path> --reason TEXT"; :>> synopsis = "arm a single-use, path-bound write unlock; consuming it records an obligation"; }
    part cliClaim : CliCommand { :>> id = "3b658bed-ce59-40dd-a8e4-3acddaa64171"; :>> title = "keel claim"; :>> createdAt = "2026-09-02"; :>> createdBy = "claudeOpus5"; :>> name = "claim"; :>> family = "governance"; :>> effect = CliEffect::both; :>> stability = CliStability::stable; :>> invocation = "<item> | --list | --mine"; :>> synopsis = "take or inspect a work claim; liveness is computed"; }
    part cliEnroll : CliCommand { :>> id = "83157649-dbcd-4fc2-bd47-67f472dec65c"; :>> title = "keel enroll"; :>> createdAt = "2026-09-02"; :>> createdBy = "claudeOpus5"; :>> name = "enroll"; :>> family = "governance"; :>> effect = CliEffect::writes; :>> stability = CliStability::stable; :>> invocation = "--actor ID --name NAME --kind human|ai"; :>> synopsis = "enroll a contributor: register the actor, bind this machine, verify the gate"; }
    part cliActor : CliCommand { :>> id = "25d2487d-8ce4-4e23-bc8a-92cc7e7d92c7"; :>> title = "keel actor"; :>> createdAt = "2026-09-02"; :>> createdBy = "claudeOpus5"; :>> name = "actor"; :>> family = "governance"; :>> effect = CliEffect::both; :>> stability = CliStability::stable; :>> invocation = "[set <id>]"; :>> synopsis = "show the actor this session writes as, or bind one for this machine"; }
    part cliAdvance : CliCommand { :>> id = "2a915821-4adb-4d43-9362-26351f60d8f9"; :>> title = "keel advance"; :>> createdAt = "2026-09-02"; :>> createdBy = "claudeOpus5"; :>> name = "advance"; :>> family = "governance"; :>> effect = CliEffect::reads; :>> stability = CliStability::stable; :>> invocation = "<sprint|process> [--to GATE|step]"; :>> synopsis = "a sprint's current ceremony step, or any process's steps with each bound check's verdict; --to is refused while an earlier step's check is red (D0436)"; }
    // ---- authoring ----
    part cliRecord : CliCommand { :>> id = "b8ab4ef9-e178-47cf-9ce9-42f2e5dda9a5"; :>> title = "keel record"; :>> createdAt = "2026-09-02"; :>> createdBy = "claudeOpus5"; :>> name = "record"; :>> family = "authoring"; :>> effect = CliEffect::writes; :>> stability = CliStability::stable; :>> invocation = "decision|issue|statement|story ... | task --file F --def D --task T --method M --dod-from FILE | sprint <N> <slug> --charter <dNNNN> [--points P] [--fill FILE] | result --file F --task T --sha S [--verdict pass|fail] --judged-by A --judged-at D [--evidence TEXT] | gate-result --file F --gate G --sha S [--verdict pass|fail] --judged-by A --judged-at D [--evidence TEXT] | review --batch FILE [--sha S] [--judged-by A] [--judged-at D] | measurement --indicator I --value V [--at DATE] | indicator-snapshot [ROOT] | reverify [--all-drift | --task N | --demos] [--by A] | mint [N]"; :>> synopsis = "record one atomic fact, each sub-verb named for what it writes: a Decision, an Issue with its resolver, a human's words verbatim, the story translating them, a task with its Definition of Done, a sprint's ceremony scaffold (--fill never writes a result, D0301), a verdict on a task's DoD or a ceremony gate, a review batch as linked critiques, an indicator measurement or a dated snapshot, fresh gate results at HEAD where the gate is green (--demos replays replayable receipts, D0444); mint prints engine-minted v4 UUIDs and writes nothing"; }
    // ---- gating ----
    part cliGate : CliCommand { :>> id = "40e9364c-6859-4ecc-8a76-5f02275f9b13"; :>> title = "keel gate"; :>> createdAt = "2026-09-02"; :>> createdBy = "claudeOpus5"; :>> name = "gate"; :>> family = "gating"; :>> effect = CliEffect::reads; :>> stability = CliStability::stable; :>> invocation = "validate [ROOT] | check FILE... | --spec-version | check-engine [ROOT] | guard [NAME] [ROOT] | rules [--enforce] [ROOT] | assured [ROOT] | adoption-check [ROOT] [--unit N] [--keep] [--vintage VERSION] | --fast [ROOT] | --workspace [ROOT]"; :>> synopsis = "the gating family under one router (D0452): validate is the semantic authority over every .tracking file; check parses .sysml files or reports the baked grammar version; check-engine resolves .engine instance references kernel-free; guard runs every enforced honest-state guard or one by name; rules lists the declared rules and whether each holds; assured is the composite READY / NOT-READY verdict; adoption-check gates a foreign tree unit by unit; --fast is the per-edit tier and --workspace gates every project the commit touches (bare `keel gate` prints this usage)"; }
    part cliAudit : CliCommand { :>> id = "90e78705-9146-4347-b3aa-20d0345b0c6e"; :>> title = "keel audit"; :>> createdAt = "2026-09-02"; :>> createdBy = "claudeOpus5"; :>> name = "audit"; :>> family = "gating"; :>> effect = CliEffect::reads; :>> stability = CliStability::stable; :>> invocation = "history [--since REF] [--max N] | adherence [--since REF] | ci-runs [ROOT] [--repo OWNER/NAME] | [ROOT]"; :>> synopsis = "retrospective adherence: charter, ceremony, estimation, sitting review; history re-derives the gate verdict per commit over a range, adherence re-derives guard-set and severity monotonicity per commit so a control cannot be disarmed unsigned, ci-runs is the external-fact gate where every ci-run receipt names a real green run on the judged SHA (D0323)"; }
    part cliHook : CliCommand { :>> id = "af1e742a-a538-4698-acbf-61cb23d4b428"; :>> title = "keel hook"; :>> createdAt = "2026-09-02"; :>> createdBy = "claudeOpus5"; :>> name = "hook"; :>> family = "gating"; :>> effect = CliEffect::tooling; :>> stability = CliStability::internal; :>> invocation = "post-edit|stop|pre-bash|pre-write|subagent-stop|user-prompt|config-change"; :>> synopsis = "the in-loop gates the harness calls; not for a human to invoke"; }
    // ---- orientation: one router; its eleven former siblings are lenses below (D0450) ----
    part cliOrient : CliCommand { :>> id = "f75b33ee-25ec-4c84-be70-3624b045d24e"; :>> title = "keel show orient"; :>> createdAt = "2026-09-02"; :>> createdBy = "claudeOpus5"; :>> name = "orient"; :>> family = "lens"; :>> effect = CliEffect::reads; :>> stability = CliStability::stable; :>> invocation = "show orient [ROOT] [--html]"; :>> synopsis = "in-progress sprints, the ready and suspect frontier, the non-blocking burndown"; }
    part cliWhatsNext : CliCommand { :>> id = "c26440a5-e2d4-4069-9f5e-f6011f6eb483"; :>> title = "keel show whats-next"; :>> createdAt = "2026-09-02"; :>> createdBy = "claudeOpus5"; :>> name = "whats-next"; :>> family = "lens"; :>> effect = CliEffect::reads; :>> stability = CliStability::stable; :>> invocation = "show whats-next [ROOT]"; :>> synopsis = "the ready list in priority order - declaration order is priority"; }
    part cliStatus : CliCommand { :>> id = "17a4ebe1-d98c-4c9d-a5bc-6c9b686246e6"; :>> title = "keel show status"; :>> createdAt = "2026-09-02"; :>> createdBy = "claudeOpus5"; :>> name = "status"; :>> family = "lens"; :>> effect = CliEffect::reads; :>> stability = CliStability::stable; :>> invocation = "show status [ROOT]"; :>> synopsis = "every base in one screen: engine pin, library drift, model honesty, work, CI verdict for HEAD"; }
    part cliShow : CliCommand { :>> id = "2491288e-59fc-4ad6-bb1b-f70c4e6a79dd"; :>> title = "keel show"; :>> createdAt = "2026-09-02"; :>> createdBy = "claudeOpus5"; :>> name = "show"; :>> family = "orientation"; :>> effect = CliEffect::reads; :>> stability = CliStability::stable; :>> invocation = "<lens> [ROOT]"; :>> synopsis = "one computed lens by name; `show` alone lists them"; }
    part cliView : CliCommand { :>> id = "c13ce44c-0673-406d-a8ae-19a88e8741b8"; :>> title = "keel show view"; :>> createdAt = "2026-09-02"; :>> createdBy = "claudeOpus5"; :>> name = "view"; :>> family = "lens"; :>> effect = CliEffect::reads; :>> stability = CliStability::stable; :>> invocation = "show view <name> [ROOT]"; :>> synopsis = "render a declared TOML view as text"; }
    part cliItem : CliCommand { :>> id = "ae1e0d6b-6ad0-4043-97bf-a7d89894080f"; :>> title = "keel show item"; :>> createdAt = "2026-09-02"; :>> createdBy = "claudeOpus5"; :>> name = "item"; :>> family = "lens"; :>> effect = CliEffect::reads; :>> stability = CliStability::stable; :>> invocation = "show item <name> [ROOT]"; :>> synopsis = "one item with its attributes and edges"; }
    part cliArch : CliCommand { :>> id = "9500f139-9732-441f-8a90-1cc700ad8841"; :>> title = "keel show arch"; :>> createdAt = "2026-09-02"; :>> createdBy = "claudeOpus5"; :>> name = "arch"; :>> family = "lens"; :>> effect = CliEffect::reads; :>> stability = CliStability::stable; :>> invocation = "show arch elements|criticality|coupling|drift|stpa-inputs|coverage [ROOT]"; :>> synopsis = "architecture lenses over the code registry"; }
    part cliAttestation : CliCommand { :>> id = "2db70f1e-c22a-4b36-a6ea-b2a39cc7c638"; :>> title = "keel show attestation"; :>> createdAt = "2026-09-02"; :>> createdBy = "claudeOpus5"; :>> name = "attestation"; :>> family = "lens"; :>> effect = CliEffect::reads; :>> stability = CliStability::stable; :>> invocation = "show attestation [ROOT] [--json]"; :>> synopsis = "is a pass a receipt or a testimony: results by judge kind, receipts, fail rate"; }
    part cliActorTrace : CliCommand { :>> id = "8607fac9-7cdb-4a5c-84d7-79e3293d483e"; :>> title = "keel show actor-trace"; :>> createdAt = "2026-09-02"; :>> createdBy = "claudeOpus5"; :>> name = "actor-trace"; :>> family = "lens"; :>> effect = CliEffect::reads; :>> stability = CliStability::stable; :>> invocation = "show actor-trace <actor> [ROOT]"; :>> synopsis = "everything an actor authored, judged or owns"; }
    part cliGoverningVersion : CliCommand { :>> id = "51777d16-e7bd-434a-aa5e-8ddb64664818"; :>> title = "keel show governing-version"; :>> createdAt = "2026-09-02"; :>> createdBy = "claudeOpus5"; :>> name = "governing-version"; :>> family = "lens"; :>> effect = CliEffect::reads; :>> stability = CliStability::stable; :>> invocation = "show governing-version <item> [ROOT]"; :>> synopsis = "which process version governs an item"; }
    part cliReprocessCandidates : CliCommand { :>> id = "ca2ae269-a61c-40c3-a968-9bf508a44751"; :>> title = "keel show reprocess-candidates"; :>> createdAt = "2026-09-02"; :>> createdBy = "claudeOpus5"; :>> name = "reprocess-candidates"; :>> family = "lens"; :>> effect = CliEffect::reads; :>> stability = CliStability::stable; :>> invocation = "show reprocess-candidates [ROOT]"; :>> synopsis = "items whose governing process version has moved since they were judged"; }
    part cliEnforcementReport : CliCommand { :>> id = "bf728bae-dcbb-4134-b09b-34adac06fce2"; :>> title = "keel show enforcement-report"; :>> createdAt = "2026-09-02"; :>> createdBy = "claudeOpus5"; :>> name = "enforcement-report"; :>> family = "lens"; :>> effect = CliEffect::reads; :>> stability = CliStability::stable; :>> invocation = "show enforcement-report [ROOT]"; :>> synopsis = "fires, blocks, overrides and red-yields from the machine-local fire-ledger"; }
    // ---- rendering ----
    part cliRender : CliCommand { :>> id = "0a1ae892-8bff-44fd-ac58-3e88da818f82"; :>> title = "keel render"; :>> createdAt = "2026-09-02"; :>> createdBy = "claudeOpus5"; :>> name = "render"; :>> family = "rendering"; :>> effect = CliEffect::reads; :>> stability = CliStability::stable; :>> invocation = "<view>|model [--mode graph|table|review] | report <assurance|traceability|quality-debt|flow|governance|friction> [--html] [--trend] | decision-card [NAME] [--proposed]"; :>> synopsis = "everything that draws (D0449): a declared view or the whole-model graph as interactive HTML; a scorecard; a Decision's deciding context as JSON - the channel issue body"; }
    part cliDeck : CliCommand { :>> id = "a1ce1036-a8ab-403c-b4a5-6b992086b579"; :>> title = "keel deck"; :>> createdAt = "2026-09-02"; :>> createdBy = "claudeOpus5"; :>> name = "deck"; :>> family = "rendering"; :>> effect = CliEffect::both; :>> stability = CliStability::stable; :>> invocation = "[ROOT] [--out FILE]"; :>> synopsis = "the mobile obligation deck; saving writes through the API"; }
    part cliServe : CliCommand { :>> id = "4ba9decd-7b1a-4ae7-ba2e-166c8364ddf6"; :>> title = "keel serve"; :>> createdAt = "2026-09-02"; :>> createdBy = "claudeOpus5"; :>> name = "serve"; :>> family = "rendering"; :>> effect = CliEffect::both; :>> stability = CliStability::stable; :>> invocation = "[--port N] [ROOT]"; :>> synopsis = "the interactive console: lenses, approve queue, deck; wraps the write API"; }
    // ---- integration ----
    part cliInit : CliCommand { :>> id = "09f98e47-a5ac-451d-a018-b93f82ffe4cf"; :>> title = "keel init"; :>> createdAt = "2026-09-02"; :>> createdBy = "claudeOpus5"; :>> name = "init"; :>> family = "integration"; :>> effect = CliEffect::writes; :>> stability = CliStability::stable; :>> invocation = "DIR"; :>> synopsis = "scaffold the engine into a new project"; }
    part cliSync : CliCommand { :>> id = "58c2b8a5-7b73-4935-84ad-8a91e37823f7"; :>> title = "keel sync"; :>> createdAt = "2026-09-02"; :>> createdBy = "claudeOpus5"; :>> name = "sync"; :>> family = "integration"; :>> effect = CliEffect::both; :>> stability = CliStability::stable; :>> invocation = "[ROOT]"; :>> synopsis = "fetch, report divergence, integrate by merge, gate the result"; }
    part cliLand : CliCommand { :>> id = "eb260144-83ef-479f-a329-03a777473a6f"; :>> title = "keel land"; :>> createdAt = "2026-09-02"; :>> createdBy = "claudeOpus5"; :>> name = "land"; :>> family = "integration"; :>> effect = CliEffect::both; :>> stability = CliStability::stable; :>> invocation = "[ROOT]"; :>> synopsis = "gate every project, push; on rejection merge and gate the merged tree, then retry; refuses the push naming the paths whose working-copy line ending differs from their .gitattributes eol (issue478)"; }
    part cliMigrate : CliCommand { :>> id = "2940eeed-cb75-4b91-b295-99dc7ae3aeec"; :>> title = "keel migrate"; :>> createdAt = "2026-09-02"; :>> createdBy = "claudeOpus5"; :>> name = "migrate"; :>> family = "integration"; :>> effect = CliEffect::both; :>> stability = CliStability::stable; :>> invocation = "[ROOT] [--dry-run]"; :>> synopsis = "bring an existing project onto this binary's engine vintage, refusing and rolling back on failure"; }
    part cliClaude : CliCommand { :>> id = "ec150093-1b7f-401f-9b87-ff942c0fdf68"; :>> title = "keel claude"; :>> createdAt = "2026-09-03"; :>> createdBy = "claudeOpus5"; :>> name = "claude"; :>> family = "integration"; :>> effect = CliEffect::tooling; :>> stability = CliStability::stable; :>> invocation = "[claude args...]"; :>> synopsis = "launch Claude Code with the keel hooks pinned ON: the plugin rendering, disableAllHooks:false above project scope, KEEL_BIN = this binary (D0296)"; }
    part cliSyncClaude : CliCommand { :>> id = "b9970443-8887-49ce-98fc-714542cb3695"; :>> title = "keel sync-claude"; :>> createdAt = "2026-09-02"; :>> createdBy = "claudeOpus5"; :>> name = "sync-claude"; :>> family = "integration"; :>> effect = CliEffect::both; :>> stability = CliStability::stable; :>> invocation = "[ROOT] [--check]"; :>> synopsis = "regenerate the keel-owned .claude/ surface; --check reports drift only"; }
    part cliProjects : CliCommand { :>> id = "71838c0b-ca2f-4fe2-81e7-8211a7978bbc"; :>> title = "keel projects"; :>> createdAt = "2026-09-02"; :>> createdBy = "claudeOpus5"; :>> name = "projects"; :>> family = "integration"; :>> effect = CliEffect::reads; :>> stability = CliStability::stable; :>> invocation = "[ROOT] [--json]"; :>> synopsis = "every keel project in this repository, and which one you are in"; }
    part cliVersion : CliCommand { :>> id = "af68422e-9d42-48d6-ab29-e7b861cd01f9"; :>> title = "keel version"; :>> createdAt = "2026-09-02"; :>> createdBy = "claudeOpus5"; :>> name = "version"; :>> family = "integration"; :>> effect = CliEffect::tooling; :>> stability = CliStability::stable; :>> invocation = "[--json]  (also --version)"; :>> synopsis = "release version, build commit, guard inventory"; }
    // ---- distribution ----
    part cliProcess : CliCommand { :>> id = "892b60cf-442d-40db-b790-af05ea326a9f"; :>> title = "keel process"; :>> createdAt = "2026-09-02"; :>> createdBy = "claudeOpus5"; :>> name = "process"; :>> family = "distribution"; :>> effect = CliEffect::both; :>> stability = CliStability::stable; :>> invocation = "list|search|show|export|import|publish|retire|remove ..."; :>> synopsis = "the process catalogue: import, export or remove a unit"; }
    part cliLibrary : CliCommand { :>> id = "c42e167c-c9c9-4c55-ba85-8618732f2772"; :>> title = "keel library"; :>> createdAt = "2026-09-02"; :>> createdBy = "claudeOpus5"; :>> name = "library"; :>> family = "distribution"; :>> effect = CliEffect::both; :>> stability = CliStability::stable; :>> invocation = "init|sync|list"; :>> synopsis = "the machine-local cache of the portable-content repository"; }
    part cliOnboard : CliCommand { :>> id = "1a317df3-436c-4f39-8df8-1c083b93ea1a"; :>> title = "keel onboard"; :>> createdAt = "2026-09-02"; :>> createdBy = "claudeOpus5"; :>> name = "onboard"; :>> family = "distribution"; :>> effect = CliEffect::reads; :>> stability = CliStability::stable; :>> invocation = "[ROOT] [--json]"; :>> synopsis = "has this project chosen its processes, and on what basis"; }
    part cliActivation : CliCommand { :>> id = "b28e804f-b009-4ea8-b5e4-05f530c6e98e"; :>> title = "keel activation"; :>> createdAt = "2026-09-02"; :>> createdBy = "claudeOpus5"; :>> name = "activation"; :>> family = "distribution"; :>> effect = CliEffect::reads; :>> stability = CliStability::stable; :>> invocation = "[ROOT]"; :>> synopsis = "which processes and viewpoints this project has adopted"; }
    part cliActivate : CliCommand { :>> id = "40d44529-86f6-4af6-8b91-b2ac1b681e8b"; :>> title = "keel activate"; :>> createdAt = "2026-09-02"; :>> createdBy = "claudeOpus5"; :>> name = "activate"; :>> family = "distribution"; :>> effect = CliEffect::writes; :>> stability = CliStability::stable; :>> invocation = "<process|viewpoint> [ROOT]"; :>> synopsis = "adopt a process or viewpoint as a unit"; }
    part cliDeactivate : CliCommand { :>> id = "2507f615-e6ef-453c-ab68-49c15c3ffe48"; :>> title = "keel deactivate"; :>> createdAt = "2026-09-02"; :>> createdBy = "claudeOpus5"; :>> name = "deactivate"; :>> family = "distribution"; :>> effect = CliEffect::writes; :>> stability = CliStability::stable; :>> invocation = "<process|viewpoint> [ROOT]"; :>> synopsis = "drop a process or viewpoint as a unit"; }
    // ---- channel ----
    part cliGithub : CliCommand { :>> id = "3b7f2c91-5d64-4e0a-9f18-c2a6e7d40b53"; :>> title = "keel github"; :>> createdAt = "2026-09-12"; :>> createdBy = "claudeFable5"; :>> name = "github"; :>> family = "channel"; :>> effect = CliEffect::both; :>> stability = CliStability::stable; :>> invocation = "pull --repo O/N --by ACTOR --at DATE [--limit N] [--trust T] | ingest --repo O/N --issue N --by ACTOR --at DATE [--from FILE] | decider [<login>] | gesture (env: COMMENT_BODY ...) | decision-id <id>"; :>> synopsis = "the channel family under one router (D0453): pull ingests every open issue no Statement cites as a verbatim Statement, autonomy following repository visibility (D0264); ingest records one issue, idempotent on its URL; decider says who may decide on the channel, an unmapped login refused, never defaulted; gesture parses a channel comment into a JSON verdict; decision-id splits a channel decision id into project and name - decider, gesture and decision-id are deprecated with the channel workflow they served (D0289)"; }
    part cliSuite : CliCommand { :>> id = "4d1f8b2e-7c3a-4e9d-b5f6-2a8c0e1d3f57"; :>> title = "keel suite"; :>> createdAt = "2026-09-06"; :>> createdBy = "claudeOpus5"; :>> name = "suite"; :>> family = "gating"; :>> effect = CliEffect::both; :>> stability = CliStability::stable; :>> invocation = "[ROOT] [--touched] [-- <cargo test args>]"; :>> synopsis = "run the full suite and write the machine-local receipt of what it cost - a measurement, gating nothing (D0356); refuses from the image cargo relinks and records no verdict for a run that never reached a test (issue386); --touched runs only the integration tests that name a module changed since the base and writes its own receipt (D0421); --touched refuses to run, receipt outcome eol-mismatch, when a tracked path holds a line ending its .gitattributes eol does not declare (issue478)"; }
    part cliCurrency : CliCommand { :>> id = "c9d2e4f6-5a7b-4c8d-9e0f-1a2b3c4d5e6f"; :>> title = "keel currency"; :>> createdAt = "2026-09-05"; :>> createdBy = "claudeOpus5"; :>> name = "currency"; :>> family = "channel"; :>> effect = CliEffect::writes; :>> stability = CliStability::stable; :>> invocation = "[ROOT] --repo OWNER/NAME --by ACTOR [--at DATE] [--skip-pull]"; :>> synopsis = "the unattended currency pass: pull open issues as verbatim Statements, sync the library, read drift back - one report, never a triage (D0338)"; }
    // ---- knowledge ----
    part cliRecall : CliCommand { :>> id = "6c541a08-53c8-4d3e-961e-d7c3e3d12a9e"; :>> title = "keel recall"; :>> createdAt = "2026-09-02"; :>> createdBy = "claudeOpus5"; :>> name = "recall"; :>> family = "knowledge"; :>> effect = CliEffect::reads; :>> stability = CliStability::stable; :>> invocation = "--prompt -"; :>> synopsis = "seed recall from a prompt on stdin and print a budgeted brief; zero model calls"; }
    // ---- lens ----
    part cliAssumptions : CliCommand { :>> id = "683fd530-7705-418c-814e-071a1b352059"; :>> title = "keel assumptions"; :>> createdAt = "2026-09-02"; :>> createdBy = "claudeOpus5"; :>> name = "assumptions"; :>> family = "lens"; :>> effect = CliEffect::reads; :>> stability = CliStability::stable; :>> invocation = "show assumptions [ROOT]"; :>> synopsis = "accepted-but-unverified items something depends on"; }
    part cliAttestationCoverage : CliCommand { :>> id = "b09f1638-2654-49c7-8997-67e85b0ceccf"; :>> title = "keel attestation-coverage"; :>> createdAt = "2026-09-02"; :>> createdBy = "claudeOpus5"; :>> name = "attestation-coverage"; :>> family = "lens"; :>> effect = CliEffect::reads; :>> stability = CliStability::stable; :>> invocation = "show attestation-coverage [ROOT]"; :>> synopsis = "accepted Decisions lacking a passing acceptance result"; }
    part cliAuthorityQueue : CliCommand { :>> id = "e66bac4e-494e-42c9-82c7-0895f3bdbc88"; :>> title = "keel authority-queue"; :>> createdAt = "2026-09-02"; :>> createdBy = "claudeOpus5"; :>> name = "authority-queue"; :>> family = "lens"; :>> effect = CliEffect::reads; :>> stability = CliStability::stable; :>> invocation = "show authority-queue [ROOT]"; :>> synopsis = "what awaits a human's authority, and what may not be self-attested"; }
    part cliBoundary : CliCommand { :>> id = "ac5b0d17-b5e3-4369-a297-7cdd60c92828"; :>> title = "keel boundary"; :>> createdAt = "2026-09-02"; :>> createdBy = "claudeOpus5"; :>> name = "boundary"; :>> family = "lens"; :>> effect = CliEffect::reads; :>> stability = CliStability::stable; :>> invocation = "show boundary [ROOT]"; :>> synopsis = "one element's interface surface; takes an element"; }
    part cliBoundarySweep : CliCommand { :>> id = "96556c21-078f-477d-bd45-876eaeab51a6"; :>> title = "keel boundary-sweep"; :>> createdAt = "2026-09-02"; :>> createdBy = "claudeOpus5"; :>> name = "boundary-sweep"; :>> family = "lens"; :>> effect = CliEffect::reads; :>> stability = CliStability::stable; :>> invocation = "show boundary-sweep [ROOT]"; :>> synopsis = "tier-satisfaction white-box sweep, per Need slice"; }
    part cliBusiness : CliCommand { :>> id = "5a8cf38b-e5a5-4f1a-a605-0574479f3237"; :>> title = "keel business"; :>> createdAt = "2026-09-02"; :>> createdBy = "claudeOpus5"; :>> name = "business"; :>> family = "lens"; :>> effect = CliEffect::reads; :>> stability = CliStability::stable; :>> invocation = "show business [ROOT]"; :>> synopsis = "the what/why layer: Brief, Personas, Needs, UseCases"; }
    part cliConcernCoverage : CliCommand { :>> id = "4985df5e-ce21-4385-940d-57e5bbff0850"; :>> title = "keel concern-coverage"; :>> createdAt = "2026-09-02"; :>> createdBy = "claudeOpus5"; :>> name = "concern-coverage"; :>> family = "lens"; :>> effect = CliEffect::reads; :>> stability = CliStability::stable; :>> invocation = "show concern-coverage [ROOT]"; :>> synopsis = "declared viewpoints against stakeholder concerns - which concerns nothing serves"; }
    part cliContentions : CliCommand { :>> id = "01279b6f-34c7-420b-b0ad-a8bdd0a65a95"; :>> title = "keel contentions"; :>> createdAt = "2026-09-02"; :>> createdBy = "claudeOpus5"; :>> name = "contentions"; :>> family = "lens"; :>> effect = CliEffect::reads; :>> stability = CliStability::stable; :>> invocation = "show contentions [ROOT]"; :>> synopsis = "recorded disagreements between contributors awaiting adjudication"; }
    part cliCommitDelta : CliCommand { :>> id = "7f570bde-dde8-4185-8bf8-ec7c9448def0"; :>> title = "keel commit-delta"; :>> createdAt = "2026-09-10"; :>> createdBy = "claudeOpus5"; :>> name = "commit-delta"; :>> family = "lens"; :>> effect = CliEffect::reads; :>> stability = CliStability::stable; :>> invocation = "show commit-delta [ROOT] [--range A..B]"; :>> synopsis = "the model delta a git range made - Needs, Requirements, Decisions, Issues and tasks added, items retired by #Supersede and Issues resolved, with titles, reconciled against the diff's added declarations by count; empty when the range changed no item (D0282)"; }
    part cliControlCensus : CliCommand { :>> id = "3f940581-1c81-4762-8e00-41506e888eae"; :>> title = "keel control-census"; :>> createdAt = "2026-09-10"; :>> createdBy = "claudeOpus5"; :>> name = "control-census"; :>> family = "lens"; :>> effect = CliEffect::reads; :>> stability = CliStability::stable; :>> invocation = "show control-census [ROOT]"; :>> synopsis = "every control by whose act it binds, the ledger blocks by actor kind, its motivating incidents (observed vs code-read) and its evidence class - friction and hypothetical first"; }
    part cliControlStructure : CliCommand { :>> id = "7a4ab5d4-98f6-4ae9-9cc9-337fb7a48e5d"; :>> title = "keel control-structure"; :>> createdAt = "2026-09-02"; :>> createdBy = "claudeOpus5"; :>> name = "control-structure"; :>> family = "lens"; :>> effect = CliEffect::reads; :>> stability = CliStability::stable; :>> invocation = "show control-structure [--svg] [ROOT]"; :>> synopsis = "STPA step 2 for this project's own workflow, computed: authorities, what each issues on which process carrying what data, and what feedback returns; --svg draws it (D0285)"; }
    part cliControls : CliCommand { :>> id = "b6ab7adb-4d02-4a71-823d-353e9a9c9bc6"; :>> title = "keel controls"; :>> createdAt = "2026-09-02"; :>> createdBy = "claudeOpus5"; :>> name = "controls"; :>> family = "lens"; :>> effect = CliEffect::reads; :>> stability = CliStability::stable; :>> invocation = "show controls [ROOT]"; :>> synopsis = "the two-way hazard/control diff: uncovered failure conditions and unanchored controls; per control DECLARED, ARMED and PROOF (PROVEN / UNPROVEN / UNDETERMINED, D0360)"; }
    part cliCoverage : CliCommand { :>> id = "7b7e182b-e09b-4f4b-913c-90d1f5034e8e"; :>> title = "keel coverage"; :>> createdAt = "2026-09-02"; :>> createdBy = "claudeOpus5"; :>> name = "coverage"; :>> family = "lens"; :>> effect = CliEffect::reads; :>> stability = CliStability::stable; :>> invocation = "show coverage [ROOT]"; :>> synopsis = "Needs and requirements with and without satisfy and verify edges"; }
    part cliCritiqueCoverage : CliCommand { :>> id = "9a2646ec-294c-47d5-ad5f-8c818f3fcc74"; :>> title = "keel critique-coverage"; :>> createdAt = "2026-09-02"; :>> createdBy = "claudeOpus5"; :>> name = "critique-coverage"; :>> family = "lens"; :>> effect = CliEffect::reads; :>> stability = CliStability::stable; :>> invocation = "show critique-coverage [ROOT]"; :>> synopsis = "per-element required-lens matrix and the gap set"; }
    part cliCritiquePolicy : CliCommand { :>> id = "4f2f975c-7e36-4e3c-a887-532ae3fa80a6"; :>> title = "keel critique-policy"; :>> createdAt = "2026-09-02"; :>> createdBy = "claudeOpus5"; :>> name = "critique-policy"; :>> family = "lens"; :>> effect = CliEffect::reads; :>> stability = CliStability::stable; :>> invocation = "show critique-policy [ROOT]"; :>> synopsis = "which antagonistic lenses each assurance-element type requires"; }
    part cliDecisionFollowThrough : CliCommand { :>> id = "83cbf6bf-0099-4ff1-9962-3a6c45bb0154"; :>> title = "keel decision-follow-through"; :>> createdAt = "2026-09-02"; :>> createdBy = "claudeOpus5"; :>> name = "decision-follow-through"; :>> family = "lens"; :>> effect = CliEffect::reads; :>> stability = CliStability::stable; :>> invocation = "show decision-follow-through [ROOT]"; :>> synopsis = "every accepted Decision's downstream items and evidence, and the gaps"; }
    part cliDecisions : CliCommand { :>> id = "eff14c2f-e07f-49c9-b11c-0c532981cfbf"; :>> title = "keel decisions"; :>> createdAt = "2026-09-02"; :>> createdBy = "claudeOpus5"; :>> name = "decisions"; :>> family = "lens"; :>> effect = CliEffect::reads; :>> stability = CliStability::stable; :>> invocation = "show decisions [ROOT]"; :>> synopsis = "load-bearing Decisions, ranked by how much depends on them"; }
    part cliDispositions : CliCommand { :>> id = "1da4c7f3-47c7-4bb4-8a50-8cc50b95c841"; :>> title = "keel dispositions"; :>> createdAt = "2026-09-02"; :>> createdBy = "claudeOpus5"; :>> name = "dispositions"; :>> family = "lens"; :>> effect = CliEffect::reads; :>> stability = CliStability::stable; :>> invocation = "show dispositions [ROOT]"; :>> synopsis = "findings by verdict: act, acceptRisk, dismiss, undispositioned"; }
    part cliFlow : CliCommand { :>> id = "d0626b8c-2628-4f6c-be8c-ecb777289d9e"; :>> title = "keel show flow"; :>> createdAt = "2026-09-11"; :>> createdBy = "claudeOpus5"; :>> name = "flow"; :>> family = "lens"; :>> effect = CliEffect::reads; :>> stability = CliStability::stable; :>> invocation = "show flow [ROOT] [--json]"; :>> synopsis = "per-sprint cycle time from GIT in minutes - first commit touching the delivery file to the commit landing its retro result, open while none has - with commits, the elapsed time from the preceding commit, the inter-commit gap over the last 7 days against the 7 before, and the point calibration over the last 80 closed sprints (issue483/issue485)"; }
    part cliHardening : CliCommand { :>> id = "b5d468e8-0491-4fed-8b56-8d985f1f5c4e"; :>> title = "keel hardening"; :>> createdAt = "2026-09-02"; :>> createdBy = "claudeOpus5"; :>> name = "hardening"; :>> family = "lens"; :>> effect = CliEffect::reads; :>> stability = CliStability::stable; :>> invocation = "show hardening [ROOT]"; :>> synopsis = "the critique process's own questions, computed"; }
    part cliIndicators : CliCommand { :>> id = "639c5faf-c94e-4a23-ab82-8fa50fe808b7"; :>> title = "keel indicators"; :>> createdAt = "2026-09-02"; :>> createdBy = "claudeOpus5"; :>> name = "indicators"; :>> family = "lens"; :>> effect = CliEffect::reads; :>> stability = CliStability::stable; :>> invocation = "show indicators [ROOT]"; :>> synopsis = "monitored values with no enforced threshold"; }
    part cliIntake : CliCommand { :>> id = "51e7ebca-d901-4196-a674-8cb89f50626b"; :>> title = "keel intake"; :>> createdAt = "2026-09-02"; :>> createdBy = "claudeOpus5"; :>> name = "intake"; :>> family = "lens"; :>> effect = CliEffect::reads; :>> stability = CliStability::stable; :>> invocation = "show intake [ROOT]"; :>> synopsis = "statements, user stories and routing: unparsed, unrouted, unsourced"; }
    part cliKnowledge : CliCommand { :>> id = "c3f1a256-f67f-4379-82df-4361aa061246"; :>> title = "keel knowledge"; :>> createdAt = "2026-09-02"; :>> createdBy = "claudeOpus5"; :>> name = "knowledge"; :>> family = "lens"; :>> effect = CliEffect::reads; :>> stability = CliStability::stable; :>> invocation = "show knowledge [ROOT]"; :>> synopsis = "question coverage: does seeding find an entity and traversal reach an answer"; }
    part cliLaunchables : CliCommand { :>> id = "8532df45-ca6c-444b-9e70-1a9ba9c87e45"; :>> title = "keel launchables"; :>> createdAt = "2026-09-02"; :>> createdBy = "claudeOpus5"; :>> name = "launchables"; :>> family = "lens"; :>> effect = CliEffect::reads; :>> stability = CliStability::stable; :>> invocation = "show launchables [ROOT]"; :>> synopsis = "the console's launchable set from declared skills and processes"; }
    part cliLs : CliCommand { :>> id = "39beb087-2aa3-40f0-ba85-4691739dd2a1"; :>> title = "keel ls"; :>> createdAt = "2026-09-02"; :>> createdBy = "claudeOpus5"; :>> name = "ls"; :>> family = "lens"; :>> effect = CliEffect::reads; :>> stability = CliStability::stable; :>> invocation = "show ls [ROOT]"; :>> synopsis = "the .tracking files"; }
    part cliMarkerCensus : CliCommand { :>> id = "089845be-5a25-4bbf-8201-8a674a2e1d14"; :>> title = "keel marker-census"; :>> createdAt = "2026-09-02"; :>> createdBy = "claudeOpus5"; :>> name = "marker-census"; :>> family = "lens"; :>> effect = CliEffect::reads; :>> stability = CliStability::stable; :>> invocation = "show marker-census [ROOT]"; :>> synopsis = "per-marker edge count against prose mentions"; }
    part cliPriority : CliCommand { :>> id = "8d97910f-cf43-4cf6-bb25-0ba2d43a8da4"; :>> title = "keel show priority"; :>> createdAt = "2026-09-05"; :>> createdBy = "claudeOpus5"; :>> name = "priority"; :>> family = "lens"; :>> effect = CliEffect::reads; :>> stability = CliStability::stable; :>> invocation = "show priority [ROOT]"; :>> synopsis = "the priority metric: every ready item in declared order with its computed class - resolver severity or retro recurrence - and the inversions (D0311)"; }
    part cliOpenIssues : CliCommand { :>> id = "f4dced33-b00a-4a49-b7af-2d889d6ee718"; :>> title = "keel open-issues"; :>> createdAt = "2026-09-02"; :>> createdBy = "claudeOpus5"; :>> name = "open-issues"; :>> family = "lens"; :>> effect = CliEffect::reads; :>> stability = CliStability::stable; :>> invocation = "show open-issues [ROOT]"; :>> synopsis = "every open Issue, its resolvers, and whether each resolver is complete"; }
    part cliOrphans : CliCommand { :>> id = "fb13e187-9853-4959-ab89-86449a53a9e4"; :>> title = "keel orphans"; :>> createdAt = "2026-09-02"; :>> createdBy = "claudeOpus5"; :>> name = "orphans"; :>> family = "lens"; :>> effect = CliEffect::reads; :>> stability = CliStability::stable; :>> invocation = "show orphans [ROOT]"; :>> synopsis = "items nothing references: tasks with no DoD, Issues with no resolver"; }
    part cliOutstanding : CliCommand { :>> id = "72483253-0290-4f5e-928c-8112395a0b8a"; :>> title = "keel outstanding"; :>> createdAt = "2026-09-02"; :>> createdBy = "claudeOpus5"; :>> name = "outstanding"; :>> family = "lens"; :>> effect = CliEffect::reads; :>> stability = CliStability::stable; :>> invocation = "show outstanding [ROOT]"; :>> synopsis = "every not-done item, flat"; }
    part cliRecent : CliCommand { :>> id = "1a0dc92f-111b-415b-9c74-8b297d21008c"; :>> title = "keel recent"; :>> createdAt = "2026-09-02"; :>> createdBy = "claudeOpus5"; :>> name = "recent"; :>> family = "lens"; :>> effect = CliEffect::reads; :>> stability = CliStability::stable; :>> invocation = "show recent [ROOT]"; :>> synopsis = "git-derived activity timeline over .tracking and .engine"; }
    part cliRootedness : CliCommand { :>> id = "6ec111f2-0527-41ed-92c6-25efe8fa772e"; :>> title = "keel rootedness"; :>> createdAt = "2026-09-02"; :>> createdBy = "claudeOpus5"; :>> name = "rootedness"; :>> family = "lens"; :>> effect = CliEffect::reads; :>> stability = CliStability::stable; :>> invocation = "show rootedness [ROOT]"; :>> synopsis = "charter-source burndown: need-rooted, decision-chartered, orphan"; }
    part cliSittingCoverage : CliCommand { :>> id = "6863c616-132d-47bb-ae7f-9173d1b8a285"; :>> title = "keel sitting-coverage"; :>> createdAt = "2026-09-02"; :>> createdBy = "claudeOpus5"; :>> name = "sitting-coverage"; :>> family = "lens"; :>> effect = CliEffect::reads; :>> stability = CliStability::stable; :>> invocation = "show sitting-coverage [ROOT]"; :>> synopsis = "per-sitting human review currency"; }
    part cliSuspect : CliCommand { :>> id = "db0175fd-8113-4363-9632-698e5500738a"; :>> title = "keel suspect"; :>> createdAt = "2026-09-02"; :>> createdBy = "claudeOpus5"; :>> name = "suspect"; :>> family = "lens"; :>> effect = CliEffect::reads; :>> stability = CliStability::stable; :>> invocation = "show suspect [ROOT]"; :>> synopsis = "done work whose evidence drifted from the tree it was judged against"; }
    part cliTierSatisfaction : CliCommand { :>> id = "41727336-4ad1-4a8e-8c90-8faa5a81f087"; :>> title = "keel tier-satisfaction"; :>> createdAt = "2026-09-02"; :>> createdBy = "claudeOpus5"; :>> name = "tier-satisfaction"; :>> family = "lens"; :>> effect = CliEffect::reads; :>> stability = CliStability::stable; :>> invocation = "show tier-satisfaction [ROOT]"; :>> synopsis = "per tier, the fraction cleanly satisfied downstream"; }
    part cliTrace : CliCommand { :>> id = "4aa73d14-9776-415a-89ad-e8bf456cdcc1"; :>> title = "keel trace"; :>> createdAt = "2026-09-02"; :>> createdBy = "claudeOpus5"; :>> name = "trace"; :>> family = "lens"; :>> effect = CliEffect::reads; :>> stability = CliStability::stable; :>> invocation = "show trace [ROOT]"; :>> synopsis = "every typed edge reaching an item, both directions"; }
    part cliTraceNeed : CliCommand { :>> id = "cd62c90b-80e5-440a-a016-7198af52f31f"; :>> title = "keel trace-need"; :>> createdAt = "2026-09-02"; :>> createdBy = "claudeOpus5"; :>> name = "trace-need"; :>> family = "lens"; :>> effect = CliEffect::reads; :>> stability = CliStability::stable; :>> invocation = "show trace-need [ROOT]"; :>> synopsis = "one Need's satisfaction chain down to test results"; }
    part cliVerification : CliCommand { :>> id = "f8df3bfa-c17b-4023-99e4-b991bd73a9df"; :>> title = "keel verification"; :>> createdAt = "2026-09-02"; :>> createdBy = "claudeOpus5"; :>> name = "verification"; :>> family = "lens"; :>> effect = CliEffect::reads; :>> stability = CliStability::stable; :>> invocation = "show verification [ROOT]"; :>> synopsis = "EXAMINED against EXERCISED, never one number; --pending lists the gap"; }
    part cliWhy : CliCommand { :>> id = "79e8e85c-f235-480b-a46c-8655231adb97"; :>> title = "keel why"; :>> createdAt = "2026-09-02"; :>> createdBy = "claudeOpus5"; :>> name = "why"; :>> family = "lens"; :>> effect = CliEffect::reads; :>> stability = CliStability::stable; :>> invocation = "show why [ROOT]"; :>> synopsis = "answer a question from the model as a graph, with provenance"; }
    part cliWorkflows : CliCommand { :>> id = "de0e3d9d-1b00-4dc2-8b72-7a16992b2893"; :>> title = "keel workflows"; :>> createdAt = "2026-09-02"; :>> createdBy = "claudeOpus5"; :>> name = "workflows"; :>> family = "lens"; :>> effect = CliEffect::reads; :>> stability = CliStability::stable; :>> invocation = "show workflows [ROOT]"; :>> synopsis = "the six workflows and their phases"; }
}
