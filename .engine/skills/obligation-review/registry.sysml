// The obligation-review skill's own registry declaration, beside the skill it describes (D0222).
//
// MOVED verbatim out of the shared skills-registry by a committed migration transform (D0222).
// The shared registry
// could not travel with a unit, so adopting any unit left the receiving project's
// `process-skill` guard failing on arrival (issue252). Moved, never copied: the id is
// unchanged and `duplicate-identity` is what proves it.
package SkillsRegistryObligationReview {
    private import EngineElement::*;
    private import EngineSkills::*;

    part obligationReview : AISkill {
        :>> id = "0a5c37e9-64b1-4d28-9f70-e13c8b5407fa";
        :>> title = "obligation-review";
        :>> purpose = "Deploys .engine/processes/obligation-review.sysml. Turn what is waiting on the HUMAN into the keel deck they can operate away from the terminal - on a phone - with every tap either saved through keel serve's tested endpoints (local) or delivered as a row to the keel-deck-inbox sheet via the artifact mcp capability (mobile), then pulled and recorded through the write API with computed-view verification (the Smartsheet tap-inbox was RETIRED by D0206). Generated by `keel deck` (keel-cli/src/deck.rs) from the computed obligation views; e2e-tested by an engine-dev-only end-to-end test that does not ship before any deploy. The deck is a #View: regenerable, never truth, and nothing is a recorded fact until it reads back from a computed view.";
        :>> location = ".engine/skills/obligation-review/SKILL.md";
        :>> triggerCondition = "The human wants to review or give feedback on outstanding items away from the terminal, or asks for something usable on mobile - `keel serve` needs a server, a localhost browser and a shell, and their obligations do not wait for those conditions.";
        :>> writePolicy = WritePolicy::direct;
    }
}
