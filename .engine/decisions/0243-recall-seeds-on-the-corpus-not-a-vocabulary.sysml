// D0243 (status: the `status` field below is the truth) — recall seeds on the corpus's own statistics, not an authored vocabulary
// Recorded via `keel record decision` (D0105 RMWX axis; issue054). Acceptance is a separate explicit
// human gate (method=confirmation, D0106): flip status + add the d0243Accept event on sign-off.
package Decision0243 {
    private import EngineElement::*;
    private import EngineWork::*;
    private import EngineVerification::*;
    private import EngineRelationships::*;

    part d0243 : Decision {
        :>> id = "9536e348-602a-4af3-8c8f-ad465ee3da33";
        :>> title = "recall seeds on the corpus's own statistics, not an authored vocabulary";
        :>> createdAt = "2026-08-27";
        :>> createdBy = "claudeOpus5";
        :>> status = DecisionStatus::accepted;
        :>> context = "D0242 planned the injection tier and described seeding as matching a prompt 'against the lexicon, aliases and declared element names'. Measuring the existing traversal afterwards showed two things that change the design. FIRST, the store is already nearly vestigial for recall. `.knowledge/lexicon/` declares four terms and they are all ALIASES - aFinished, aApprove, aLaptop, aBuildServer - not a subject vocabulary. Asking `keel why workspace` returns 65 seeds whose provenance is 57 name matches and 8 title matches: every one from the MODEL, none from the store. The typed model IS the graph, exactly as D0161 said for the already-typed corpus case, and seeding does not currently depend on authored vocabulary at all. SECOND, and this is the real problem: seeding is substring-based and explodes. Measured seeds and reached counts - decision 294/1087, change 96/444, the 795/3283, gate 5806/6805, a 11112/12893. Output stays capped at 40 rows so nothing breaks, but ranking 12,893 reached elements by hop count is noise. A curated vocabulary is what would normally solve that, which is why one was in the design.";
        :>> decision = "Recall seeds on the CORPUS's own statistics and shape, not on an authored vocabulary. `.knowledge/` becomes an optional refinement rather than a prerequisite. Four precision rules, in order of preference: 1. IDENTIFIER-SHAPED TOKENS FIRST. `dNNNN`, `issueNNN`, `sprintNNN`, and camelCase element names are unambiguous, and a prompt asking about one already contains it. 2. WORD AND SEGMENT BOUNDARIES, never substrings. `gate` matched 5,806 elements because it sits inside gated, gating, keel-gate and staleGateProse; camelCase is split into segments before matching. 3. RARITY WEIGHTING DERIVED FROM THE CORPUS. A token matching thousands of elements carries no information and is dropped; one matching a handful is a strong seed. This is stop-wording COMPUTED from the tree rather than authored, so it needs no maintenance and cannot go stale. 4. HUB SUPPRESSION, which already exists (`hubsNotExpanded`). Aliases stay supported, because an alias is the one thing corpus statistics cannot infer - it maps a word the corpus never uses to a thing the corpus does. Questions stay supported, because `question-coverage` measures against them. Both are refinements; neither is required for recall.";
        :>> rationale = "The human's framing was 'take the good ideas from the knowledge graph, if the intent is so similar, and just infest it into keel', and the measurement says that is not a shortcut - it is what the thing already is. Seven of eight spine steps are built, seeding is already model-driven, and the separate store contributes four aliases. Keeping a parallel subsystem for that is the dual-truth shape D0018 exists to remove. ALTERNATIVES for precision: (A) require a curated subject vocabulary, as the source process's steps 1-2 imply - rejected, because it makes recall's usefulness proportional to authoring effort in every downstream project, and this project's own four-term lexicon after a week is the evidence for how that goes. It also contradicts the typed-corpus case, where identity and types are already authored. (B) cap seeds arbitrarily (top-N by name length, say) - rejected: it is precision theatre, discarding information without a reason anyone could defend, and it would silently drop the right seed. (C) derive precision from the corpus - CHOSEN. CRITERIA: does recall work on a project with zero authored vocabulary; does a common word produce noise; and does the rule stay true as the corpus grows without anyone maintaining it. Rarity weighting satisfies the third criterion in a way authoring never can: a word that is rare today and common in a year is re-weighted automatically, because the weight is recomputed from the tree.";
        :>> consequences = "This SIMPLIFIES D0242 rather than extending it. Part 2's seeding no longer depends on the lexicon, and part 5 shrinks: a downstream project needs no authored vocabulary to get recall, so portability is the binary plus `sync-claude`, and the skill's human-owned half becomes OPTIONAL - declare questions if you want coverage measured, declare aliases if the corpus uses different words than you do. The `kgRecallSeedsFromAPrompt` and `kgTravelsWithTheEngine` DoDs are updated to match. What this does NOT do is make precision solved. It names the mechanism; the numbers above are the before, and `kgInjectionProvenOnTheTrap` now has to measure precision as well as tool-calls-to-answer - pushing the wrong facts confidently is worse than pushing none, and a 40-row cap hides an explosion rather than fixing it. The honest-outcome clause from D0242 part 4 stands: if the trap shows no gain, record it and keep the command tier. `.knowledge/` remains removable by construction, which is now a stronger claim than it was: with seeding independent of it, deleting the directory costs aliases and coverage measurement, not recall.";
    }

    // acceptance event (D0121 review-queue sign-off; D0066/D0106 — human-judged, not fabricated)
    verification d0243Accept : Test { :>> id = "e7f42f51-483d-433b-a5a8-ddd5206f3f3c"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0243AcceptR1 : TestResult { :>> id = "8e025e04-0301-4fa2-9539-33bba3d2df78"; :>> outcome = VerdictKind::pass; :>> judgedAgainst = "b04c9c6"; :>> judgedAt = "2026-08-28"; :>> judgedBy = "wweatherholtz"; }
}
