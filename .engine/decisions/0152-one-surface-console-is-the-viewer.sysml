// D0152 — ACCEPTED (wweatherholtz, 2026-08-16): ONE surface. The operator console IS the viewer;
// D0114's shape-B choice (a separate viewer app) is superseded. Architecture decision, recorded
// AFTER the Business gate on the console Needs (business-architecture: needs-before-architecture).
package Decision0152 {
    private import EngineElement::*;
    private import EngineWork::*;
    private import EngineVerification::*;
    private import EngineRelationships::*;

    #ProspectiveChange part d0152 : Decision {
        :>> id = "7f2b4d61-9c38-4a05-b7e2-1d63a0f95c84";
        :>> title = "D0152: one surface — the operator console IS the viewer (supersedes D0114 shape B)";
        :>> createdAt = "2026-08-16";
        :>> createdBy = "claudeOpus5";
        :>> status = DecisionStatus::accepted;
        :>> context = "D0114 chose shape B — a separate viewer app consuming keel over a versioned read API — from the three shapes N-6 left open (A extend serve / B separate app / C thin renderer). N-6 itself constrains AUTHORITY, not deployment: 'the viewing surface must consume keel as the authoritative engine rather than duplicating SysML-v2 management; keel's write API + guards remain the ONLY write path', and it names the shape explicitly as the open architecture decision. WHAT CHANGED SINCE. The viewer app was not built. The console meanwhile accreted twelve hardcoded tabs (console.html:41) organised by data type with NO authored Business layer behind any of them — 56 UseCases exist in this model and not one described it. The substrate the two surfaces would need is identical: the read API, the schema API, item introspection, section render, and the critique/disposition write-back all already exist and already serve the console. And the human, who is the entire operator audience, asked for one: 'I like the one app but filtered idea. I think that's the best balance between focus, usefulness, and flexibility.'";
        :>> decision = "ACCEPTED: shape A. ONE surface serves both purposes. The console IS the viewer, and it therefore INHERITS the viewer's Need set rather than being held to a lower bar: N-1 (a viewpoint is a query AND a visual form targeting a named audience), N-2 (explorable navigable graph), N-6 (authority stays with keel — the surface never becomes a second write path), and above all N-17 (the UI is GENERATED from the declared model; views and actions are not hardcoded). Those join the five console Needs accepted at the Business gate. The separate-viewer-app plan is retired, not deferred.";
        :>> rationale = "WHY ONE: the substrate is shared, so two surfaces means maintaining two information architectures over one API for a single operator — which is the console's own clutter problem raised one level. N-6 permits shape A and always did. And the console already implements a substantial share of what UC-1..UC-16 describe, so 'separate app' had become a plan to rebuild what exists. THE ARGUMENT I NO LONGER HAVE, recorded because its loss weakens this Decision and a reader deserves to see that: the merge was first argued on the grounds that the operator/stakeholder split is a FILTER rather than a deployment boundary, since a Viewpoint already carries an `audience` field. The human then DEFERRED audience filtering — 'I won't prevent access or use role-specific views for a bit' — so that filter is not being built, and the merge now rests on shared substrate and single-operator focus alone. CONSEQUENTLY THIS IS THE DECISION THAT REOPENS if a non-technical stakeholder surface is ever needed: the audiences genuinely differ, mixing them is how a surface reaches twelve tabs, and nothing here prevents that recurrence except the discipline of N-17 and N-C5. ALTERNATIVES: (i) keep shape B and design the console's IA separately — REJECTED, it doubles the IA work and leaves the console's Needs unowned, which is how it got here; (ii) shape C, a thin renderer over emitted view data — REJECTED, it cannot satisfy N-17's requirement that the surface generate itself from the declared model, since a thin renderer receives what it is given rather than reading the declarations.";
        :>> consequences = "The console's bar rises sharply: it must now satisfy N-1, N-2 and N-17, not merely avoid annoying its single user, and N-17 in particular condemns the current hardcoded tab array outright. UC-1 through UC-16 become console use cases; D0115's scope revisions (single-user, unauthenticated, auth/multi-user/per-user dropped) continue to apply to the merged surface. The versioned read API keeps its contract — it is now consumed in-process rather than across a network boundary, and remains the seam that keeps keel authoritative. Retiring the separate app removes the deployment story that would have carried a stakeholder audience, which is the risk named in the rationale.";
    }

    // Supersedes only D0114's SHAPE choice. The rest of that Decision — the versioned read API as the
    // seam, and keel remaining authoritative — is retained and restated above, not discarded.
    #SupersedeClause dependency from d0152 to d0114;

    // acceptance event (D0121 review-queue sign-off; D0066/D0106 — human-judged, not fabricated)
    verification d0152Accept : Test { :>> id = "b4e9c07a-52d1-4f86-9a3b-6e18d2c40f75"; :>> method = VerificationMethod::confirmation; :>> procedureText = "wweatherholtz, 2026-08-16, verbatim: 'I like the one app but filtered idea. I think that's the best balance between focus, usefulness, and flexibility. let's proceed with that. supercede d0114 if we need to.' — given in direct reply to a critique that set out the case for and against one surface, including that merging supersedes D0114 and that the audiences genuinely differ. Confirmed again at the Business gate on 2026-08-16 with 'looks great, proceed', authorising the architecture phase in which this Decision is recorded. Recording was deliberately HELD until after the Needs gate: the human's permission predated it, but the business-architecture ordering rule puts an architecture Decision after the Needs it serves are accepted, and recording it earlier would have been the issue054 defect."; }
    part d0152AcceptR1 : TestResult { :>> id = "8c31f5be-7a04-4d29-b6e5-0f927ac31d68"; :>> outcome = VerdictKind::pass; :>> judgedAgainst = "15e33f0"; :>> judgedAt = "2026-08-16"; :>> judgedBy = "wweatherholtz"; }
}
