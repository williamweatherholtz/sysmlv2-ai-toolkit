// D0421 (status: the `status` field below is the truth) — touchedTestsRunBeforeLand: keel land computes the integration tests whose text names a module changed since the base and runs exactly those before the first push, refusing on a failure - declared now, armed only by the human's acceptance of this Decision
// Recorded via `keel record decision` (D0105 RMWX axis; issue054). Acceptance is a separate explicit
// human gate (method=confirmation, D0106): flip status + add the d0421Accept event on sign-off.
package Decision0421 {
    private import EngineElement::*;
    private import EngineWork::*;
    private import EngineVerification::*;
    private import EngineRelationships::*;

    // #ProspectiveChange (D0070) - this Decision governs a process/schema change; the co-committed
    // change rides the process-change guard's hard lock.
    #ProspectiveChange part d0421 : Decision {
        :>> id = "f20e3b9d-334f-4e0d-9135-4cf5b4e1830a";
        :>> title = "touchedTestsRunBeforeLand: keel land computes the integration tests whose text names a module changed since the base and runs exactly those before the first push, refusing on a failure - declared now, armed only by the human's acceptance of this Decision";
        :>> createdAt = "2026-09-09";
        :>> createdBy = "claudeOpus5";
        :>> status = DecisionStatus::accepted;
        :>> context = "issue416, tracked as dcTouchedTestsRunBeforeLand: control_structure.rs changed, keel-cli/tests/control_structure_is_computed.rs asserted the old shape, the commit gate was green and CI was red, because the only thing that ran the integration tests was the full suite - whose land gate the human withdrew as too costly at D0356 (~11 wall minutes every time code moved, against roughly one catchable bad push in twenty-five). Since then every CI red of this kind (issue416, and issue433's six runs were found by two integration tests that name the changed module in their text) has been a test whose text named the very module the commit changed. The full suite is the wrong instrument at this price; nothing at all is the wrong instrument at any price; the set of tests that can have been broken by the change is small and computable from text.";
        :>> decision = "NOT A FORK: the DoD names one set, one point of application and one arming condition. keel-cli/src/touched.rs computes the TOUCHED set: the module stems of every path changed since the base (origin/<branch>, else the last suite receipt's head, else HEAD~1; keel-cli/src/<stem>.rs and keel-cli/src/<dir>/mod.rs contribute <stem> and <dir>; main.rs and lib.rs contribute nothing and are reported as unattributed), and the set is every keel-cli/tests/<name>.rs whose text names a stem as a whole word, plus every test file the push itself changed, plus the lib's own unit tests (cargo test --lib) whenever any keel-cli/src path changed - a module's cfg(test) block names it by construction, and a unit test elsewhere may read the changed module's live facts (issue438). keel land prints the set on every self-build push. Once this Decision carries the human's acceptance (d0421AcceptR1 in its file, the D0338 pattern) land RUNS exactly those binaries as one cargo test --release --no-fail-fast invocation before the first push and REFUSES the push on any failure, naming the failing binaries from cargo's own rerun hint; an empty set runs nothing and says so; the same run is keel suite --touched. While this Decision is proposed the set is printed, nothing is run, and the receipt records outcome not-run. Every run writes .keel/metrics/touched-receipt.toml - base, stems, unattributed, tests, outcome, counts, seconds, log - beside the suite's receipt and never in it. A downstream tree is untouched.";
        :>> rationale = "A test that names a module in its text is the test that module's change can have broken, and it costs less than the suite by exactly the binaries it leaves out - which on a real change is fewer than the fixture suggested. MEASURED on the first live set (5fbe410, 2026-09-09, this host): a commit touching view, corpus, indexer, critique, staleness and perf named 15 integration binaries plus the lib, 519 tests, 528 s wall - 234 s of it cargo compiling the lib under cfg(test) and linking 16 release binaries, 286 s running them (batched_governance_agrees 93 s, the lib's 453 tests 86 s, federation 39 s) - against the full suite's 585 s (58 binaries, 625 tests, receipt at 9369863). The fixture's set of one runs in about two seconds; a live set that names view does not, because view is the module most test text names and every named binary is relinked in release. The withdrawal at D0356 was about cost per catch, and this changes the cost while keeping the catch; it is not the same gate returning, which push_gate_is_withdrawn.rs continues to pin (its fixture's lib.rs names no module and lands with an empty set). The refusal is outside standing consent - it is a new gate on the push path - so it is declared inert and armed only by the human's word (D0337), and everything but the refusal (the computed set, the receipt, keel suite --touched) is live now so the set's shape and cost are on the record before anyone is asked to accept a gate on it. Cargo's rerun hint is read for the failing names because a capture reads stdout whole before stderr and the Running header pairing that holds on a terminal does not hold there - the first live run recorded failed = 1 and failing = [] - and the unit test carries that capture as its known-positive (D0388).";
        :>> consequences = "touched.rs (module, pure set functions with probe-pair unit tests, compute, run, before_push, cmd); suite.rs exposes own_image_refusal to the touched run and routes keel suite --touched; sync.rs cmd_land calls touched::before_push after the tree gate; lib.rs declares the module; the cliSuite fact in both homes names --touched and cites this Decision; keel-cli/tests/touched_tests_run_before_land.rs is the DoD's three cases (refuse-then-land with the receipt on each step, inert while proposed, the pure set). The land fixtures' own-image refusal is shared with keel suite (issue386). What accepting binds: a push whose touched set fails is refused on this machine; the fix is to fix or re-agree the test, never to skip. What it forecloses: nothing about the suite - keel suite is unchanged. What would change it: a measured cost of the touched run that approaches the suite's - which the first live set did (528 s of 585 s) for a view-touching change, so the cost lever is on the record before the word is asked: consolidating the 61 integration files into one test binary would cut the 16 release links to one, and the lib's own 86 s is the same on either path, or a CI red whose test named no changed module - both would show in the receipts, which is why the receipt is live before the refusal is.";
    }

    // acceptance event (D0121 review-queue sign-off; D0066/D0106 — human-judged, not fabricated)
    verification d0421Accept : Test { :>> id = "fd587b27-9410-42ef-9c7e-1bca7d565819"; :>> method = VerificationMethod::confirmation; :>> procedureText = "chat acceptance of option A (accept both) after the measured 528 s price was put in front of them - their words, verbatim: “accept D0421 and D0422”"; }
    part d0421AcceptR1 : TestResult { :>> id = "4c79f7b3-1bcd-4223-8ac1-5fc57273e130"; :>> outcome = VerdictKind::pass; :>> judgedAgainst = "f319fb4"; :>> judgedAt = "2026-09-10"; :>> judgedBy = "wweatherholtz"; :>> createdBy = "claudeOpus5"; }
}
