// D0457 (status: the `status` field below is the truth) — verbCountAfterTheFiveFolds: the five folds land at 35 top-level verbs, not under 25 - fold eleven more names away or amend D0273's clause to the measured number
// Recorded via `keel record decision` (D0105 RMWX axis; issue054). Acceptance is a separate explicit
// human gate (method=confirmation, D0106): flip status + add the d0457Accept event on sign-off.
package Decision0457 {
    private import EngineElement::*;
    private import EngineWork::*;
    private import EngineVerification::*;
    private import EngineRelationships::*;

    // RESEARCH: Measured 2026-09-12 at the post-fold build of sprint 683: keel show hardening reads helpCoverage.dispatched 35, namedInHelp 35 (hardening683.json); cli_facts.rs holds 85 facts of which 34 are top-level verbs and 51 are lenses under show (verb_census.py over cli_facts.rs, re-runnable). By family: governance 8 (accept, reject, judge-set, override, claim, enroll, actor, advance), integration 8 (init, sync, land, migrate, claude, sync-claude, projects, version), distribution 6 (process, library, onboard, activation, activate, deactivate), gating 4 (gate, audit, hook, suite), rendering 3 (render, deck, serve), channel 2 (github, currency), authoring 1 (record), orientation 1 (show), knowledge 1 (recall). By effect: 10 write, 12 read-and-write, 9 read, 3 tooling. d0399's arithmetic re-run: 70 verbs at 649b433 minus 10 gating, 11 orientation, 3 rendering, 8 authoring, 3 channel = 35. The five folds took sprints 678 to 683 (six sprints, 15 points, five transforms under .engine/tools/migrations/, two #SafetyChange Decisions signed by the human's own word). issue507 records the finding; issue338 is D0273's original under-25 miss.
    part d0457 : Decision {
        :>> id = "54df343f-c58e-42b0-a362-08c0eadb5433";
        :>> title = "verbCountAfterTheFiveFolds: the five folds land at 35 top-level verbs, not under 25 - fold eleven more names away or amend D0273's clause to the measured number";
        :>> createdAt = "2026-09-12";
        :>> createdBy = "claudeFable5";
        :>> status = DecisionStatus::accepted;
        :>> context = "D0273 (accepted) promised that the lens collapse leaves under 25 visible verbs; issue338 recorded that the promise was written without deriving it, and dcRemainingCliFamilies was chartered to make one of two honest resolutions happen. d0399 put that fork to the human with counts and they chose OPTION A, fold the remaining five families, whose text stated that the folds land the count at roughly 20 and make D0273's clause true as written. The five folds are done (D0446 rendering, D0447 orientation, D0451 authoring, D0452 gating, D0453 channel) and every one of their per-fold deltas read back from the tree as stated. The count is 35. Option A's own numbers said 35 - 70 minus the 35 names the five folds removed - and its context said under 25 needs the writers and the read-write set collapsed too; the landing figure was a wish beside a derivation that contradicted it, the same class as the clause it set out to honour (issue507). So dcRemainingCliFamilies has done everything option A named and the clause it exists to make honest is still false, and its DoD says the choice of what remains is the human's, with the counts.";
        :>> decision = "OPTION A (fold eleven or more of the remaining 34 names away, to under 25): the candidates by the same shape the five folds used - each a D0067 transform with a byte-equality baseline and its call-site rewrites in one commit, no alias window. The governance eight are the human's own acts and their names are what keel accept, keel reject, keel judge-set and keel override mean in D0192, D0289 and D0312; folding them under one router (keel judge accept, keel judge reject ...) removes seven names. The integration eight are git-shaped (init, sync, land, migrate, projects) and tooling (claude, sync-claude, version); a keel repo router removes up to seven, and land and sync-claude sit in .githooks/post-commit and the hooks, so that fold is a #SafetyChange awaiting the human's word. The distribution six under keel adopt removes five. Any two of the three reach under 25; all three reach about 18. COST: three more breaking changes to names the human types by hand every day (accept, judge-set, land), two of them on the enforcement surface; from the five folds' rate, three sprints and about eight points; every downstream project's skills that name these verbs update with the engine again; and the governance names lose the property D0289 leaned on - that the word the human types is the act they perform - for a shorter --help. OPTION B (amend the clause to the measured number): a follow-on Decision carries a #SupersedeClause edge to d0273 reversing only the under-25 consequence and states what the six sprints achieved - 111 dispatch arms at D0273's start to 35 verbs and 51 lenses behind show - and a second #SupersedeClause to d0399 reversing option A's landing figure of roughly 20, leaving option A's course and its five folds in force; dcRemainingCliFamilies then closes on the read-back its DoD names (hardening 35 equals the number the amended clause states) and issue338 and issue507 are resolved by that closure. COST: one or two Decisions and no code; a newcomer reads 34 names in keel --help rather than about 18, and the number D0273 promised is corrected in the record rather than reached. RECOMMEND, AND WHAT WOULD CHANGE IT: OPTION B. The five folds removed every family whose verbs were the same act with different arguments (gate and audit checks, show lenses, render targets, record kinds, github sub-verbs); what remains are verbs that name distinct acts, and the governance verbs in particular are the words the human's acceptance is bound to. The clause was never derived, twice, and the honest correction of an underived number is to record the measured one. It would change to A if the human wants the typed surface small for its own sake - if they read keel --help to recall a verb, or a downstream adopter names the count as friction - observables only they or an adopter hold; and it would change to A for the integration family alone if the hooks are being rewritten anyway for another reason, since that is the one fold whose enforcement-surface cost is then already paid. DO-NOTHING: dcRemainingCliFamilies stays open with issue338 and issue507 unresolved and D0273's clause stands false in an accepted Decision; the priority guard keeps ranking the task and every retro that reads the count re-finds the miss.";
        :>> rationale = "A criterion that the work cannot meet, left standing, is worse than either course: it makes the task that owns it undone forever and teaches that a Decision's stated number is decoration. Both options are honest; they differ in what the human values - the record's accuracy at no cost, or a smaller surface at the cost of renaming the words their own acts are bound to. That is a value only they hold, which is why this is a fork and not a Decision I take under standing consent, and why the counts are in the research field so the reader can re-run them. NOT A PROCESS CHANGE: this Decision changes no process, schema, guard or hook; it names the safety-change status one fold under option A would carry later, in its own Decision.";
        :>> consequences = "Held proposed until the human's word. Under B: one follow-on Decision with --supersedes-clause d0273 and one with --supersedes-clause d0399 (or one Decision carrying both edges, if the write API allows two), each stating the measured 35; dcRemainingCliFamilies' DoD result records hardening 35 against the amended clause; issue338 and issue507 resolve by that closure; the priority-inversion warnings that rank dcRemainingCliFamilies above the High-class items go with it. Under A: one Decision per family chosen, in the D0453 shape, the integration fold as #SafetyChange; three sprints; the byte comparison per fold; dcRemainingCliFamilies stays open until hardening reads under 25. Either way nothing in the five landed folds moves.";
    }

    // D0303 layering: the fork d0399 option A resolved, re-put with the measured count; the clause D0273 stated
    #DependsOn dependency from d0457 to d0399;
    #DependsOn dependency from d0457 to d0273;

    // acceptance event (D0121 review-queue sign-off; D0066/D0106 — human-judged, not fabricated)
    verification d0457Accept : Test { :>> id = "7fb2cbe0-1144-4da8-beec-9f71df2b05e8"; :>> method = VerificationMethod::confirmation; :>> procedureText = "Selected on the decision brief copy-out (eighteenth publish), pasted into chat 2026-09-12; d0457 option B chosen, the recommended course. Their prefix read 'Amend the Claude', the start of the option's own words; no note added. - their words, verbatim: “B: amend the clause to the measured number - 34 verbs, 51 lenses behind show - by two clause corrections, no code (recommended)”"; }
    part d0457AcceptR1 : TestResult { :>> id = "e0216832-918a-4dd1-a48c-ba9a60848bb7"; :>> outcome = VerdictKind::pass; :>> judgedAgainst = "25527cc"; :>> judgedAt = "2026-09-12"; :>> judgedBy = "wweatherholtz"; :>> createdBy = "claudeFable5"; }
}
