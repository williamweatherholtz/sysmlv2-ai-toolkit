// D0419 (status: the `status` field below is the truth) — citationCheckHoldsWhereTheDecisionsLive: guard cli-surface-declared reads what a synopsis cites only in a tree that holds the engine's Decision channel, recognised by D0271 being present
// Recorded via `keel record decision` (D0105 RMWX axis; issue054). Acceptance is a separate explicit
// human gate (method=confirmation, D0106): flip status + add the d0419Accept event on sign-off.
package Decision0419 {
    private import EngineElement::*;
    private import EngineWork::*;
    private import EngineVerification::*;
    private import EngineRelationships::*;

    // #ProspectiveChange (D0070) - this Decision governs a process/schema change; the co-committed
    // change rides the process-change guard's hard lock.
    #ProspectiveChange part d0419 : Decision {
        :>> id = "95479dbd-6a46-43e9-9b66-128dc2ab75f7";
        :>> title = "citationCheckHoldsWhereTheDecisionsLive: guard cli-surface-declared reads what a synopsis cites only in a tree that holds the engine's Decision channel, recognised by D0271 being present";
        :>> createdAt = "2026-09-09";
        :>> createdBy = "claudeOpus5";
        :>> status = DecisionStatus::accepted;
        :>> context = "issue433, Critical, tracked as dcCitationCheckHoldsWhereTheDecisionsLive. D0412 (issue423) added a check to guard cli-surface-declared at e902566: every dNNNN token in a CliCommand synopsis, in both fact homes, must have a file under .engine/decisions and must not be retired. The check ran in every tree. The Decisions a synopsis cites are the ENGINE's, and a downstream project's .engine/decisions holds THAT project's Decisions - keel init ships none - so every scaffolded tree read as citing twelve missing Decisions (d0301, d0323, d0296, d0356, d0338, d0311, in each home). CI was red for six consecutive pushes, e902566 through afd90d0: adoption_check_can_fail failed on the scaffold it builds and push_gate_is_withdrawn failed because keel land refused its fixture on the same twelve. D0412's consequences stated a limit (title citations not read) and did not state the tree the check applies to; this Decision states it.";
        :>> decision = "NOT A FORK: the DoD names one predicate and the guard has one place to apply it. The synopsis-citation check of cli-surface-declared runs only when decision_ids_present(root) contains d0271 - the Decision that made the CLI surface an authored fact, which exists exactly in the engine's own Decision channel. A tree without it (a keel init scaffold, a downstream project carrying its own d0001.., a test fixture shaped like the self-build) receives the surface, dispatch and help checks unchanged and no citation check. keel-cli/Cargo.toml is not the predicate: a fixture shaped like the self-build carries no Decisions either, and the property being checked is about where the cited Decisions live, not about what the tree builds. D0412 stands; this narrows the tree it reads.";
        :>> rationale = "A check that asks whether a citation resolves must run where the thing cited could be. Everywhere else its answer is a statement about the wrong tree: twelve violations in a scaffold say nothing about the engine's synopses and turned the one gate every downstream adopter runs red at init. The predicate is the fact the check depends on - the engine's Decisions are present - rather than a proxy for it, so the check cannot again fire where its answer is meaningless, and a tree that removed D0271 would lose the citation check rather than fail it, which is the honest reading. The two integration tests that went red are the known-positive that found this; the unit test citations_are_read_only_where_the_engines_decisions_live carries the known-negative (the engine's facts with no Decisions, 0 citation violations) and the known-positive (a 0271- file added, at least 12) per D0388.";
        :>> consequences = "guards.rs cli_surface_declared wraps the citation block in the d0271 predicate with the comment naming issue433; the unit test above is added beside the_live_synopses_cite_only_live_decisions; .engine/docs/guards.md states the tree the check reads. adoption_check_can_fail and push_gate_is_withdrawn pass again and CI is green on the landing commit, read from gh run list --json conclusion (issue434 is the separate defect in how that verdict was reported; D0420). This is a change to an enforced guard's scope - narrower in a downstream tree - so it carries #ProspectiveChange and waits for the human's word (D0337); the six red runs are the record of what the wider scope cost. What would change it: a downstream project that legitimately cites the engine's Decisions in its OWN CliCommand facts, which no project does today because the facts are the engine's and resync overwrites them.";
    }

    // acceptance event (D0121 review-queue sign-off; D0066/D0106 — human-judged, not fabricated)
    verification d0419Accept : Test { :>> id = "e36da13c-88fc-49a4-a28b-ade60c0bc142"; :>> method = VerificationMethod::confirmation; :>> procedureText = "Selected on the decision brief copy-out (fifteenth publish), pasted into chat 2026-09-11: the set of 33 HELD process-change ratifications accepted with one word, this record being one member (D0406 named it in the table). No note added. - their words, verbatim: “Accept the set: each of the 33 rules named in the table is recorded accepted on its own, quoting these words (recommended)” WARN: read-back - the quoted words do not name d0419 (D0201 B); recorded as given (D0423)."; }
    part d0419AcceptR1 : TestResult { :>> id = "f4d53064-c6ba-4812-afae-7298b6149ed2"; :>> outcome = VerdictKind::pass; :>> judgedAgainst = "3e6c518"; :>> judgedAt = "2026-09-11"; :>> judgedBy = "wweatherholtz"; :>> createdBy = "claudeOpus5"; }
}
