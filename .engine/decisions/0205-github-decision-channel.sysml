// D0205 (status: the `status` field below is the truth) — githubChannel: decisions become GitHub issues; a one-letter comment records them with a receipt, no hosting, machine off
// Recorded via `keel record decision` (D0105 RMWX axis; issue054). Acceptance is a separate explicit
// human gate (method=confirmation, D0106): flip status + add the d0205Accept event on sign-off.
package Decision0205 {
    private import EngineElement::*;
    private import EngineWork::*;
    private import EngineVerification::*;
    private import EngineRelationships::*;

    // #ProspectiveChange (D0070) - this Decision governs a process/schema change; the co-committed
    // change rides the process-change guard's hard lock.
    #ProspectiveChange part d0205 : Decision {
        :>> id = "600eb7d7-6048-4de6-849b-dfc2de2245fe";
        :>> title = "githubChannel: decisions become GitHub issues; a one-letter comment records them with a receipt, no hosting, machine off";
        :>> createdAt = "2026-08-23";
        :>> createdBy = "claudeFable5";
        :>> status = DecisionStatus::accepted;
        :>> context = "Their words, 2026-08-23: 'I have accepted these multiple times and it doesn't seem they're saving... we need a better way to interact... the Claude approach isn't consistent and even where it is, it isn't quite introspectable... I'd like them recorded directly from a deck, but recording in GitHub is fine too... interact automatically with this terminal client, that isn't required to be on the machine, without requiring us to host something that's accessible everywhere.' Ground truth behind the trigger: every tap HAD landed in the Smartsheet inbox - the defect was the missing feedback loop (a static page cannot change in front of them) plus three mutually opaque trust domains (artifact runtime, connector, keel), which a four-lens panel autopsied as structural, not fixable. Dossier: docs/reviews/interaction-channel-panel-2026-08-23.md.";
        :>> decision = "ADOPT THE GITHUB-NATIVE CHANNEL, panel-converged: (1) when a proposed Decision lands on main, an Action opens a GitHub ISSUE - short-name title, body = the decision's own plain-language context, options and costs, labeled blocks-work. (2) THE GESTURE: the human comments the option letter (A / B / accept / reject <why>) from the GitHub mobile app or by replying to the notification email; latest comment wins and every supersession is announced; reactions and checklists were evaluated and rejected (no event trigger / weak attribution). (3) THE RECORDER: a hardened Action (allowlisted login gate first, body via env with strict regex, permissions scoped per job, keel binary only - never an agent in the recording loop) runs keel accept with the actor mapped via a committed github-actors.toml, integrates merge-only, gates the merged tree, pushes, then posts a RECEIPT comment quoting exactly what entered git with the commit link, and closes the issue - the push-notified done-signal. Receipt ladder budget: eyes-reaction under 60s, recorded under 3min, close seconds later; a 10-minute sweeper re-drives missed events; every failure speaks in-thread, never silently. (4) THE BOARD is the issues list itself filtered is:open label:blocks-work - native state, no regenerated copies (the static-deck failure class), no hosting. (5) THE TERMINAL SESSION becomes sync-only for human judgment: keel sync picks up acceptances recorded while the machine was off; the session also sweeps unprocessed comments idempotently so Actions is a recorder, never a dependency. (6) AMENDS tap-to-sign (D0201 B): GitHub's 2FA-backed comment identity subsumes the device HMAC for this channel - the receipt is the re-fetchable comment id/URL, the guard verifies the actor id against the live comment, and the periodic human-signed ratification stays as the offline anchor; residuals (account compromise, a compromised workflow fabricating as the bot) recorded plainly. (7) The Smartsheet inbox and artifact-deck save path RETIRE after one end-to-end dry run; keel deck survives as a computed view.";
        :>> rationale = "Scores 9-10 of 10 on every stated constraint: recorded in GitHub natively; zero self-hosted components; works with the machine off (durable compute fires on the event); introspectable end to end - the comment, the workflow file, the run log, the commit, the receipt are all plain inspectable artifacts, replacing three opaque trust domains with one. The gesture surface and the done-signal live in the same thread, so the did-it-save question cannot arise: silence within budget is itself reported as a failure.";
        :>> consequences = "Three workflow files, one actor-mapping contract, issue templates; the deck's tap machinery retires; the D0201 amendment rides this decision; the local console and chat channels remain for when the machine is on. REJECTING keeps the Smartsheet path with its structural opacity, stated.";
    }

    // acceptance event (D0121 review-queue sign-off; D0066/D0106 — human-judged, not fabricated)
    verification d0205Accept : Test { :>> id = "37eafadf-a30b-41b1-9fad-d086cd1060b6"; :>> method = VerificationMethod::confirmation; :>> procedureText = "Accepted. Their words, verbatim: 'yep let's go' (chat, 2026-08-23), in direct response to the presented githubChannel design and dry-run plan."; }
    part d0205AcceptR1 : TestResult { :>> id = "92ecba69-e981-4638-b1a8-5ebaa9b4e643"; :>> outcome = VerdictKind::pass; :>> judgedAgainst = "f51da89"; :>> judgedAt = "2026-08-23"; :>> judgedBy = "wweatherholtz"; }
}
