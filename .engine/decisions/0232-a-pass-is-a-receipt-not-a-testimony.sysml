// D0232 (status: the `status` field below is the truth) — evidenceCited: an AI-judged test result records what it ran, and the over-claim rate becomes a measured number instead of a policed sentence
// Recorded via `keel record decision` (D0105 RMWX axis; issue054). Acceptance is a separate explicit
// human gate (method=confirmation, D0106): flip status + add the d0232Accept event on sign-off.
package Decision0232 {
    private import EngineElement::*;
    private import EngineWork::*;
    private import EngineVerification::*;
    private import EngineRelationships::*;

    // #SafetyChange (D0070) - this Decision governs a process/schema change; the co-committed
    // change rides the process-change guard's hard lock.
    #SafetyChange part d0232 : Decision {
        :>> id = "72f1059f-6b1c-4309-b3bd-5afddf804b8b";
        :>> title = "evidenceCited: an AI-judged test result records what it ran, and the over-claim rate becomes a measured number instead of a policed sentence";
        :>> createdAt = "2026-08-25";
        :>> createdBy = "claudeFable5";
        :>> status = DecisionStatus::accepted;
        :>> context = "The human named the problem directly: I very often over-claim - one test for one scenario, reported as though the thing were now perfect - and said they expect an AI to be overconfident, so the question is how to improve attestation SYSTEMICALLY. Measured: of 5,135 recorded TestResults, exactly ONE recorded what produced it. A result carries outcome, judgedBy, judgedAt and judgedAgainst - so every pass in this model is a TESTIMONY that no third party can re-derive, and the actor doing the work also authors the verdict AND the sentence describing it. The 3.9 percent fail rate across 5,120 results is not a quality signal; it is the signature of a system recording that work happened. They also corrected the aim: I am not here to constrain and check THEM, I am here to constrain and check other work.";
        :>> decision = "Guard 52, evidence-cited: an AI-judged method=test result must carry a `// RAN:` receipt naming what produced the verdict, written by `append-result --evidence` as a structured comment rather than a schema field, since schema/core is frozen. A HUMAN-judged result is NEVER IN SCOPE - not exempted as a courtesy but excluded by design, because a human's word IS the evidence and demanding a receipt from them would point the control at the wrong party. Forward-only from 2026-08-25. Alongside it, `keel attestation` reports the census: results by judge kind, how many EXERCISED claims carry a receipt, and the fail rate, so the over-claim rate is a number anyone can read.";
        :>> rationale = "The gate had to be STRUCTURAL rather than linguistic, and that conclusion is measured rather than preferred. Three attempts to gate the WORDING of a verdict were calibrated against the real corpus and all three failed: a verdict word with no number in its field flagged 111 items, nearly all terse old backlog prose; an unqualified universal (perfect, cannot fail, guaranteed) flagged 35, nearly all CRITIQUES using the phrase to criticise vacuity; and a rule requiring a coverage claim to cite something re-runnable ran at 0 percent precision on live data - both of its hits were me DESCRIBING the claim pattern rather than making a claim, and narrowing it to claims naming a tracked item still left a false positive, because a 400-character window over a 1,500-character gate field always contains some issue id. A blocking guard at that precision teaches the author to route around the write path, which is where every other check lives, and D0214 already argues the fix must be subtractive because this engine detects more than it triages. Structure, by contrast, is decidable: whether a result records a command is not a matter of tone. And the human-only exclusion is what keeps the control aimed at the party it can legitimately bind.";
        :>> consequences = "The reported verification numbers will get WORSE, and that is the intended effect: a great deal of what I have been stamping method=test was one manual observation, and it now either carries a receipt or is honestly an inspection. The census reads 4,749 AI-judged results, 1,146 of them EXERCISED, with 0 percent carrying a receipt - the first honest measurement of the gap, against 318 human judgments correctly out of scope. THE THIRD CONTROL WAS NOT BUILT AS ASKED and this is the honest record of that: verdict-wording policing does not calibrate here, so it ships as part of the census indicator instead of a guard, with the false-positive counts recorded so the decision can be re-argued rather than re-guessed. STATED RESIDUAL: none of this constrains what I say in chat, which is where the human actually experiences the over-claiming - CLAUDE.md already concedes no gate can read conversational output (D0151) - so the only lever there is indirect, making the RECORD specific enough that a vague prose claim reads as thinner than the record it summarises. Verified: the guard fired immediately on my own five results from twenty minutes earlier and they now carry real receipts; tested in four directions including that a human's attestation is not even scanned. Resolves issue266.";
    }

    // acceptance event (D0121 review-queue sign-off; D0066/D0106 — human-judged, not fabricated)
    verification d0232Accept : Test { :>> id = "64bc32f2-9f42-4dea-b474-3f9a5b369e0d"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0232AcceptR1 : TestResult { :>> id = "bf974305-8094-4097-9535-4627c87ded3c"; :>> outcome = VerdictKind::pass; :>> judgedAgainst = "c84671a"; :>> judgedAt = "2026-08-25"; :>> judgedBy = "wweatherholtz"; }
}
