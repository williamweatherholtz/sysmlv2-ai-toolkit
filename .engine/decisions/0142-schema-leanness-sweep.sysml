// D0142 — Dead and stale schema removed from frozen schema/core: 19 never-instantiated types, a
// duplicate Release, a port def contradicting D0100, and the stale claims inside it.
// #ProspectiveChange (D0070): nothing authored under the prior schema is invalidated.
package Decision0142 {
    private import EngineElement::*;
    private import EngineWork::*;
    private import EngineVerification::*;
    private import EngineRelationships::*;

    #ProspectiveChange part d0142 : Decision {
        :>> id = "9d41b6e8-05fa-4c37-8b92-6e13a70cf25d";
        :>> title = "D0142: schema leanness sweep — 19 dead types, the duplicate Release, the D0100-contradicting port def, and stale claims removed";
        :>> createdAt = "2026-08-14";
        :>> createdBy = "claudeOpus5";
        :>> status = DecisionStatus::accepted;
        :>> context = "The three-critic panel's non-marker findings, which all three rated more consequential than the marker count the human originally asked about. Each was RE-MEASURED before any change, as dcSchemaLeannessSweep required. (a) TWO live `Release` types — `part def Release` (work.sysml) and `occurrence def Release` (baseline.sysml) — and `.engine/workflows/deploy.sysml` imported the FIRST, threading it through four action signatures, while all 7 authored releases bind the second. The Deploy workflow declared an artifact type nobody produced. (b) NINETEEN types with zero DECLARATIONS anywhere: Task, Epic, Assumption, ComponentRequirement, TestPlan, Risk, Mitigation, DesignElement, FunctionAllocation, InterfacePort, Agent, Role, WorkflowDefinition, MaintainerVP, OutstandingView, SuspectView, TraceView, RequirementCoverage, SuspicionSweep. This contradicts the repo's OWN recorded policy at rules.sysml:63-66, where `OrderingRule` was removed as dead schema with the explicit rule 're-add it THEN, with an instance'. (d) `port def InterfacePort` and `port ifaces : InterfacePort[*]` sat in schema/core while ACCEPTED D0100 states 'No ports/interfaces enter schema/core', and the `#View item def ICD` COMMENT advertised a computation over ports and connections when the repo contains ZERO `connect` statements — the type itself is consumed by the Architecture workflow and stays. (f) Stale claims INSIDE frozen schema: `query.py` cited 8 times though retired at D0074, rules.sysml:5 claiming '14 guards' against the real 28, and an `EdgeKind` comment labelling `verifyEdge` a typed native edge when verify is a metadata marker. (g) The 17th marker `metadata def View` lived in workflows/_meta.sysml, whose own header says it holds workflow-local artifact types only, so an audit from relationships.sysml undercounted the custom vocabulary by one marker and 73 uses.";
        :>> decision = "(A) Delete all 19 never-instantiated types. (B) Delete `part def Release` from EngineWork and retarget deploy.sysml to `EngineBaseline`, the type every authored release actually binds. (C) Delete `port def InterfacePort` and the `port ifaces` member on Component — D0100 already decided this and the schema had not followed. `#View item def ICD` is RETAINED: the panel called it uncomputable, which is true, but `architecture.sysml:19` declares `out icd : ICD`, so it is an unbuilt capability with a real consumer rather than dead schema. I deleted it first and the KERNEL caught it; the reference check that cleared the other deletions was scoped to schema/views/rules and did not cover workflows. (D) Correct the stale claims: `query.py` citations become the `keel` commands that exist, the guard count becomes 28, and the EdgeKind comment states plainly that satisfy/allocate/dependency are native while verify/supersede are markers, so the `Edge` suffix reads as reserved-word avoidance rather than a claim of nativeness. (E) Move `metadata def View` into relationships.sysml, the declared marker home. (F) Deletions leave NO tombstones (the standing rule): the record of what was removed and why is this Decision, not a comment in the file.";
        :>> rationale = "Dead schema is not free. Every downstream project carries it into its own `.engine/`, a standard viewer renders it as empty definitions, and it dilutes what the type surface communicates — `Epic` and `Task` sitting beside `Story` implies a three-level hierarchy this project has never used, and `Risk`/`Mitigation` imply a risk register that does not exist. The removal is also the repo APPLYING ITS OWN PRECEDENT rather than a new judgement: rules.sysml:63-66 already recorded exactly this rule for `OrderingRule`, and 19 types had accumulated in violation of it. ON `Assumption` SPECIFICALLY, because it is the one genuine loss: requirements.sysml argued it was 'first-class because when an assumption BREAKS, everything derived from it goes suspect — a high-value input to the suspicion engine'. That capability is real and was never built in the year the type existed. Keeping an unused type does not preserve the capability; re-adding the type WITH its first instance and the suspicion wiring does, and the precedent says exactly that. WHAT THIS SWEEP DELIBERATELY DOES NOT DO: it does not retype `Process`/`ProcessStep` to `action def`, and it does not convert the ~3000 string provenance fields to `ref Actor`. Both are correct diagnoses from the panel and both are large migrations over instance data requiring D0067's gated expand/migrate/contract with reconciled control totals. Bundling a 3000-edit data migration into a dead-code deletion would make the deletion unreviewable and the migration unverifiable. They stay tracked as separate items. VERIFIED rather than asserted: `.engine` and `.tracking` validate clean, all 28 guards pass, and a fresh `keel init` project still passes its OWN full gate — which is the only test that matters, since a downstream project is the thing this schema is shipped to.";
        :>> consequences = "schema/core loses 19 type definitions, one duplicate `Release`, one `port def` and one port member; `.engine/workflows/_meta.sysml` loses the `metadata def View` declaration, which moves to relationships.sysml, and gains an import of that home plus an honest comment on ICD; deploy.sysml imports EngineBaseline. Marker inventory is unchanged at 17 and now declared in ONE place. Doc prose naming deleted types is corrected in the same commit. Marked #ProspectiveChange (D0070): nothing authored under the prior schema is invalidated, because every deleted type had zero instances by measurement — the sweep cannot orphan work that never existed. Frozen-schema sign-off is carried by the human's acceptance recorded in the d0142Accept event. STILL OPEN, tracked separately: Process-as-behaviour (`action def`), provenance-as-`ref Actor`, and `.engine/workflows` absent from the Model (issue104).";
    }

    verification d0142Accept : Test { :>> id = "4e7a91c2-3d68-4b05-a19f-82c604d5e731"; :>> title = "Human acceptance of d0142 (frozen schema/core, §2.5)"; :>> createdAt = "2026-08-14"; :>> createdBy = "claudeOpus5"; :>> method = VerificationMethod::confirmation; :>> procedureText = "wweatherholtz, 2026-08-14, verbatim: 'let's do it!' — given in direct reply to my statement that the remaining frontier items all touch FROZEN schema/core, naming specifically the deletion of dead types, retyping Process, and converting ~3000 provenance strings, and noting that unlike the preceding work these are not reversible by a follow-up commit. §2.5 requires explicit human sign-off for a schema/core change and this is it. SCOPE: this attestation covers the DELETION sweep recorded here. It does not cover the Process-to-action-def retype or the provenance migration, which this Decision explicitly excludes and which remain tracked as separate items — the human also asked in the same message for a summary to review, so those two are deliberately left for that review rather than folded in."; }
    part d0142AcceptR1 : TestResult { :>> id = "b70c8e35-9a24-4f61-83d7-1c5b0942ae68"; :>> outcome = VerdictKind::pass; :>> judgedAgainst = "628c1fd"; :>> judgedAt = "2026-08-14"; :>> judgedBy = "wweatherholtz"; }
}
