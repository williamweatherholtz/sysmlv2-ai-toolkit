// D0276 (status: the `status` field below is the truth) — Migrate tolerates a NEW engine-written obligation record, and names the ones it tolerated
// Recorded via `keel record decision` (D0105 RMWX axis; issue054). Acceptance is a separate explicit
// human gate (method=confirmation, D0106): flip status + add the d0276Accept event on sign-off.
package Decision0276 {
    private import EngineElement::*;
    private import EngineWork::*;
    private import EngineVerification::*;
    private import EngineRelationships::*;

    // #SafetyChange (D0070) - this Decision governs a process/schema change; the co-committed
    // change rides the process-change guard's hard lock.
    #SafetyChange part d0276 : Decision {
        :>> id = "524dd545-6eb3-47e2-90f0-f1ff16b1b75b";
        :>> title = "Migrate tolerates a NEW engine-written obligation record, and names the ones it tolerated";
        :>> createdAt = "2026-09-01";
        :>> createdBy = "claudeOpus5";
        :>> status = DecisionStatus::accepted;
        :>> context = "Three individually-correct controls composed into a lock with no non-bypassing exit, reported by a downstream session because this repository structurally cannot reach it. Migrate refuses a dirty tree, and its git status sees UNTRACKED files, so one brand-new file is enough. Committing that file to clean the tree fails, because the pre-commit gate runs validate and validate REFUSES under engine-version skew (D0251). Skew clears by running the pinned binary or by migrating, and migrating is the first step. The file that springs it is written BY THE ENGINE - record_obligation under D0176/K7, whose own doc comment reasons about deadlock at the FILE level and misses it at the TREE level - and it fires preferentially when a project is ALREADY unhealthy, because that is when an obligation gets recorded. The human's escape was git stash push -u, which works and bypasses nothing; the outcome worth preventing is the contributor who reaches for --no-verify instead and disables every other check to get past one.";
        :>> decision = "check_preconditions tolerates an uncommitted entry when it is NEW (untracked, or staged-add) AND sits under .tracking/obligations/ AND ends .sysml. Everything else still refuses. The tolerated entries are RETURNED rather than swallowed, and migrate prints them: an exemption nobody is told about is indistinguishable from a check that quietly stopped working. The status query also moves to -uall, because git COLLAPSES a wholly-untracked directory into a single entry and a per-file decision is impossible without it.";
        :>> rationale = "WHY A CARVE-OUT IS LEGITIMATE HERE AT ALL, on migrate's own stated reasoning: the refusal exists because a half-migrated tree mixed with uncommitted edits cannot be told apart afterwards. A brand-new file in a directory nothing but the engine writes CAN be told apart. That is the whole justification, and it is also why the test is exactly this narrow - the property being relied on is additivity and separability, so anything that is not purely additive falls outside it. Hence NEW only: a MODIFIED obligation record is a hand-edit, no longer separable, and stays refused. REJECTED, having the recorder STAGE its own file: it does not help, because staged is still uncommitted and git status reports it either way - this was checked rather than assumed. REJECTED, degrading the pre-commit gate to a warning under pure skew: it weakens one control to work around another, which is how a control gets hollowed out one exception at a time, and the gate being degraded is the one that catches dishonest state. WHAT THE TEST FOUND THAT REASONING DID NOT: the first implementation was correct in principle and did nothing, because git reported `?? .tracking/obligations/` - the directory, with no filename - so the per-file predicate never matched. Only running it against real git surfaced that, which is the argument for the fixture work this Decision sits beside.";
        :>> consequences = "A project behind its pin holding only engine-written obligation records can migrate, and is told which files it moved with. Four cases hold it, and two of them exist to prove the carve-out stayed NARROW rather than to prove it works: any other uncommitted .tracking file still refuses and still names what blocked it, and a modified obligation record is not tolerated. ARMED (D0253): the escape and the naming cases were both observed FAILING against the pre-fix binary, with the deadlock's own refusal text in the failure output. A NOTED GAP, recorded because it is adjacent and I found it while checking whether this change needed a signed Decision: migrate's refusals are safety controls that srMigrationIsReversible depends on, and migrate.rs is NOT on D0209 clause 2's enforcement surface - only guards.rs, adherence.rs, .githooks/ and the CI workflows are. So this weakening could have been made with no Decision at all. That is a real hole in the keystone lock's coverage; this Decision is recorded voluntarily rather than because a gate demanded it, and the coverage question is left open rather than answered here, since widening the locked set to all of keel-cli/src would make every code change need a signature.";
    }

    // acceptance event (D0121 review-queue sign-off; D0066/D0106 — human-judged, not fabricated)
    verification d0276Accept : Test { :>> id = "7d3dd6b1-c024-41c1-acfc-e183157af697"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0276AcceptR1 : TestResult { :>> id = "34048c09-5e48-424c-af6c-25c72b7b9672"; :>> outcome = VerdictKind::pass; :>> judgedAgainst = "21cdce7"; :>> judgedAt = "2026-09-01"; :>> judgedBy = "wweatherholtz"; }
}
