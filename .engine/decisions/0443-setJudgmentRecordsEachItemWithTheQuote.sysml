// D0443 (status: the `status` field below is the truth) — A human judges a SET of proposed results in one sitting; every item is recorded on its own, quoting them
// Recorded via `keel record decision` (D0105 RMWX axis; issue054). Acceptance is a separate explicit
// human gate (method=confirmation, D0106): flip status + add the d0443Accept event on sign-off.
package Decision0443 {
    private import EngineElement::*;
    private import EngineWork::*;
    private import EngineVerification::*;
    private import EngineRelationships::*;

    // #ProspectiveChange (D0070) - this Decision governs a process/schema change; the co-committed
    // change rides the process-change guard's hard lock.
    #ProspectiveChange part d0443 : Decision {
        :>> id = "6c07389a-0b16-4dc7-8ac8-9af818001da9";
        :>> title = "A human judges a SET of proposed results in one sitting; every item is recorded on its own, quoting them";
        :>> createdAt = "2026-09-11";
        :>> createdBy = "claudeOpus5";
        :>> status = DecisionStatus::accepted;
        :>> context = "D0312 option B left the human's judging half unbuilt: an AI-examined pass (demo, analyze, inspect) lands as VerdictKind::proposed and counts as done for nothing, and there is no write path by which a human judges it. Today 26 proposed results stand under .tracking (keel attestation --json, 2026-09-11, the ceremony gates of sprints 663-667) and the only way to close one is a hand-edited result line. D0312 B said how the human judges: a SET in one sitting - one card, one command - so they are not hammered per item, while each item is recorded INDIVIDUALLY with its own result and its own quote receipt, because issue158 was exactly a COUNT accepted as one card with no per-item record. B also said the human SAMPLES rather than judges every set. The pieces exist apart: keel accept's channel rules (delegation, quoted words, gesture citations written by the surface that saw them, D0289/D0411/D0423), the D0198 companion shape <test>Attest<N> that the confirmation substance rule already recognises, the attestation census that counts proposed, and the deck whose taps a paired device signs (D0334/D0335).";
        :>> decision = "keel judge-set <file> --words '<their words>' --by <human> --date YYYY-MM-DD [--verdict pass|fail] [--fail <test>,..] [--all] records the human's verdict on the SAMPLED proposed results in one .tracking file - a sprint record or the backlog - writing for EACH item its own TestResult (outcome pass or fail, judgedBy the human, createdBy the recorder, judgedAgainst HEAD) and its own <test>Attest<N> companion (method confirmation) whose procedureText quotes the human verbatim inside the declared pair, so every item carries the D0198 receipt on its own line and no count is ever accepted as a card. The set is computed, never chosen: attestation-policy.toml's [proposedJudgment] section declares sampling as a share ('50%') or a count per file (3); a file's proposed results are ordered by their result uuid - a v4 uuid is a uniform random order nothing authored - and the first ceil(share x n) or min(count, n) are the sample, with every proposal a human has already judged counted in the sample first so sampled is never below judged; an absent rule samples everything. keel attestation reports proposed, sampled and judged as three separate numbers beside the by-judge census. The channel rules are keel accept's, parametrised: from an agent session the write needs the confirmationRecord delegation and the human's quoted words, refusing no-quote and no-delegation with a judge-set ledger line; the read-back WARN does not apply because the subject is a file, not a Decision. The deck grows one card per file with a sampled set awaiting judgment, tapping through /api/judge-set with the device receipt appended by the server exactly as an acceptance tap is. judge-set joins HUMAN_ONLY_WRITE_COMMANDS: the write layer refuses an AI-kind judge before any line is built.";
        :>> rationale = "One item, one record, one quote is the issue158 lesson and D0312 B's explicit clause; the card and the command are only how the human reaches the set in one sitting. Ordering by result uuid makes the sample deterministic for the reader and unchoosable by the writer: the census and the command compute the same set from the same tree, and no agent can steer which of its proposals a human will read. Counting judged proposals into the sample first keeps the three numbers coherent when a later proposal shifts the order. Reusing keel accept's channel refusal rather than a new one keeps the census's write-path rows honest: the same two controls, the same subject (the agent's act), one more verb they bind. NOT A FORK: D0312 B chose the set-with-individual-records shape and the sampling; this Decision is that clause's write path and names the one place the chosen shape needed a rule of its own (how the sample is drawn).";
        :>> consequences = "Process-change: a new write verb and a new policy key, and two census write-path rows (judge-set:no-quote, judge-set:no-delegation) - held proposed for the human's word (D0337). keel-cli/src: attestation.rs gains proposals/sample/the three counts; write.rs gains judge_set and adds judge-set to HUMAN_ONLY_WRITE_COMMANDS; main.rs gains cmd_judge_set and verdict_channel_refusal takes the delegation class and an optional read-back subject; deck.rs and serve.rs gain the judgment card and /api/judge-set; cli_facts.rs, cli_surface.rs and .engine/cli/commands.sysml declare the verb. This project's policy declares sampling = '50%' under [proposedJudgment]; keel init ships the section commented like the grants, since the share is the human's load and theirs to set. The D0388 pair lives in attestation.rs: six proposals under a 50% rule sample three and judge none; the same tree with one human result samples three and judges one; a tree of passes proposes nothing. What this does not do: it does not judge the proposals already standing - that is the human's, one set at a time - and it does not make a proposed result count as done; only the human's recorded pass does that, as D0312 B said.";
    }

    // acceptance event (D0121 review-queue sign-off; D0066/D0106 — human-judged, not fabricated)
    verification d0443Accept : Test { :>> id = "c08a5049-055d-446c-8e7d-b155d419e6ce"; :>> method = VerificationMethod::confirmation; :>> procedureText = "Selected on the decision brief copy-out (fifteenth publish), pasted into chat 2026-09-11: the set of 33 HELD process-change ratifications accepted with one word, this record being one member (D0406 named it in the table). No note added. - their words, verbatim: “Accept the set: each of the 33 rules named in the table is recorded accepted on its own, quoting these words (recommended)”"; }
    part d0443AcceptR1 : TestResult { :>> id = "330caa78-e97e-4507-bb87-61db72a03e55"; :>> outcome = VerdictKind::pass; :>> judgedAgainst = "3e6c518"; :>> judgedAt = "2026-09-11"; :>> judgedBy = "wweatherholtz"; :>> createdBy = "claudeOpus5"; }
}
