// D0173 — PROPOSED. The obligation-review process delivers mobile verdicts through the viewer's own
// connector (the artifact mcp capability) with a store-side receipt; the live-doc mechanism is retired.
// #ProspectiveChange (D0070).
package Decision0173 {
    private import EngineElement::*;
    private import EngineWork::*;
    private import EngineVerification::*;
    private import EngineRelationships::*;

    #ProspectiveChange part d0173 : Decision {
        :>> id = "3d4c0fb4-8ad6-4495-c76c-ebfe69ad322f";
        :>> title = "D0173: mobile verdicts travel as connector-inbox rows with a receiver-side receipt — the live-doc mechanism is retired";
        :>> createdAt = "2026-08-21";
        :>> createdBy = "claudeOpus5";
        :>> status = DecisionStatus::accepted;
        :>> context = "THEIR TWO CONSTRAINTS CLOSED THE DESIGN SPACE. #1, verbatim: 'they're not recoverable it seems. nothing is there' - the live-doc appends were absent from their own phone's page, so the write itself dropped (issue194), upgrading issue193's write-only finding to write-DROPPED and killing any salvage of that mechanism. #2, verbatim: 'can't do- the device I remote control from can't be guaranteed to be on my vpn' - closing the tunnel-to-keel-serve option issue193 had recorded as theirs to choose. Then: 'just make the remote artifact pipeline worked. test again if you made fixes.' What remains must work from any network AND carry an acknowledgment the receiver side can check.";
        :>> decision = "PROPOSED: the deck's mobile transport is the artifact mcp capability calling the viewer's OWN Smartsheet connector. Each tap delivers one ROW to the keel-deck-inbox sheet (config in .engine/contracts/deck-inbox.toml; sheet and workspace created for this purpose); the STORE's reply - a row id - is the receipt the page shows, labelled 'delivered to inbox row N' per the label ladder (never 'saved': that word stays reserved for the local transport's write-API 200 plus computed-view read-back). The AI session pulls Processed=false rows and records them through the write API via .engine/tools/deck_inbox_record.py, verifying EVERY row from the computed view before marking it processed; duplicates dedup by latest-At per (uid, kind), which makes the page's re-tap-on-ambiguous-outcome advice safe. The orPublish and orRecord steps of the obligation-review process now say exactly this. The live-doc mechanism is RETIRED and pinned out by a test.";
        :>> rationale = "WHY A CONNECTOR STORE RATHER THAN ANOTHER PAGE MECHANISM: the five-version failure series and issue193/194 establish that a transport whose only witness is the sender cannot carry a save claim; the store's row id is a genuine receiver-side acknowledgment, and the pull side is machine-testable end to end - the rehearsal ran the actually-delivered row through a served copy and read the disposition back from the computed view. WHY SMARTSHEET SPECIFICALLY: it is a connector the viewer already holds, its add_rows tool acks with row identity, and the capability contract's observe-before-publish rule was satisfiable in-session. WHY THE CONFIG IS ALL-OR-NOTHING: a partial config yielding a half-working transport is the D0132 lesson; the page claims NO transport instead. WHY THE HUMAN GATE IS UNCHANGED: rows carry By, and the server-side Person enforcement on human-gated writes still refuses an AI - the transport moves bytes, never authority.";
        :>> consequences = "IF ACCEPTED: mobile taps arrive with receipts; the session's pull-record-verify-mark loop becomes part of the obligation-review procedure; the deck page cannot be shared publicly while it declares the mcp capability (acceptable: it is the sole reviewer's private queue). COSTS, stated: the inbox adds a third-party store to the pipeline (contents: item uid/name, verdict, note, reviewer name, HEAD sha - no deliverable content beyond titles already in git); the viewer consents to the connector on first tap; and the in-page callTool leg remains field-tested only, mitigated by per-code error states that name their own fix. IF REJECTED: the deck reverts to local-transport-only and mobile queue review waits for an infrastructure route that satisfies constraint #2. REMOVAL PATH (D0163): delete deck-inbox.toml (the page then claims no mobile transport), deck_inbox_record.py, the two process-step sentences, and the sheet; supersede this Decision.";
    }

    // acceptance event (D0121 review-queue sign-off; D0066/D0106 — human-judged, not fabricated)
    verification d0173Accept : Test { :>> id = "3f82fe7d-3386-4fd7-b493-31b36ae5f04d"; :>> method = VerificationMethod::confirmation; :>> procedureText = "wweatherholtz tapped Sign on the d0173 card in the obligations deck (deck HEAD c9999aa), delivered through the connector inbox as row 4837717745729412 at 2026-08-21T14:23:43Z with no per-item note. The card stated the Decision's full title - mobile verdicts travel as connector-inbox rows with a receiver-side receipt; the live-doc mechanism is retired - so the tap is their sign-off on that specific claim. THIS ACCEPTANCE IS ITSELF THE TRANSPORT'S FIRST FIELD TEST: the signature accepting the inbox pipeline arrived through the inbox pipeline, with the store's row id as its receipt, and was verified from the computed view before recording was reported."; }
    part d0173AcceptR1 : TestResult { :>> id = "a1f4d7c1-f751-4c08-bb1a-cd8c4590c893"; :>> outcome = VerdictKind::pass; :>> judgedAgainst = "d24d52d"; :>> judgedAt = "2026-08-21"; :>> judgedBy = "wweatherholtz"; }
}
