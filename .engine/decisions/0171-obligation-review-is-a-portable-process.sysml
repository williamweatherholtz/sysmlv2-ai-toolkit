// D0171 — PROPOSED. The obligation deck becomes a declared PROCESS, so it travels to any project that
// uses keel; a Decision is SIGNED rather than voted on; and copy-paste stops being a route.
// #ProspectiveChange (D0070).
package Decision0171 {
    private import EngineElement::*;
    private import EngineWork::*;
    private import EngineVerification::*;
    private import EngineRelationships::*;

    #ProspectiveChange part d0171 : Decision {
        :>> id = "2c74e0b9-5a38-4d16-9f42-71ca85be3d07";
        :>> title = "D0171: obligation review is a declared, portable process — a signature is not a verdict, and copy-paste is not a route";
        :>> createdAt = "2026-08-20";
        :>> createdBy = "claudeOpus5";
        :>> status = DecisionStatus::accepted;
        :>> context = "THEIR INSTRUCTION, verbatim: 'we need to cement the mobile, automatic-feedback (NO copy paste), claude-hosted artifact skill, that clearly delineates decisions AI skill, so we can reuse it anywhere keel is used'. THREE OF THE FIVE PROPERTIES ALREADY HELD and are worth stating so the change is not larger than it needs to be: the deck is already mobile-first (a 680px fluid column, a device-width viewport, no fixed layout), already published as a Claude-hosted artifact, and already a LIVE DOC - the `artifact` capability means a verdict or a note is appended as the viewer at the moment of the gesture. TWO DID NOT HOLD. (1) IT WAS NOT REUSABLE, because it was a SKILL with no PROCESS behind it. D0128 makes a process the movable unit - `keel process export` and `keel activate` operate on processes - so a skill deploying nothing cannot travel: a downstream project would have to copy a python file by hand and know it existed. (2) COPY-PASTE WAS STILL A ROUTE. The `Copy for Claude` button sat in the bottom bar of every view including a fully writable one, so the reader was taught that copying is what they are meant to do - a habit the live doc exists to remove, and which they have now asked to be rid of twice.";
        :>> decision = "PROPOSED, in three parts. (A) A PROCESS, `.engine/processes/obligation-review.sysml`, with five steps: compute the obligation set from the declared views rather than enumerating it; DELINEATE signatures from judgments; publish as a live document; record each judgment through the write API with their words verbatim; read the queue back from the computed view. The skill's registry purpose now names the process file, satisfying the D0059 convention, and the catalogue goes from 19 processes to 20 with every one still having a deploying skill. (B) A DECISION IS SIGNED, NOT VOTED ON. An acceptance card now carries the verb `Sign`, a heavier left rail, and a `needs your signature` ribbon; every other class keeps `Accept`. The distinction is structural rather than a hue, because a colour is a legend lookup and the reader should not have to consult a legend to notice that a card needs their name on it. (C) THE COPY FALLBACK IS HIDDEN unless the view genuinely cannot write. It is not deleted - a read-only viewer has no other way to return anything, and there it is the only thing that works, so it appears exactly then.";
        :>> rationale = "WHY THE SIGNATURE DISTINCTION IS THE PART THAT MATTERS MOST, and it is not aesthetics. Every non-acceptance class asks for a judgment an AI could in principle have formed and is merely deferring to a human. An acceptance asks for something an AI may NEVER supply: section 4 says a `method=confirmation` result records a human's word and cannot be inferred from an instruction, from the work being done, or from my own judgment. Rendering those two identically on the same card, with the same green button, is precisely the confusion that produced issue144 - where I turned an instruction into a recorded attestation by mechanical substitution. The deck is the surface where that confusion is cheapest to make and most expensive to catch, because the human's tap is the only evidence that ever existed. WHY A PROCESS RATHER THAN A BETTER SKILL: D0040 says a recurring task without a skill leaks process knowledge into conversation history. A skill without a process leaks it one level up - into THIS repository. The deck's five steps are the reusable part, and a project that adopts the process gets the steps, the skill and the generator as one unit with a removal path, instead of a python file someone copied.";
        :>> consequences = "IF ACCEPTED: 20 declared processes, all with deploying skills (`process-skill` PASS, 20 scanned). The generated deck renders 45 cards - 4 acceptance with `Sign`, 41 with `Accept` - verified by counting the emitted HTML rather than by reading the generator. A downstream project runs `keel activate obligation-review` and has the whole surface. WHAT THIS DOES NOT FIX, and it is the honest limit: the deck can only carry a judgment BACK if the viewer holds the write grant. A read-only viewer still has the copy fallback and always will, because there is no third option - and that fallback is now invisible until it is the only thing that works, which means a reader who needs it sees it and a reader who does not is never taught the habit. ALSO UNFIXED: the deck reports what is waiting, and nothing forces a human to look. `keel hook stop` already advises when obligations exist and no console answers (issue150); it does not know about the deck, and wiring it to publish one automatically is a separate proposal I am NOT making here, because a hook that publishes artifacts unasked is a different kind of change. REMOVAL PATH, per D0163: delete the process file, the skill directory, the generator and the registry entry. Nothing else reads any of it; the obligation VIEWS it consumes are independent and stay.";
    }

    // acceptance event (D0121 review-queue sign-off; D0066/D0106 — human-judged, not fabricated)
    verification d0171Accept : Test { :>> id = "720dc151-4217-4a70-b757-ad62ef7d84dc"; :>> method = VerificationMethod::confirmation; :>> procedureText = "Their words, verbatim: 'accept all. proceed'. Said in response to the queue of six proposed Decisions presented for signature - D0167, D0168, D0169, D0170, D0171, D0172 - so 'all' is that queue and this acceptance covers d0171 as one of the six. For D0170 the acceptance includes the Decision's stated lean, retire."; }
    part d0171AcceptR1 : TestResult { :>> id = "f3611979-4216-4a1d-880f-c95175f97269"; :>> outcome = VerdictKind::pass; :>> judgedAgainst = "3abc583"; :>> judgedAt = "2026-08-20"; :>> judgedBy = "wweatherholtz"; }
}
