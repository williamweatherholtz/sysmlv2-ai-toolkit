// D0384 (status: the `status` field below is the truth) — supersessionHome: which representation of a Decision's supersession is authoritative - the status field, the Supersede edge, or both held equal by a guard
// Recorded via `keel record decision` (D0105 RMWX axis; issue054). Acceptance is a separate explicit
// human gate (method=confirmation, D0106): flip status + add the d0384Accept event on sign-off.
package Decision0384 {
    private import EngineElement::*;
    private import EngineWork::*;
    private import EngineVerification::*;
    private import EngineRelationships::*;

    // RESEARCH: Census of .engine/decisions on 2026-09-08 (scratchpad supersede_census.py, re-runnable): 382 Decisions - 373 accepted, 7 superseded, 2 rejected; 57 #Supersede edges of which 10 target a Decision and 45 target a need or requirement. The two representations disagree in 11 records: 7 ACCEPTED Decisions carry an incoming Supersede edge and stay in force (d0114, d0115, d0129, d0175, d0178, d0205, d0351 - each edge reverses one clause, d0149 -> d0129 leaves never-rebase standing), and 4 status=superseded Decisions have NO incoming edge (d0003, d0038, d0069, d0071 - the superseder is named only in a trailing comment). The write path records the edge and never touches the target (keel-cli/src/write.rs:1607-1623); the queue reads status alone (view/mod.rs:2184 pending_acceptances -> proposed_decisions). So today an edge means 'reverses something in the target', not 'retires it', and only the status says retired.
    // #ProspectiveChange (D0070) - this Decision governs a process/schema change; the co-committed
    // change rides the process-change guard's hard lock.
    #ProspectiveChange part d0384 : Decision {
        :>> id = "3697529a-697c-474a-ba3d-002d37f08d49";
        :>> title = "supersessionHome: which representation of a Decision's supersession is authoritative - the status field, the Supersede edge, or both held equal by a guard";
        :>> createdAt = "2026-09-08";
        :>> createdBy = "claudeOpus5";
        :>> status = DecisionStatus::accepted;
        :>> context = "issue396: d0353 read status=proposed while d0356's #Supersede edge had already retired it, so the pending-acceptance list asked the owner to sign a rule the project had reversed, for a day, until the attribute was edited by hand. Two writable representations of one fact, with nothing holding them equal. dcSupersessionIsSaidOnce's DoD requires the choice to be recorded with what it costs before either representation is removed, because one of them is load-bearing in existing records. The census in the RESEARCH line is the evidence: the edge cannot carry retirement today because seven accepted Decisions carry one and remain in force.";
        :>> decision = "OPTION A (edge is authoritative): DecisionStatus::superseded leaves the authored vocabulary; supersession is computed from #Supersede edges wherever it is read - the queue, the decisions scorecard, why-traversal. COST: the edge must gain a scope (whole versus clause) or the seven partial reversals retire Decisions still in force, including never-rebase; that is a schema change through the frozen gate, a D0067 migration of seven status values, and four edges authored from trailing comments - about a day, and the graph then answers 'is this in force' without opening the file. OPTION B (status is authoritative): status stays the authored fact of a Decision's standing; a new guard FAILS a Decision reading proposed with an incoming #Supersede edge, and record decision --supersedes refuses a proposed target, naming the remedy - the target's status is set superseded or rejected in the same commit. COST: the retiring author edits another owner's field, an exception to D0108 the guard text must state; the seven partial reversals stay as they are, edge present and status accepted, which a reader must know means 'a clause'; about two hours, no schema change. OPTION C (both, held equal by a guard): status stays and a guard fails EVERY mismatch - proposed with an edge, and accepted with an edge unless the superseder's text carries the word clause. COST: the seven existing records gain the word or are reclassified now; the strictest reading, about half a day. OPTION D (as it stands): the queue alone excludes a proposed Decision with an incoming edge; both stay writable. COST: the state that produced issue396, kept; the DoD forbids it, so it is the do-nothing course for comparison.";
        :>> rationale = "WHY NOT DECIDE THIS AUTONOMOUSLY: it changes what an accepted record means, and 373 accepted Decisions and every acceptance guard read the status field; the human owns which surface their signature binds to. WHAT I RECOMMEND, AND WHAT WOULD CHANGE IT: OPTION B. The census shows the edge is not a retirement mark and cannot become one without a scope it does not have; B closes the defect at the write path and the commit gate with no schema change, and the one thing it leaves ambiguous - an accepted Decision with an incoming edge - is true today and readable as a clause reversal. It would change to A if the human wants 'is this Decision in force' answerable from the graph alone, without opening the file; the scope attribute is that answer's price.";
        :>> consequences = "On A: a schema CR adds scope to Supersede, seven status values migrate under D0067 with control totals, four edges are authored, pendingAcceptances and the scorecard read the edge, and DecisionStatus::superseded is refused by validate. On B: guard supersede-target-standing joins the enforced set, record decision --supersedes refuses a proposed target with the remedy, and D0108's owner rule gains the stated exception; dcSupersessionIsSaidOnce is then a two-hour sprint. On C: as B plus the accepted-with-edge rule and seven records amended. On D: dcSupersessionIsSaidOnce is withdrawn by a superseding Decision and issue396 is mooted with the reason stated.";
    }

    // acceptance event (D0121 review-queue sign-off; D0066/D0106 — human-judged, not fabricated)
    verification d0384Accept : Test { :>> id = "97cd0e31-4d55-4c19-8661-fd822ce7d995"; :>> method = VerificationMethod::confirmation; :>> procedureText = "Selected on the decision brief copy-out (tenth publish), pasted into chat 2026-09-09; d0384 option A chosen over the recommended B. No note added. - their words, verbatim: “A: the edge is authoritative; status leaves the vocabulary; the edge gains a scope”"; }
    part d0384AcceptR1 : TestResult { :>> id = "e4895483-2ac8-4d15-8cd5-1168c7b32a4b"; :>> outcome = VerdictKind::pass; :>> judgedAgainst = "f998019"; :>> judgedAt = "2026-09-09"; :>> judgedBy = "wweatherholtz"; :>> createdBy = "claudeOpus5"; }
}
