// D0237 (status: the `status` field below is the truth) — the shipped reference decision history gets its own package namespace
// Recorded via `keel record decision` (D0105 RMWX axis; issue054). Acceptance is a separate explicit
// human gate (method=confirmation, D0106): flip status + add the d0237Accept event on sign-off.
package Decision0237 {
    private import EngineElement::*;
    private import EngineWork::*;
    private import EngineVerification::*;
    private import EngineRelationships::*;

    part d0237 : Decision {
        :>> id = "eeac50ff-841f-405c-b7d1-eef0729b6114";
        :>> title = "the shipped reference decision history gets its own package namespace";
        :>> createdAt = "2026-08-27";
        :>> createdBy = "claudeOpus5";
        :>> status = DecisionStatus::accepted;
        :>> context = "A field project (pdp-gate-review-3q26, init vintage ~2026-08-25) hit a collision on its very first recorded decision. keel init remaps the engine's own 236 decisions into .engine/reference/decisions/ as read-only reference, and ships .engine/decisions/ empty for the project's own. But write.rs::next_decision_number scans only the project's directory, so the first `keel record decision` allocates 0001 and declares `package Decision0001 { part d0001 ... }` — colliding with reference/decisions/0001-text-files-are-truth.sysml. The registry silently merges same-named packages; `keel validate` and `keel check-engine` both report CLEAN, and only duplicate-identity catches it, naming the read-only reference file as the offender — the one file the author must not edit. The field workaround was to renumber the project's decisions into a 1xxx series, which re-collides if the reference history ever reaches 1001. The root is older than the allocator. Sprint 104's record states the reference copy is 'NOT scanned as instance — the rust views scan .engine/decisions'. That was never true: collect_sysml has no exclusions, so the reference copy has always been parsed and registered. Sprint 104 implemented the PATH remap and not the scanning boundary it declared, and verified with 'a fresh init project validates clean + guards ALL PASS + shows 0 instance decisions' — a check that could not have failed, because the collision requires a first recorded decision and a fresh init has none. Sprint 115's init smoke test asserts the same shape and shares the same blind spot.";
        :>> decision = "The reference copy's PACKAGE is renamed on the way in: a decision file remapped to reference/decisions/ has its declaration rewritten `package DecisionNNNN` -> `package ReferenceDecisionNNNN`. Project decisions keep the natural DecisionNNNN / dNNNN scheme, so a downstream project's first decision is D0001 as its author would expect. The transform (migrate.rs::remap_engine_content) is paired with remap_engine_path and applied at both copy sites — `keel init` and `keel migrate`'s engine-resync step. Because resync compares TRANSFORMED content against disk, that step IS the repair for a project inited before this existed, and a no-op for one inited after: verified on an old-vintage fixture (236 planned edits, 241 files written, duplicate-identity FAIL -> PASS, re-plan empty).";
        :>> rationale = "ALTERNATIVES: (A) allocate past the highest number across BOTH directories — rejected: it fixes the first allocation and reopens the hole at the next migrate, because the project takes 0237, the engine later reaches 0237, resync copies it in, and the two collide again; renumbering an accepted decision is not available as a remedy, since its number is cited in commits and prose. (B) give PROJECT decisions a distinct scheme (ProjectDecisionNNNN / pdNNNN) — rejected: it diverges keel's own repo from its 236 existing decisions, or else makes the emitted scheme conditional on context, and it moves the change into the write path that every reader shares. (C) drop the reference copy from the model entirely — rejected: .engine/rules/rules.sysml carries 10 real #JustifiedBy edges to dNNNN targets, which would dangle downstream. (D) rename the reference PACKAGE — CHOSEN. CRITERIA: durability against future growth of either namespace; blast radius on the write path; and whether the transform is mechanically total. The chosen option makes the two namespaces disjoint BY PREFIX, so number overlap stops mattering permanently — verified with a project Decision0001 and a ReferenceDecision0001 coexisting green. It is one line per file, always at identifier position, so it cannot corrupt prose: 189 of the 514 dNNNN occurrences in the decision corpus sit inside procedureText strings, which is exactly why the PART names are left alone. dNNNN stays resolvable because Rust name resolution is global — the 10 rules.sysml edges still resolve after the rename, confirmed by check-engine clean. No code matches on a 'package Decision' prefix and nothing imports a decision package by name, so the rename has no reader to update.";
        :>> consequences = "Downstream: a fresh project's first recorded decision is D0001 and the gate stays green; an existing project is repaired by `keel migrate`, which is idempotent. keel's own repo is untouched — it has no reference/ directory, so the transform never fires here, which is also why this defect could not appear in the self-build. What this does NOT fix, recorded separately: the reference copy is still parsed as instance data, so a downstream project's model contains 235 attestations judged by keel's human and 236 judgedAgainst SHAs that do not resolve in that repository. The numbering collision was the symptom that surfaced; the declared-but-unimplemented engine/instance scanning boundary is the defect, and it inflates a downstream project's verification surface with someone else's word. Sprint 104's false claim is left in place as the evidence of what was believed, and the header comment describing present behaviour is corrected to state what IS. The verification lesson generalises: both gates that covered init exercised the one state in which the defect is invisible. A scaffold check that never records a fact cannot see a collision between the scaffold and a recorded fact.";
    }

    // acceptance event (D0121 review-queue sign-off; D0066/D0106 — human-judged, not fabricated)
    verification d0237Accept : Test { :>> id = "066c525f-ab03-45d4-9feb-9b506429272a"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0237AcceptR1 : TestResult { :>> id = "342f22d3-75f0-42d7-9f7a-4769c09308f1"; :>> outcome = VerdictKind::pass; :>> judgedAgainst = "d07a647"; :>> judgedAt = "2026-08-27"; :>> judgedBy = "wweatherholtz"; }
}
