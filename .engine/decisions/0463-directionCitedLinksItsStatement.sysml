// D0463 (PROPOSED — NOT YET ACCEPTED) — directionCitedLinksItsStatement: a Decision or task DoD that quotes the human links a Statement holding their words verbatim - guard direction-cited, forward-only from 2026-09-12
// Recorded via `keel record decision` (D0105 RMWX axis; issue054). Acceptance is a separate explicit
// human gate (method=confirmation, D0106): flip status + add the d0463Accept event on sign-off.
package Decision0463 {
    private import EngineElement::*;
    private import EngineWork::*;
    private import EngineVerification::*;
    private import EngineRelationships::*;

    // #ProspectiveChange (D0070) - this Decision governs a process/schema change; the co-committed
    // change rides the process-change guard's hard lock.
    #ProspectiveChange part d0463 : Decision {
        :>> id = "9b09e007-5473-4484-93e4-a838e7c0bef6";
        :>> title = "directionCitedLinksItsStatement: a Decision or task DoD that quotes the human links a Statement holding their words verbatim - guard direction-cited, forward-only from 2026-09-12";
        :>> createdAt = "2026-09-12";
        :>> createdBy = "claudeFable5";
        :>> status = DecisionStatus::proposed;
        :>> context = "stpa-self run 2 (UCA-H1, 2026-09-09) read humanDirects off the computed control structure as a prose channel nothing parses, and recorded issue428: a Decision may cite the human in its context or rationale - an attribution phrase and a quoted span - with no Statement recorded and no DerivedFrom edge, so the tree holds the agent's rendering of the direction and nothing to check it against (hazard EHZ3, words attributed to the human without their record). The channel exists: keel record statement (D0216/D0236) records their words verbatim with saidBy, saidAt and channel, and a Need or story derives from it by a DerivedFrom edge - but only the elicitation process was bound to it. D0289 binds an ACCEPTANCE to the human's quoted words and guard acceptance-binds-to-text holds that receipt; the direction that produced the Decision had no equivalent. keel hardening (D0166) reports unsourced items as a view and gates nothing. Measured on the tree at HEAD before this control: 8 Decisions quote the human in their own fields with no Statement behind the span, and 6 task DoDs do the same while carrying no createdAt at all, because keel record task stamps neither createdAt nor createdBy on the DoD Test it writes (issue513, found here).";
        :>> decision = "Guard direction-cited (HARD) reads every Decision under .engine/decisions/ (context, decision, rationale, consequences) and every verification <x>DoD : Test under .tracking/ (procedureText). A record is read as CITING when a field carries an attribution phrase - their words, the human's words, the human said, human's own words, or the human followed by a YYYY-MM-DD date - then an optional verbatim, then a quoted span of eight characters or more in curly or straight quotes (a straight closing quote is one not followed by a letter or digit, so an apostrophe inside the quote does not close it). A citing record dated on or after 2026-09-12 by its createdAt HOLDS when it carries a DerivedFrom dependency edge to a Statement whose text contains every quoted span verbatim, the write path's doubled-quote and backslash escapes folded and whitespace collapsed; otherwise it is a violation naming the record and the first unsupported span, and the fix: record their words with keel record statement and author the edge, or quote nobody. A phrase with no quoted span after it is a mention and is not read. Citing Decisions dated before 2026-09-12, and citing DoDs with no createdAt, are one counted-history line, never enumerated (D0261). The guard is registered as constraint def directionCited (D0195 clause 1), mapped to hazard EHZ3 in control-map.sysml, and its constraint ccDirectionLinksItsStatement binds to it.";
        :>> rationale = "The reason a Statement exists at all (D0166, D0236) is that the human's words are an irreducible fact and the agent's rendering of them is not; a Decision that quotes them without the record is the rendering wearing the record's clothes. Binding the citation to a Statement by a typed edge and a verbatim containment check makes the words checkable at the one place they are cited, the same way D0289 made an acceptance checkable. The predicate is deliberately narrow: it fires on an attribution phrase AND a quoted span, so a Decision that paraphrases the human, names them, or quotes a document is untouched - the guard establishes provenance for what claims to be their words, it does not compel every Decision to carry a Statement. Forward-only because the eight earlier citing Decisions were accepted on those renderings and re-litigating them is the D0129 class; the undated DoDs are counted apart because the boundary is not in the tree for them, and the honest fix is the write path stamping the date (issue513), not the guard guessing one.";
        :>> consequences = "Resolves issue428 through dcDirectionDecisionsLinkTheirStatement (sprint 690). guards.rs and guard-constraints.sysml change, so this Decision rides the commit as its ProspectiveChange (D0209 clause 2) and is held proposed for the human. From this date a Decision I record that quotes the human must be preceded by keel record statement and carry the DerivedFrom edge - the decision draft's derived-from flag (D0352) authors it with the Decision. DoDs recorded through keel record task stay in the counted class until issue513's resolver stamps their date, at which point new citing DoDs are judged forward like Decisions. STATED: the anchor list is a closed vocabulary; a citation phrased outside it (a bare name and a quote) is not read, and widening the vocabulary is a later clause on this one, not a silent edit to the constant. The 8 and 6 are the counts the guard prints at HEAD before this commit; they do not grow, because every later citing record is judged.";
    }
    #DependsOn dependency from d0463 to d0236;
}
