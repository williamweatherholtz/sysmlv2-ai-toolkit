// D0245 (status: the `status` field below is the truth) — one console per machine: a registry of served projects, and keel serve becomes idempotent
// Recorded via `keel record decision` (D0105 RMWX axis; issue054). Acceptance is a separate explicit
// human gate (method=confirmation, D0106): flip status + add the d0245Accept event on sign-off.
package Decision0245 {
    private import EngineElement::*;
    private import EngineWork::*;
    private import EngineVerification::*;
    private import EngineRelationships::*;

    part d0245 : Decision {
        :>> id = "322faedb-9d24-41a3-9501-b3d34a15e4f1";
        :>> title = "one console per machine: a registry of served projects, and keel serve becomes idempotent";
        :>> createdAt = "2026-08-28";
        :>> createdBy = "claudeOpus5";
        :>> status = DecisionStatus::accepted;
        :>> context = "The human supervises eight keel projects on this machine, in eight separate git repositories, and wants ONE browser tab with a project selector. What they have instead is several `keel serve` windows, each a separate process on its own port, and new projects starting their own. Measured, today: `keel serve` binds 127.0.0.1:7777 by default and hard-errors if the port is taken, so a second serve either fails or is given `--port` and becomes another window. `/api/projects` populates the selector by scanning the PARENT DIRECTORY of the active root for siblings holding `.engine` and `.tracking`. On this machine all eight projects happen to be siblings under `claude_code/`, so the selector appears to work - by accident of directory layout. A project in any other parent, or nested as a workspace peer, is invisible, and no project has any way to ASK to be listed or to stop being listed. The human named this exactly: 'it's not actually projects requesting to tap into keel serve, it seems to be based on directory structure.' There is no cross-project keel state today. Everything is per-project (`.keel/`, `.keel-serve.json`), and this Decision introduces the first machine-local, cross-repo artifact.";
        :>> decision = "ONE CONSOLE PER MACHINE, a machine-local REGISTRY, and `keel serve` becomes IDEMPOTENT. 1. A registry outside any repository records: the live console's port and pid, and one entry per project - root, label, owning repo, last served. 2. `keel serve` in a project first asks whether a healthy console is already answering. If it is, the command REGISTERS this project with it, prints the URL that opens it, and EXITS 0 without starting anything. Only when no console answers does it start one. That single change is what stops the window proliferation, because running the command twice stops producing two servers. 3. `/api/projects` reads the REGISTRY rather than scanning sibling directories, so a project in another repository appears and a project that has never been served does not. 4. PRUNE DEAD, KEEP THE REST (the human's choice): an entry whose directory no longer exists is dropped automatically; everything else stays until explicitly deregistered. No time-based expiry - a project supervised monthly must not silently vanish. 5. READ ANY, WRITE ACTIVE ONLY (the human's choice): the selector may point the surface at any registered project, and every write - accept, disposition, edit - targets the ACTIVE project only. Switching active stays an explicit act, and `rebind`'s existing guarantee is kept: it REFUSES an invalid target rather than falling back to the previous root. 6. Port behaviour is unchanged and deliberately rigid: 7777, refuse loudly if taken by something that is not a keel console. Silent port-hopping is the mechanism that produced the windows being complained about.";
        :>> rationale = "THE PRINCIPLE THIS BENDS, stated rather than slipped past. `api_projects` currently carries the comment 'A config file would be a second place to keep the list true, and the filesystem already knows', and workspace discovery is built on the same rule (D0234: DISCOVERED, NOT DECLARED). That rule is right for 'what projects does this repository contain' and WRONG here, because 'which projects do I want in my console' is not a fact the filesystem holds. It is an operator preference, it spans repositories, and it belongs to a person rather than to a tree. The filesystem knows which directories are projects; it cannot know which ones the human cares about today. The resolution keeps the spirit: the registry is A RECORD OF AN ACT, not a configuration to maintain. An entry appears because someone ran `keel serve` there, and disappears when the directory does. There is nothing to hand-edit and nothing to keep true, so it does not become the second source of truth the original comment was guarding against. ALTERNATIVES: (A) keep one server per project and add a front proxy - rejected, it multiplies the processes the human is complaining about. (B) widen the sibling scan to a configured list of roots - rejected, that IS the config file to maintain, with none of the self-maintenance. (C) scan the whole filesystem for projects - rejected: slow, and it would list projects the human has never asked for, which is the opposite of the complaint. (D) registry written by an act, pruned by existence - CHOSEN. CRITERIA: does running the command twice produce two servers; does a project in another repo appear; and is there anything the human must maintain by hand. On clause 5, the human was asked directly because it is an authority question, not a UX one: one tab that can write into eight repositories is a materially larger surface than eight tabs that each write into one, and Decision acceptance recorded through that surface is their own attestation. Read-any plus write-active-only keeps the blast radius of a forgotten tab to the project it is pointed at.";
        :>> consequences = "Running `keel serve` in a second project stops producing a second window, which is the reported problem. A project in another repository becomes reachable from the same tab, which sibling scanning could never do. New surface, stated plainly: a machine-local file naming filesystem paths outside any repository, and a console whose selector spans repositories. It binds 127.0.0.1 only, as today. It is not committed and must never be, since it describes one machine's working arrangement. What this does NOT do: it does not make the console multi-tenant. There is one active project at a time and one process; switching is a rebind, and every computed view is recomputed against the new root - the existing cache invalidation on rebind already handles that and is unchanged. A residual worth naming: version skew. A console started from one project's binary will serve another project whose `.engine` may be of a different vintage. The console already reports the engine-version warning per project, and this Decision does not change that; whether the SERVER's binary version should be checked against each registered project is left open rather than silently assumed safe.";
    }

    // acceptance event (D0121 review-queue sign-off; D0066/D0106 — human-judged, not fabricated)
    verification d0245Accept : Test { :>> id = "e3a82a31-a569-4718-a0f3-7ef9c7b63b95"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0245AcceptR1 : TestResult { :>> id = "f4b4f92a-a91d-4c28-a880-3883313dc65a"; :>> outcome = VerdictKind::pass; :>> judgedAgainst = "ba8a6c3"; :>> judgedAt = "2026-08-28"; :>> judgedBy = "wweatherholtz"; }
}
