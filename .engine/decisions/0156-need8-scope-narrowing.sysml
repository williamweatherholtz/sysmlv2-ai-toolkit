// D0156 — ACCEPTED (wweatherholtz, 2026-08-17): N-8 is SUPERSEDED by N-19, which states the concern
// that survives D0115 in the human's own framing of it. Their answer rejected all four options this
// Decision originally proposed, and the record says so rather than quietly adopting a fifth.
// #ProspectiveChange (D0070): supersedes one Need and adds another; nothing already derived changes.
package Decision0156 {
    private import EngineElement::*;
    private import EngineWork::*;
    private import EngineVerification::*;
    private import EngineRelationships::*;

    #ProspectiveChange part d0156 : Decision {
        :>> id = "a71f3e08-4c92-4b65-8d17-903fe2cb5471";
        :>> title = "D0156: supersede N-8 with N-19 — a saved view travels to another machine; sharing is not authentication";
        :>> createdAt = "2026-08-17";
        :>> createdBy = "claudeOpus5";
        :>> status = DecisionStatus::accepted;
        :>> context = "issue132, open since 2026-08-15. nViewerPersistedViewpoints (N-8) states that viewpoints and view state must be 'shareable across users' with 'per-user view state'. D0115 clause 1 says the opposite in as many words — 'the viewer is single-user + unauthenticated; saveable viewpoints are covered by N-8 (drop auth/multi-user/per-user)' — so part of N-8's statement describes scope an accepted Decision removed, and a reader decomposing N-8 today would derive requirements for work that was cut. THIS DECISION WAS FIRST PROPOSED WITH FOUR OPTIONS AND ALL FOUR WERE WRONG, which is recorded because the reason is the finding: every one of them assumed N-8's 'shareable' was about the VIEWER. The human's answer named the actual need — 'we want to support users on different computers running keel, the real need is to be able to transfer processes to them easily... it's not single user altogether, it's a single user per machine' — which is a different object, and one the model already holds as nProcessPortability / srPortCatalogExchange (verified sprint 297). Asking about the wrong object produced four coherent answers to a question nobody had.";
        :>> decision = "ACCEPTED: (1) SUPERSEDE N-8 via #Supersede from this Decision — the same mechanism D0115 itself used on N-7, N-9, N-11 and N-14, rather than editing a statement in place, so the human's 2026-07-14 accepted-as-is attestation keeps naming the exact words it accepted. (2) ADD N-19 (nViewerViewStateTravels): a saved viewpoint selection, filters and layout must persist as an artifact in the repository and TRAVEL with it, so the same view opens on another machine and in another person's clone with no account, no server-side session, and nothing the model cannot see. (3) REPOINT srViewerPersistedViewState's satisfy edge from N-8 to N-19 — the requirement itself needed no change, because it already said sharing is by the artifact travelling in git. (4) The hosted multi-user and marketplace direction is recorded separately as D0157 and derives no requirement. N-19 was authored by claudeOpus5 under the human's explicit authorization, D0108's non-owner bar being the reason it could not be done unbidden; its substance is theirs and I may not narrow it further without them.";
        :>> rationale = "WHY SUPERSEDE RATHER THAN EDIT: D0115 superseded four Needs and left their text intact. Narrowing the fifth in place would treat the same kind of change two different ways, and would leave keelViewerNeedsAccept (2026-07-14, judgedAgainst 5f82eec) attesting eight Needs 'AS-IS' while one of them no longer says what was accepted — recoverable at that SHA, but only by a reader who thinks to look. WHY 'TRAVELS' IS THE RIGHT WORD AND 'SHAREABLE' WAS NOT: the human's correction separates two things one word had merged. Transfer between machines needs no account — it is a file moving through git, which is the engine's whole premise. Multi-user access to a running service needs authentication, per-user state and a server. N-8 asked for the second while meaning the first, and 'travels' cannot be misread into auth work. WHY THE OLD REQUIREMENT SURVIVED UNTOUCHED: srViewerPersistedViewState was authored against 'the scope D0115 left standing' and stated it explicitly, so the residual was recordable as an Issue rather than as a defect in the requirement. Containing damage in the Issue layer is what let this be corrected by one supersession instead of a rework.";
        :>> consequences = "issue132 resolves. N-8 stays in the model, superseded and readable, with its acceptance intact. `keel tier-satisfaction` and the rootedness computations see N-19 satisfied by an existing verified requirement, so no burndown number moves. THE COST, stated: a reader now finds two Needs where there was one, and must follow a #Supersede edge to know which is live — the price of not rewriting an attested statement. NOT RESOLVED HERE, deliberately: whether viewpoint DEFINITIONS should be portable the way processes are (issue138), and whether D0115's phrase 'single-user' should be restated as 'one actor per machine' now that distributed collaboration has shipped (issue137). Both are separate questions and neither is settled by this Decision.";
    }

    #Resolves dependency from d0156 to issue132;
    // Kept now that this Decision is accepted: the edge is what BLOCKED the resolving action while it was
    // proposed (blocked-on-acceptance counts only a proposed Decision), and deleting it would erase the
    // record that the work was correctly held rather than merely late.
    #DependsOn dependency from dcNeed8ScopeNarrowing to d0156;

    // acceptance event (D0121 review-queue sign-off; D0066/D0106 — human-judged, not fabricated)
    verification d0156Accept : Test { :>> id = "3b8d5f21-9e47-4c06-a15b-72fe08c93d64"; :>> method = VerificationMethod::confirmation; :>> procedureText = "wweatherholtz, 2026-08-17, verbatim: 'yes implement as indicated' — given in direct reply to a message that named exactly three records to write, the first being 'Supersede N-8 with a Need about the viewer's own object, stated the way you just stated the real need — view state persists as an artifact in the repo so it travels to another machine and another person's clone, no account and no server.' The substance of N-19 is the human's own, from the answer immediately before it: 'we want to support users on different computers running keel, the real need is to be able to transfer processes to them easily. so it's not single user altogether, it's a single user per machine - this service app is local only at the moment.' THIS ALSO CARRIES THE OWNERSHIP AUTHORIZATION that D0108 requires: N-8 is theirs, so superseding it and authoring its replacement needed their word, and 'implement as indicated' against a message that spelled out the supersession is that word. It attests the SCOPE DECISION and the authorization to author N-19; it is not a line-by-line review of N-19's wording, which they may still revise as its owner in substance."; }
    part d0156AcceptR1 : TestResult { :>> id = "6e2a94c7-0db3-4f85-9c31-58a107ed2b96"; :>> outcome = VerdictKind::pass; :>> judgedAgainst = "PENDING"; :>> judgedAt = "2026-08-17"; :>> judgedBy = "wweatherholtz"; }
}
