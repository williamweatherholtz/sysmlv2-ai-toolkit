// =====================================================================
// D0124 (status: the `status` field below is the truth) — the viewer's encoding channels are a MODULAR REGISTRY.
// Adding an encoding type = adding one channel module; the panel/apply/legend are generated from the
// registry (no channel-specific branches). Refines D0120 (encoding-spec design); serves srEncodingModular
// (N-18). Human-directed 2026-07-15 ("these encoding types should be modular... add different types going
// forward... ensure architecture is modular"). Acceptance = sitting review.
// =====================================================================
package Decision0124 {
    private import EngineElement::*;
    private import EngineWork::*;
    private import EngineVerification::*;
    private import EngineRelationships::*;

    part d0124 : Decision {
        :>> id = "10a1b0c1-4124-42a3-ab5c-516273849724";
        :>> title = "D0124: encoding channels are a modular registry — add an encoding type = add one module";
        :>> createdAt = "2026-07-15";
        :>> createdBy = "claudeOpus";
        :>> status = DecisionStatus::accepted;
        :>> context = "The first encoding engine (D0120/sprint230) hardcoded four channels (colour/x/swimlane/nested) as fixed selects + branchy apply logic. The human directed (2026-07-15): 'these encoding types should be modular — I want to be able to add different types going forward. ensure architecture is modular, such that new encoding types can be added seamlessly.' A branchy design would rot as channels multiply (size, shape, opacity, border, icon, grouping, …).";
        :>> decision = "Model the viewer's visual channels as a REGISTRY (ENCODE_CHANNELS): an array of self-contained channel modules. Each module declares its `id`, `label`, `role` (style | x | row), the attribute `kinds` it accepts ('*' or a list), and — for style channels — a `prep`(type,attr)->ctx + `apply`(node,ctx) value→cytoscape-style mapper + a `legend`(type,attr) renderer. The Encode PANEL (one select per channel), the APPLY pass (position from x/row-role channels; style from style-role channels), and the LEGEND are all GENERATED by iterating the registry — there are NO channel-specific branches anywhere else. Row-role channels compose to nested swimlanes of any depth (product of their domains). Adding an encoding type is adding ONE module; removing one is deleting it.";
        :>> rationale = "ALTERNATIVES: (i) keep the four hardcoded channels + add if-branches per new channel — REJECTED: does not scale, every new type touches the panel + apply + legend (the rot the human is pre-empting). (ii) a full external viz grammar (Vega-Lite) as the channel layer — heavier + less control over cytoscape specifics; the registry can wrap such a lib later without changing the contract. CHOSEN: an in-app channel registry — minimal, keeps the value→style mapping local to each channel, and makes extensibility a one-entry change. PROVEN by adding two new channels (size ← numeric → node width/height; shape ← enum/categorical → node shape) with no other code change — verified live (6 generated selects; 43 nodes across 5 channels; 6 distinct shapes). Mirrors the engine's generative principle (D0117): behaviour follows a declared set, not hardcoded cases.";
        :>> consequences = "Recorded PROPOSED; acceptance = sitting review. Refines D0120; serves srEncodingModular (N-18). The viewer app (sysmlv2-viewer@258323e) holds the registry; new channels (opacity, border, node-icon, grouping, edge-encodings) are future one-module additions. Any future channel with a genuinely new ROLE (beyond style/x/row) adds a small role handler in the apply pass — the only non-one-entry case, noted for honesty. Composes with D0119 (standard view kinds) + D0117 (generative)."; }

    #DerivedFrom dependency from d0124 to nViewerEncodingViewpoints;
    #DependsOn dependency from d0124 to d0120;

    // acceptance event (D0121 review-queue sign-off; D0066/D0106 — human-judged, not fabricated)
    verification d0124Accept : Test { :>> id = "1975ae26-1e43-4011-9da1-211dbc91cc23"; :>> method = VerificationMethod::confirmation; :>> procedureText = "accepted"; }
    part d0124AcceptR1 : TestResult { :>> id = "85d7d554-25fe-4153-af1d-e2d4e3b3e338"; :>> outcome = VerdictKind::pass; :>> judgedAgainst = "e995440"; :>> judgedAt = "2026-07-15"; :>> judgedBy = "wweatherholtz"; }
}
