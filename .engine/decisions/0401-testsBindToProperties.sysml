// D0401 (status: the `status` field below is the truth) — testsBindToProperties: a test that asserts program source contains a code-shaped literal is refused by the suite, and the refusal names the property to bind to
// Recorded via `keel record decision` (D0105 RMWX axis; issue054). Acceptance is a separate explicit
// human gate (method=confirmation, D0106): flip status + add the d0401Accept event on sign-off.
package Decision0401 {
    private import EngineElement::*;
    private import EngineWork::*;
    private import EngineVerification::*;
    private import EngineRelationships::*;

    // RESEARCH: Census 2026-09-09 over keel-cli (grep for include_str! and read_to_string of a .rs path inside test regions, re-runnable): 14 tests read program source. 11 read it BY DESIGN - a guard catalogue compared with GUARD_NAMES, a dispatch table compared with help text, a route list, six offender scans that assert a set is EMPTY, and one doc-claim test whose needles are prose. 3 assert that a code-shaped literal is present: main.rs the_turn_boundary_blocks_only_on_dishonest_state (`if problems.is_empty() {`, `return 0;`), guards.rs the_runner_flags_a_violation_against_an_empty_scan (`self.scanned == 0 && !self.violations.is_empty()`), fingerprint.rs the_epoch_is_advanced_by_writes_and_observations_not_by_reads (`let writes = method != axum::http::Method::GET`, a count of 2 calls). The discriminator - a positive assert that a source-bound identifier contains a literal carrying `;` `{` `}` `==` `!=` `return ` `let ` `if ` `fn ` or `=>` - separates the two sets with zero overlap on this tree. Each of the three already has, or gains in sprint 627, a behavioural test of the same property: tests/remaining_controls_actually_fire.rs turn_boundary_gate_allows_a_clean_tree_and_blocks_a_dishonest_one and tests/stop_says_nothing_about_decisions.rs for the first; GuardReport::self_contradiction as a pure function for the second; an axum oneshot through log_request counting epoch movement for the third.
    // #ProspectiveChange (D0070) - this Decision governs a process/schema change; the co-committed
    // change rides the process-change guard's hard lock.
    #ProspectiveChange part d0401 : Decision {
        :>> id = "d1a9fc3c-6364-43f9-8cda-5ad3805f8912";
        :>> title = "testsBindToProperties: a test that asserts program source contains a code-shaped literal is refused by the suite, and the refusal names the property to bind to";
        :>> createdAt = "2026-09-09";
        :>> createdBy = "claudeOpus5";
        :>> status = DecisionStatus::accepted;
        :>> context = "issue388: main.rs carried a test that read main.rs with include_str! and asserted that the literal `if problems.is_empty() {` preceded `return 0;` inside hook_stop. The doc comment above it said, in so many words, that it replaced a test bound to a mechanism rather than a property - and then bound itself to the spelling of the mechanism. Such a test passes while the behaviour is wrong (rename `problems` and it fails; invert the branch and keep the tokens and it passes), and it fails on every honest refactor, which teaches the next editor to update the needle rather than to ask what the test was for. Two more of the same shape sat in guards.rs and fingerprint.rs. The suite has no rule about which side of that line a test may stand on.";
        :>> decision = "A test in keel-cli that binds program source - `include_str!` or `read_to_string` of a `.rs` path, held in a const, static or let binding - and POSITIVELY asserts that the bound text contains a code-shaped literal is a REFUSAL: `keel-cli/tests/tests_bind_to_properties.rs` fails under `cargo test`, and for each offender its report names the file and line, the test, the literal, the property the test should bind to (the first sentence of its own doc comment) and any behavioural equivalent already in the surface (other test functions the doc comment names that exist). Code-shaped means the literal carries one of `;` `{` `}` `==` `!=` `return ` `let ` `if ` `fn ` `=>`. A negated containment (an offender scan asserting a set is empty), a literal built by format! from a catalogue, and a prose needle in a doc-claim test are outside the rule by construction. The check carries its own known-positive and known-negative fixtures as tests in the same file, run before the tree is read (D0388). NOT A FORK: the DoD of dcTestsBindToPropertiesNotSource asks for the tier to be decided on the evidence in the tree, and the evidence is that the discriminator has zero overlap with the eleven legitimate source-reading tests today, so a warning would be read by nobody and a refusal costs nothing legitimate.";
        :>> rationale = "A test earns its keep by failing when the property it guards is broken and passing when it is not. A source-shaped assertion inverts both halves: it is bound to how the code is spelled, so it passes through a behavioural regression that keeps the tokens and fails through a refactor that keeps the behaviour. Refusal rather than warning because the census shows the rule's false-positive set is empty on this tree, every current offender has a behavioural equivalent in the same commit, and a warning that no test fails on is a reminder - and manual vigilance is not a control (D0047). The property to bind to is taken from the test's own doc comment because that is where every one of the three offenders had already stated it correctly; the check turns that sentence from a comment into the report.";
        :>> consequences = "Three tests leave or change. main.rs the_turn_boundary_blocks_only_on_dishonest_state is deleted; its property is held by turn_boundary_gate_allows_a_clean_tree_and_blocks_a_dishonest_one and the two stop_says_nothing_about_decisions tests, against real scaffolds. guards.rs gains `GuardReport::self_contradiction() -> Option<String>`, called by print, and the runner test asserts its value on a zero-scan report with violations and on a populated one. fingerprint.rs loses its serve.rs-reading test; serve.rs gains a test that drives log_request with tower::ServiceExt::oneshot and asserts that fifty GETs move the epoch by fewer than fifty and fifty POSTs by at least a hundred (two bumps each, before and after) - thresholds chosen so another test bumping the global cannot flip the verdict (D0381). `tower` with the `util` feature becomes a dev-dependency (already in Cargo.lock through axum). The rule is a process change over the test surface, so this Decision carries the marker and waits for the human's word; the check is applied co-committed with it under the D0070 lock, as D0363, D0398 and D0400 were. Sprint 627 delivers dcTestsBindToPropertiesNotSource and resolves issue388.";
    }

    // acceptance event (D0121 review-queue sign-off; D0066/D0106 — human-judged, not fabricated)
    verification d0401Accept : Test { :>> id = "dac52303-b4fd-469e-a6f3-fad8e7f92865"; :>> method = VerificationMethod::confirmation; :>> procedureText = "Selected on the decision brief copy-out (fifteenth publish), pasted into chat 2026-09-11: the set of 33 HELD process-change ratifications accepted with one word, this record being one member (D0406 named it in the table). No note added. - their words, verbatim: “Accept the set: each of the 33 rules named in the table is recorded accepted on its own, quoting these words (recommended)” WARN: read-back - the quoted words do not name d0401 (D0201 B); recorded as given (D0423)."; }
    part d0401AcceptR1 : TestResult { :>> id = "2515d697-d9e4-4139-8123-d83b25a8814b"; :>> outcome = VerdictKind::pass; :>> judgedAgainst = "3e6c518"; :>> judgedAt = "2026-09-11"; :>> judgedBy = "wweatherholtz"; :>> createdBy = "claudeOpus5"; }
}
