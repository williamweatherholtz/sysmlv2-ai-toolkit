// D0216 (status: the `status` field below is the truth) — elicitationThroughIntake: eliciting a need records the stakeholder's words FIRST, and the elicitation procedure becomes a catalogued transferable process
// Recorded via `keel record decision` (D0105 RMWX axis; issue054). Acceptance is a separate explicit
// human gate (method=confirmation, D0106): flip status + add the d0216Accept event on sign-off.
package Decision0216 {
    private import EngineElement::*;
    private import EngineWork::*;
    private import EngineVerification::*;
    private import EngineRelationships::*;

    // #ProspectiveChange (D0070) - this Decision governs a process/schema change; the co-committed
    // change rides the process-change guard's hard lock.
    #ProspectiveChange part d0216 : Decision {
        :>> id = "6aabcb5d-cca4-4953-b6f8-c5805c306ab2";
        :>> title = "elicitationThroughIntake: eliciting a need records the stakeholder's words FIRST, and the elicitation procedure becomes a catalogued transferable process";
        :>> createdAt = "2026-08-24";
        :>> createdBy = "claudeFable5";
        :>> status = DecisionStatus::accepted;
        :>> context = "The human asked whether all input is recorded as Statements then translated into UserStories, and said that pulling LATENT needs out of a user is quite critical for the average user. Three of the nine panel lenses converged on the same two findings. FIRST, the capability already EXISTS and is in heavy use: the business-architecture skill runs a design/scoping dialogue deploying the Business workflow and has authored 11 Briefs, 15 Personas, 69 UseCases and 75 Needs - so a new interview process would have been a FOURTH overlapping surface rather than a missing capability, which is exactly the surface proliferation the panel's reducer warned the whole slate against. SECOND, and this is the real defect: that skill deployed WORKFLOWS and named no PROCESS, and the process-skill correspondence keys on a skill purpose naming .engine/processes/<name>.sysml - so keel's actual elicitation surface appeared in NO catalogue (not process list, not activation, not hardening), was enforceable by nothing, and was transferable by nothing, with no control noticing. And it authored Needs straight out of conversations whose utterances were never recorded, which is both the mechanical cause of the unsourced population and the D0157 defect precisely: a Need with no cited utterance cannot be checked against what the stakeholder actually said, so nobody can distinguish a real demand from one written WIDER THAN THE DEMAND.";
        :>> decision = "TWO changes, both wiring what exists rather than adding a surface. (1) AUTHOR .engine/processes/business-elicitation.sysml - the elicitation PROCEDURE as a first-class Process with six ordered ProcessSteps: name whose needs these are; ask about PAIN not features (never offer a menu, because a chosen option is evidence about the menu and not about the need); record each answer VERBATIM as a Statement BEFORE interpreting it; translate to UserStories and triage them through the SAME intake vocabulary; author Needs that CITE their evidence via #DerivedFrom; and read the Needs back asking specifically what is WIDER than the stakeholder meant. The business-architecture skill's registry purpose now names this process, so it is catalogued, exportable as a unit, and enforcement-declared. (2) AMEND the skill so recording words is STEP 0 of Phase 1, ahead of Brief and Needs, and so a Need with no #DerivedFrom to a UserStory must SAY it is my judgment rather than being dressed as elicited. Declared checkable = false in process-enforcement.toml with the reasoning stated, following the [intake] precedent: what matters is what gets asked and whether the answer was recorded before it was interpreted, and a guard that counted edges would make the practice look enforced while enforcing nothing.";
        :>> rationale = "This is deliberately a WIRING change between two things that already existed - the reactive intake chain (D0166) and the active design dialogue - rather than a new elicitation mechanism. Intake is reactive: it records direction a human volunteered. Elicitation is active: it asks, for a stakeholder who cannot author a Need but can answer a question about their pain. Sharing one substrate is the whole point: an elicited need and a volunteered one become the same kind of fact, counted by one view, so the sourcedness question has a single answer instead of two. Statement-BEFORE-Need is the load-bearing ordering, because after the Need is authored the justifying wording is gone and every later reader compares my paraphrase to my conclusion. And giving the procedure a process definition is what makes the human's portability and discoverability questions answerable for the surface that matters most to an adopting project: the first thing a new project must do is get its needs out of a human.";
        :>> consequences = "process-skill scans 24 processes instead of 23 and still passes; keel process list reports 24 declared; business-elicitation is showable and exports WHOLE as definition + deploying skill + unit.toml, which works only because issue241's catalogue fix landed first in this same run. The elicitation procedure is now activation-visible, so a downstream project can see it, take it, and know it asserts no guard. NOT CLAIMED: no guard enforces the ordering, and the declaration says why; the unsourced backlog is untouched, because back-filling Statements for conversations nobody recorded would be fabrication. Resolves issue245. Doc-sync: CLAUDE.md's process list and the skill body ride this commit.";
    }

    // acceptance event (D0121 review-queue sign-off; D0066/D0106 — human-judged, not fabricated)
    verification d0216Accept : Test { :>> id = "143b1068-32e2-4f61-a6b5-97991b264329"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/13."; }
    part d0216AcceptR1 : TestResult { :>> id = "0c23e3bf-0581-4573-ba16-b4e3c90d6ed5"; :>> outcome = VerdictKind::pass; :>> judgedAgainst = "00417f1"; :>> judgedAt = "2026-08-24"; :>> judgedBy = "wweatherholtz"; }
}
