// D0250 (status: the `status` field below is the truth) — The portable-content library is a git repository, and every machine holds a cache of it
// Recorded via `keel record decision` (D0105 RMWX axis; issue054). Acceptance is a separate explicit
// human gate (method=confirmation, D0106): flip status + add the d0250Accept event on sign-off.
package Decision0250 {
    private import EngineElement::*;
    private import EngineWork::*;
    private import EngineVerification::*;
    private import EngineRelationships::*;

    // #ProspectiveChange (D0070) - this Decision governs a process/schema change; the co-committed
    // change rides the process-change guard's hard lock. Specifically it charters guard 53,
    // manifest-key-portability, in keel-cli/src/guards.rs, which is enforcement surface under
    // D0209 clause 2 and may not change without a marked Decision landing beside it.
    #ProspectiveChange part d0250 : Decision {
        :>> id = "7dac1c1f-2058-4d5d-b6a2-cb072440e284";
        :>> title = "The portable-content library is a git repository, and every machine holds a cache of it";
        :>> createdAt = "2026-08-28";
        :>> createdBy = "claudeOpus5";
        :>> status = DecisionStatus::accepted;
        :>> context = "nWorkingMaterialTravels requires that processes, skills, templates and output formats be available in every project without per-project installing or approving, and that the content keep itself current without per-update permission - while availability never constitutes activation (D0249, engineNeedsAccept). srLibraryAvailableWithoutInstall, srAvailabilityIsNotActivation and srActivatedUnitVersionIsPinned state the thresholds. None of them says WHERE the library lives, deliberately: that was the first of three architecture forks put to the human. Two candidates were offered. A MACHINE-LOCAL store follows the precedent already in the codebase - the console registry is machine-local state living outside every repository, and the hook fire-ledger is a second instance - and needs no remote, no credentials and no network. A GIT REPOSITORY gives sync across machines and history on the author's own material, at the cost of a remote and a clone. The human answered, verbatim as st029: '#1 yeah i think repo for sure.' Their earlier constraint (st026) had already made the shape hard to satisfy locally: 'it is data that I want silently synced without needing per-update permission' - and nothing syncs to a single machine. The repo answer resolves that tension rather than creating it.";
        :>> decision = "The library is a GIT REPOSITORY that the author owns. Six clauses. CLAUSE A - THE REPOSITORY IS THE SOURCE, THE CLONE IS A CACHE. Each machine holds a clone under machine-local state, beside the console registry and the fire-ledger rather than inside any project. No project tree contains the library, and no project's gate reads from it. CLAUSE B - SYNC IS FAST-FORWARD ONLY, AND SILENT WHEN IT SUCCEEDS. Refreshing the cache is a fetch and a fast-forward. It asks nothing, prints nothing on success, and NEVER merges: the cache is read-only downstream, so a non-fast-forward is a signal that something wrote to the clone locally, which is a defect to report rather than a merge to perform. CLAUSE C - AN UNREACHABLE REMOTE IS A STATED FALLBACK, NOT A FAILURE. When the fetch cannot run, the last-good cache is used and the surface SAYS the library is stale and names how stale. Offline must not block work, and it must not silently masquerade as current - the same honest-state rule that separates a control that cannot fire from one with nothing to catch. CLAUSE D - PUBLISHING BACK IS AN EXPLICIT ACT, AND IT IS A COMMIT. Improving a unit inside a project and publishing it writes a commit to the library repository. It is never silent: silent sync is a property of CONSUMING the library, never of writing to it, because a write is the one direction where an unnoticed action costs someone else their content. CLAUSE E - HISTORY IS GIT'S, AND NEVER REWRITTEN. The library repository inherits the same rule as every keel tree (D0129): integrate by merge, never rebase, squash or force-push. A unit version recorded by an installing project must resolve forever, and rewriting library history would orphan every project's recorded pin. CLAUSE F - WHAT A PROJECT RECORDS IS A PIN, NOT A POINTER. An activated unit's version is recorded in the PROJECT's tree and does not move when the library moves (srActivatedUnitVersionIsPinned). The library advancing changes what is AVAILABLE; it changes nothing that governs.";
        :>> rationale = "WHY THE REPOSITORY WINS DESPITE THE LOCAL PRECEDENT. The console registry and the fire-ledger are machine-local for a reason that does not apply here: both describe THIS MACHINE - which projects this console can reach, which hooks fired on this host - and neither is meaningful anywhere else. The library is the opposite kind of thing: it is the author's material, identical on every machine they work from, and its whole purpose is to be the same everywhere. Applying the machine-local precedent here would have followed the letter of an existing pattern against its reason. WHY THE HUMAN'S OWN EARLIER CONSTRAINT DECIDED IT. 'Silently synced' is not satisfiable by a machine-local store. There is nothing to sync with. Had the fork been decided the other way, srLibraryAvailableWithoutInstall would have been met on one machine and quietly broken on the second - and the second machine is where the failure would surface, days later, as content mysteriously missing. WHY FAST-FORWARD-ONLY RATHER THAN MERGE. A merge in the cache means someone edited the clone in place, which is exactly the fork-your-local-copy move that ends the parity story. Refusing to merge turns that into a loud, immediate report instead of a divergence nobody notices until two machines disagree about what a unit says. WHY PUBLISHING IS LOUD WHEN CONSUMING IS SILENT. The asymmetry is deliberate and is the whole safety argument. Consuming silently is safe because clause F makes library content inert until a project activates it. Writing silently is not safe at all: it changes what every other machine will consume, and it is the one operation whose blast radius extends past the person performing it. WHAT THIS DECISION DOES NOT SETTLE, and must not be read as settling: how the keel BINARY is delivered and pinned (fork 2, the wrapper), and how a unit declares its engine range (fork 3). The library carrying content is independent of both. COST OF NOT DECIDING. srLibraryAvailableWithoutInstall, srAvailabilityIsNotActivation and srActivatedUnitVersionIsPinned cannot be refined into work: none of them can be given a Gherkin scenario without knowing whether the library has a remote.";
        :>> consequences = "Program A becomes refinable. The three library requirements can now be taken through backlog-refinement into Gherkin scenarios and sprinted. TWO ALREADY-FOUND DEFECTS GET WORSE UNDER THIS DECISION AND ARE NOW URGENT, which is the finding this Decision surfaces rather than one it creates. The unit manifest currently carries FOUR machine-absolute path keys naming this machine's home directory, and it bumps unit versions with no content change. Machine-absolute paths in a file that only ever lived in one repository were a latent defect; in a library published to a repository other machines pull, they are a guaranteed break. The no-op version bump is worse for the same reason: a project deciding whether to update reads the version, and a version that moves without content moving makes every update decision noise. Both are now filed against Program A rather than deferred. A new failure mode enters the model and is stated rather than discovered later: the library remote is a dependency the engine did not previously have. Clause C bounds it - unreachable is a stated staleness, never a block and never a silent pretence of currency. The library repository is subject to the same history rule as every other keel tree, so a project's recorded unit version resolves permanently.";
    }

    // acceptance event (D0121 review-queue sign-off; D0066/D0106 — human-judged, not fabricated)
    verification d0250Accept : Test { :>> id = "764a2a3b-11f0-448d-a235-065f0cf86174"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0250AcceptR1 : TestResult { :>> id = "b9a0cb11-9415-464e-9c99-788e77012924"; :>> outcome = VerdictKind::pass; :>> judgedAgainst = "1e94ff1"; :>> judgedAt = "2026-08-29"; :>> judgedBy = "wweatherholtz"; }
}
