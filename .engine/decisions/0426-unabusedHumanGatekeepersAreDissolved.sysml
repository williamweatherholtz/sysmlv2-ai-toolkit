// D0426 (status: the `status` field below is the truth) — unabusedHumanGatekeepersAreDissolved: every guard or refusal that gatekeeps a human's act and has not been abused is dissolved outright or reduced to a recorded warning - the whole set, enumerated from the code, not one edge case
// Recorded via `keel record decision` (D0105 RMWX axis; issue054). Acceptance is a separate explicit
// human gate (method=confirmation, D0106): flip status + add the d0426Accept event on sign-off.
package Decision0426 {
    private import EngineElement::*;
    private import EngineWork::*;
    private import EngineVerification::*;
    private import EngineRelationships::*;

    // #SafetyChange (D0070) - this Decision governs a process/schema change; the co-committed
    // change rides the process-change guard's hard lock.
    #SafetyChange part d0426 : Decision {
        :>> id = "4044c51b-386a-474d-bc9a-2c6bfc102f2c";
        :>> title = "unabusedHumanGatekeepersAreDissolved: every guard or refusal that gatekeeps a human's act and has not been abused is dissolved outright or reduced to a recorded warning - the whole set, enumerated from the code, not one edge case";
        :>> createdAt = "2026-09-10";
        :>> createdBy = "claudeOpus5";
        :>> status = DecisionStatus::accepted;
        :>> context = "D0423 dissolved one refusal on the human's word. Their reply the same day (st116): 'you're kind of missing the point - any guards that have not been abused that gatekeep me should be reconsidered or dissolved outright. it's not this one edge case that's the issue, really.' The record behind the human-facing controls is the same everywhere it was read (issue445, issue446): no refusal is logged, no abuse of the human's channel is documented, and the documented subversions are all the agent's. The principle is already theirs twice over - D0204 (governance binds the AI, never the human) and nControlBindsTheSubvertingActor (us105).";
        :>> decision = "NOT A FORK: the human decided the direction; what remains is enumeration. A control gatekeeps a human when its refusal falls on an act a person performs - accepting a Decision, confirming a claim, tapping the console or deck, editing an item, committing from their own terminal - as opposed to an act an agent performs on their behalf or alone. Every such control that has no observed abuse behind it - no Issue describing an act that happened, no ledger block of a person's act that was later shown wrongful - is dissolved: where the record needs the fact for a later reader, the check writes a WARN line into the record and the write proceeds; where it does not, the check is deleted. The set is enumerated from the code with file:line by a census (dcControlCensusByActorKind runs it against the tree; until it exists a read of every refusal path stands in and says so), each dissolution lands as its own Issue linking here, and a control that binds the AGENT's act is outside this Decision however it may irritate.";
        :>> rationale = "A gate is justified by the loss it prevents, and the loss these prevented has never been observed while the cost - a person refused for the shape of their word, paired devices, quoted spans, read-back - has been paid on every acceptance. The asymmetry is not an accident: the agent is the actor with the documented record of bypass (issue267, issue266, issue256/315/322, issue400, issue434), and controls that bind it stay. A WARN in the record keeps what a reviewer needs - what kind of receipt this is - without making the human's channel conditional on it. What would change it: an observed abuse of a human-facing channel - a person's act recorded and later shown not theirs - restores that one control by a Decision naming the incident.";
        :>> consequences = "The census table is the work list; D0423 is its first row. Candidates already visible from the code read of 2026-09-10 and to be confirmed or struck by the census: the delegated-word checks (D0423); the console and deck device pairing and tap signature refusal (D0334/D0335/D0201 B - the tap is recorded with its device receipt when present, unsigned taps warn); the typographic-quote span requirement on --note (D0375); the acceptance-binds-to-text FAIL on the human's own acceptance when the text moves (D0308 - becomes a WARN naming the drift; the rebind stays available). Outside this Decision: confirmation-authenticity (the judge must be a Person - binds the agent), judgment-request-quality (binds the agent's asks), untrusted-routing and untrusted-taint (bind strangers), every guard on the agent's writes. D0337 itself - every process change waits for the human's word - is a gate on the human's ATTENTION rather than a refusal of their act, and is named here for their reconsideration, not changed. Safety-change: accepted on the human's words in st116; audit-adherence reads each dissolution's co-committed Issue and this Decision as the signed weakening.";
    }
    #DerivedFrom dependency from d0426 to us105;

    // acceptance event (D0121 review-queue sign-off; D0066/D0106 — human-judged, not fabricated)
    verification d0426Accept : Test { :>> id = "e090ed01-e6fe-4fa5-9abc-b5488e7ff4cd"; :>> method = VerificationMethod::confirmation; :>> procedureText = "chat words in st116; the Decision is the whole-set form of D0423 they asked for - their words, verbatim: “any guards that have not been abused that gatekeep me should be reconsidered or dissolved outright. it's not this one edge case that's the issue, really.”"; }
    part d0426AcceptR1 : TestResult { :>> id = "8e811b3f-57cd-46db-a461-6cb67b9c4b92"; :>> outcome = VerdictKind::pass; :>> judgedAgainst = "c1e8b69"; :>> judgedAt = "2026-09-10"; :>> judgedBy = "wweatherholtz"; :>> createdBy = "claudeOpus5"; }
}
