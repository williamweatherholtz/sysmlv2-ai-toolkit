// D0213 (status: the `status` field below is the truth) — adherenceCoversActivation: the enforcement signature includes EFFECTIVE guard state, so capturing or deactivating a guard is a detected weakening
// Recorded via `keel record decision` (D0105 RMWX axis; issue054). Acceptance is a separate explicit
// human gate (method=confirmation, D0106): flip status + add the d0213Accept event on sign-off.
package Decision0213 {
    private import EngineElement::*;
    private import EngineWork::*;
    private import EngineVerification::*;
    private import EngineRelationships::*;

    // #ProspectiveChange (D0070) - this Decision governs a process/schema change; the co-committed
    // change rides the process-change guard's hard lock.
    #ProspectiveChange part d0213 : Decision {
        :>> id = "c5f052d4-e793-4523-b2ee-b8ce469d8380";
        :>> title = "adherenceCoversActivation: the enforcement signature includes EFFECTIVE guard state, so capturing or deactivating a guard is a detected weakening";
        :>> createdAt = "2026-08-24";
        :>> createdBy = "claudeFable5";
        :>> status = DecisionStatus::accepted;
        :>> context = "The 2026-08-24 nine-lens panel found two routes that disarm a control without touching .engine/rules/ at all, so audit-adherence - the D0209 clause-1 gate built the same day for exactly the issue236 self-modification class - could not see either. (a) CAPTURE: adding one line to a guard-less process file converts a CORE, never-deactivatable guard into that process's switchable property, because guard_state returns Core only while NO unit claims the guard. The operations lens reproduced it live: core stale-gate-prose became [INACTIVE] report and its run became 'PASS - 0 scanned, 1 warning' with [guard:stale-gate-prose] PASS — 216 scanned, 0 warning(s), 0 violation(s) reporting 'NOT ACTIVE ... do NOT block'. Worse, the CLI's own deactivate refusal ADVISED the edit ('or give it an so it becomes switchable'). (b) NARROWING: removing a process from activation.toml's active list disarms every guard that process owns. Both land inside the commit keystone, but clause 1 exists precisely because a bypassed hook leaves no trace at commit time - and the hook WAS in fact bypassed on this machine for an entire session (issue240), which is exactly the scenario clause 1 was built for.";
        :>> decision = "The enforcement signature audit-adherence re-derives per commit now includes the EFFECTIVE STATE of every declared guard, not only rule severities and constraint-def presence. For each guard declared as a in .engine/rules/, the state is computed from that commit's tree: CORE when no process claims it (no activation switch reaches it), ACTIVE when a claiming process is in the declared active set, INACTIVE when a declared manifest omits the claiming process. Ranks are CORE > ACTIVE > INACTIVE > absent, so a CAPTURE (Core -> Active or Core -> Inactive) and a DEACTIVATION (Active -> Inactive) both rank as weakenings requiring a co-committed marked Decision. An ABSENT activation.toml still means everything is active (D0138/issue090), so the absent and declared-but-omitting cases stay distinguishable and no project that never adopted a manifest is reported as disarmed. Separately, the deactivate refusal text no longer advises adding an assert constraint; it names the consequence instead.";
        :>> rationale = "Clause 1's premise was that a control must be re-derivable from the tree on infra the agent cannot touch. That premise was sound and its IMPLEMENTATION was too narrow: it read one directory, while the effective enforcement of a guard is a function of three tree facts (its declaration, which process claims it, and the activation manifest). Deriving the state instead of the declaration is what makes the gate match its own stated purpose. The alternative - forbidding guard-less processes from asserting guards - would break the legitimate case where a process genuinely owns a guard, and would not address narrowing at all.";
        :>> consequences = "A commit that captures a core guard or narrows activation without a co-committed marked Decision now FAILS audit-adherence in CI with the guard named and the transition shown. Verified by two hook-bypassed negative probes in a throwaway worktree: capturing stale-gate-prose into the guard-less report process reported 'guardstate:stale-gate-prose: blocking/bound/core -> present/inactive' at exit 1, and removing doc-sync from the active list reported 'guardstate:doc-sync: warning/active -> present/inactive' at exit 1; the real history still PASSES. Two unit tests pin the rank ordering and the camel-to-kebab convention shared with activation. Resolves issue242. The declarative keel controls surface is NOT covered by this and is tracked separately as dcControlsReportArming.";
    }

    // acceptance event (D0121 review-queue sign-off; D0066/D0106 — human-judged, not fabricated)
    verification d0213Accept : Test { :>> id = "6fb59acd-534a-4d22-bf81-478f331ff69f"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/10."; }
    part d0213AcceptR1 : TestResult { :>> id = "29da5243-0625-4846-8e00-304f91cc6df4"; :>> outcome = VerdictKind::pass; :>> judgedAgainst = "543e1fa"; :>> judgedAt = "2026-08-24"; :>> judgedBy = "wweatherholtz"; }
}
