// D0164 — PROPOSED-AND-APPLIED on the strength of the human's own acceptance words on D0159:
// "viewpoints should be activateable/disableable just like processes". Mirrors accepted D0138.
// #ProspectiveChange (D0070): extends the activation contract with a second namespace.
package Decision0164 {
    private import EngineElement::*;
    private import EngineWork::*;
    private import EngineVerification::*;
    private import EngineRelationships::*;

    #ProspectiveChange part d0164 : Decision {
        :>> id = "e29c6b04-7a51-4d38-9f62-04b8ea15c73f";
        :>> title = "D0164: a Viewpoint is activatable like a process — a second namespace in the activation contract";
        :>> createdAt = "2026-08-19";
        :>> createdBy = "claudeOpus5";
        :>> status = DecisionStatus::accepted;
        :>> context = "THE HUMAN'S ACCEPTANCE OF D0159 CARRIED NEW DIRECTION BEYOND THE DECISION IT SIGNED: 'viewpoints should be activateable/disableable just like processes. maybe more kind of business ideas (like roles?). maybe this should be a composeable idea or kind of SDK that could drive other extensions.' The first clause is a clear, bounded requirement and is what this Decision implements. THE GAP IT NAMES IS REAL AND WAS MEASURED WHILE ANSWERING A DIFFERENT QUESTION (issue149): activation governs GUARDS, so `keel deactivate` reached 6 of 18 processes and NO viewpoint at all, while this repository declares 32 Viewpoints. A project adopting keel could refuse a process it did not want and could not refuse a LENS - so all 32 concerns appeared on its surfaces whether or not it had any interest in them, and the console's navigation and act-surface obligation bar are both derived from that set. D0138 already established the pattern and the invariant: adoption is DECLARED, not inferred, and an absent manifest means everything is active so that a project which never adopted a control has not violated it. Nothing about that pattern is specific to processes.";
        :>> decision = "PROPOSED AND APPLIED: `.engine/contracts/activation.toml` gains a `[viewpoints] active = [...]` section, read by the same loader and governed by the same rule as `[processes]` - an ABSENT key means every declared viewpoint is active, a declared-but-EMPTY list means none, so presence is matched rather than emptiness. `Activation::is_viewpoint_active` is the predicate. TWO PLACES OBSERVE IT, chosen so that deactivation means one thing rather than several. (1) `surfaces_json` SKIPS an inactive viewpoint, which is the single derivation behind the console's navigation and its act-surface obligation bar - so filtering there means every consumer agrees and a project that turned a lens off is not repeatedly invited to look through it. (2) The `viewpoint-renderer` guard skips it, exactly as a deactivated process's guards are skipped: a project that declared it does not use this lens has not violated a rule about the lens. `concern-coverage` DELIBERATELY STILL REPORTS IT - an unwatched concern is a fact about the project, and hiding it would convert a deliberate choice into an invisible gap. `keel activation` lists all 32 viewpoints with their state beside the processes, and `keel activate`/`keel deactivate` resolve a name in EITHER namespace, refusing an ambiguous name rather than guessing which to switch. THE WRITER NOW EMITS BOTH SECTIONS ON EVERY WRITE, because absence has meaning: writing only the edited section would silently re-activate every process the project had turned off. WHY APPLIED RATHER THAN HELD: the human stated the requirement in their own words in an acceptance record, and the mechanism is a faithful mirror of a contract they have already accepted, adding no invariant and no exception. If they reject the mechanism it comes out - the removal path is below.";
        :>> rationale = "WHY A SECOND NAMESPACE RATHER THAN TREATING VIEWPOINTS AS UNITS: a process unit bundles a skill, rules and GUARDS, and activation switches enforcement. A viewpoint is a declared LENS with a renderer, and switching it changes what the project LOOKS AT. Folding the second into the first would have required inventing a guard for every viewpoint to give it something to switch, which is enforcement invented to satisfy a data model. Two namespaces in one contract file keeps one home for 'what this project has adopted' while keeping the two meanings distinct. WHY `concern-coverage` STILL REPORTS AN INACTIVE VIEWPOINT, which is the choice I would defend hardest: the whole point of that view is to audit which stakeholder concerns are SERVED, and a concern nobody watches is exactly what it exists to surface. Suppressing deactivated lenses would let a project reach 100% concern coverage by turning off the concerns it was failing - the Goodhart failure §1.7 warns about, available in one command. THE HUMAN'S OTHER TWO IDEAS ARE NOT DESIGNED HERE and are recorded rather than absorbed: 'business ideas (like roles?)' and 'a composeable idea or kind of SDK that could drive other extensions' describe a general extension mechanism of which process- and viewpoint-activation would be two instances. That is a larger design than this, and folding a speculative SDK into a Decision that implements one clear sentence would repeat draft 1 of D0161 - designing from an idea rather than from a stated outcome.";
        :>> consequences = "IF ACCEPTED: one new section in an existing contract, one predicate, two observation points, and CLI parity between the two namespaces. No schema change, no new model, no invariant exception; `.engine/contracts/activation.toml` remains absent in this repository, so behaviour here is unchanged until someone deactivates something. REMOVAL PATH, stated per D0163's proposed rule: at the DATA level, delete the `[viewpoints]` section - or the whole file - and every viewpoint is active again, which is the documented reset and needs no code change. At the CODE level, drop `is_viewpoint_active` and its two call sites, an ordinary §3a CHANGE with doc-sync; nothing stores state, and no recorded fact becomes unreadable if it disappears. IF REJECTED: viewpoints stay unswitchable, the human's stated requirement goes unserved, and a downstream project adopting keel inherits all 32 of this project's lenses whether or not any of them describe a concern it holds - which is the adoption friction D0054 calls the dominant failure mode. EXPLICITLY NOT INCLUDED: roles, a composable extension SDK, and any per-actor or per-role scoping of viewpoints. Those are the human's larger idea and deserve their own design rather than an implementation smuggled in under this one.";
    }

    // acceptance event (D0121 review-queue sign-off; D0066/D0106 — human-judged, not fabricated)
    verification d0164Accept : Test { :>> id = "a08e3dd9-5fed-4b49-913b-2946802bcba9"; :>> method = VerificationMethod::confirmation; :>> procedureText = "ACCEPT - submitted in the obligations deck review of 2026-08-20 (verdict recorded with no per-item note)"; }
    part d0164AcceptR1 : TestResult { :>> id = "1a4f8949-ee2c-4bf3-a1c7-a284b14541bc"; :>> outcome = VerdictKind::pass; :>> judgedAgainst = "b7e000d"; :>> judgedAt = "2026-08-20"; :>> judgedBy = "wweatherholtz"; }
}
