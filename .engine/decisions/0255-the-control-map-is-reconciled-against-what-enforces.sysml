// D0255 (status: the `status` field below is the truth) — The control map is reconciled against the events the binary emits, and a partial-resolution claim is declared unenforceable
// Recorded via `keel record decision` (D0105 RMWX axis; issue054). Acceptance is a separate explicit
// human gate (method=confirmation, D0106): flip status + add the d0255Accept event on sign-off.
package Decision0255 {
    private import EngineElement::*;
    private import EngineWork::*;
    private import EngineVerification::*;
    private import EngineRelationships::*;

    // #ProspectiveChange (D0070) - this Decision governs a process/schema change; the co-committed
    // change rides the process-change guard's hard lock.
    #ProspectiveChange part d0255 : Decision {
        :>> id = "17524fc4-4320-41ea-bec5-2af44c35cf61";
        :>> title = "The control map is reconciled against the events the binary emits, and a partial-resolution claim is declared unenforceable";
        :>> createdAt = "2026-08-29";
        :>> createdBy = "claudeOpus5";
        :>> status = DecisionStatus::accepted;
        :>> context = "D0254 named implemented-but-undeclared as the third failure class after finding the launcher's dirty-tree refusal absent from a nine-entry control map, and filed issue304 to reconcile the map against the enforcement the binary actually implements - deliberately unestimated, because estimating it was the work. Reading the model back after sprints 485 and 486 then exposed a second defect, in my own output: issue303 and issue304 both computed as CLOSED while each sprint's closeOut gate said in plain words that they stay OPEN. Both DoDs had said 'resolves ... in part'.";
        :>> decision = "Three clauses. CLAUSE A - THE MAP IS RECONCILED AGAINST control-events.toml, AND STAYS SO. Every declared control event names the control it is the FIRING of, or `control = 'none'` with a `controlNote` saying why it is instrumentation rather than enforcement. Guard 54 `control-map-reconciled` resolves every named control against the control map and treats a missing `control` line as a violation, so silence reads as a gap rather than as consent. Five firing controls entered the map this way - ctlPostEditGate, ctlTurnBoundaryGate, ctlAuditAdherence, ctlAdoptionCheck, ctlOverrideObligation - two of which BLOCK. CLAUSE B - THE GUARD IS SCOPED TO ADOPTION. A project declaring no controls has nothing to reconcile and the guard reports zero scanned, never a violation. This was caught by the existing foreign-tree test, not by review: the unscoped version fired on every fresh `keel init` scaffold, because the engine ships control-events.toml while the control map is a project's own instance data. CLAUSE C - issue305 IS DECLARED UNENFORCEABLE, WITH ITS REASON. A DoD claiming it resolves an Issue 'in part' closes it outright, because resolution is computed from resolver completion and has no partial state. No structural signal distinguishes a partly-addressing resolver from a fully-addressing one. A wording gate was attempted and REMOVED after a false positive on first contact with the corpus.";
        :>> rationale = "WHY control-events.toml IS THE RIGHT ANCHOR. A control that can fire leaves a counted record, and `control-event-coverage` (D0193) already cross-checks that declaration against the event names the binary EMITS. Anchoring the map to it chains binary -> events -> controls, so the map is reconciled against something already tied to the code. A fresh hand-maintained inventory would be one more list to drift, which is the defect rather than the fix. WHY THE SCOPING CLAUSE IS NOT A WEAKENING. issue090 is the precedent: six hard guards once blocked every project without this repo's rules, because an absent declaration was reported as a violation. D0231 states the rule - a control must not fire on a project that never adopted it. The unscoped guard reproduced that exactly, and the foreign-tree test caught it before it shipped. That test earning its keep is itself the argument for nForeignTreeVerification. WHY THE WORDING GATE WAS REMOVED RATHER THAN TUNED. It flagged .tracking/backlog.sysml on its first run - a false positive - and its design was wrong twice over: file-scoped, while #Resolves edges and DoD prose live in different files, and 'in part.' matches innocent sentences. D0232 already records three attempts to gate verdict WORDING at 111, 35 and 1 false positives, with the conclusion that language policing does not calibrate here. This was the fourth. A guard with false positives is one an actor learns to ignore, which is D0197's thesis, so an honest declared gap beats a check that cries wolf. WHAT ACTUALLY CAUGHT THE PARTIAL-RESOLUTION DEFECT, and it is the only thing that would: reading the computed view back after writing it. `keel open-issues` said CLOSED while the closeOut gate said OPEN, and the disagreement was visible the moment both were read together.";
        :>> consequences = "The control map goes from 9 entries to 15 across D0254 and this Decision. Controls with evidence: 3 of 15 - one armed by view-probe, two proven by test. THAT RATIO GOT WORSE BY DECLARING HONESTLY, and that is the point: 1-of-9 with `uncoveredHazards: []` was a cleaner-looking number over a less complete map. Two #Resolves edges are re-pointed: issue303 to the OPEN `dcProveTheRemainingControls` task, issue304 to this sprint. issue303 correctly reads open again. A RESIDUAL IS CARRIED, not hidden: a downstream project that builds its own control map still inherits the shipped `control` bindings, which name THIS project's controls. Those bindings are instance knowledge riding in an engine file, and the guard would mis-fire there. Recorded in the guard's own doc rather than behind a passing check.";
    }

    // acceptance event (D0121 review-queue sign-off; D0066/D0106 — human-judged, not fabricated)
    verification d0255Accept : Test { :>> id = "c44286b7-b5fe-42ae-bd34-58e706b34cee"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0255AcceptR1 : TestResult { :>> id = "0e862b8d-763e-4f68-a2b6-e3a161916244"; :>> outcome = VerdictKind::pass; :>> judgedAgainst = "0d657ce"; :>> judgedAt = "2026-08-29"; :>> judgedBy = "wweatherholtz"; }
}
