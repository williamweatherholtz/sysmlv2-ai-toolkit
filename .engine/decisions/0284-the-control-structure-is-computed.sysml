// D0284 (status: the `status` field below is the truth) — keel's own control structure is a computed view: authorities, actions, data and feedback derived from the facts that wire them, anchors authored only where no fact can yield them
// Recorded via `keel record decision` (D0105 RMWX axis; issue054). Acceptance is a separate explicit
// human gate (method=confirmation, D0106): flip status + add the d0284Accept event on sign-off.
package Decision0284 {
    private import EngineElement::*;
    private import EngineWork::*;
    private import EngineVerification::*;
    private import EngineRelationships::*;

    part d0284 : Decision {
        :>> id = "909462a9-2a68-4146-8024-d9cda0338e6b";
        :>> title = "keel's own control structure is a computed view: authorities, actions, data and feedback derived from the facts that wire them, anchors authored only where no fact can yield them";
        :>> createdAt = "2026-09-02";
        :>> createdBy = "claudeOpus5";
        :>> status = DecisionStatus::accepted;
        :>> context = "The human's first step (st066): a defined system for keel itself - what authorities are present, how they interact, what data is sent - and, mid-turn, that the definition be computed from existing facts as far as possible. STPA step 2 had zero instances while steps 1 and 3 had many. A first attempt authored 47 parts with a prose body each; two guards refused it for adjacent reasons and the human named the real one. Sprint 518 cut the authored file to its residue (8 controller anchors, 6 controlled processes, 5 process models, 9 hazard-to-process edges); this Decision delivers the computed rest, with its prerequisite (the CLI facts, D0283) landed first because effect on a command is what tells a control action from feedback.";
        :>> decision = "keel show control-structure computes STPA step 2 for the project's own workflow. SOURCES, each a fact that already wires the authority: hook events from .claude/settings.json (each event one action on the agent's turn, its verdict kind from the dispatcher's contract - Stop, PostToolUse and SubagentStop block, PreToolUse denies or advises, the rest advise); git hooks from .githooks/ (each file one refusal on the shared history, its data the keel commands it runs); workflows from .github/workflows/ (decision-* files are the channel acting on the model by delegation, the rest are CI failing the build - and each yields a run-status feedback path to the human); the CLI facts (effect writes or both is an action the agent issues, reads is feedback to the agent; the process acted on follows the family; accept is the human's because the write layer refuses an AI actor for it, and a test holds that list equal to the write layer's); declared deciders from github-actors.toml (the human's channel action, naming the logins); the remote's branch protection fetched LIVE via gh api and reported unverified when offline - never copied into the tree - yielding the remote's refusal when force-push is blocked and a plain reading of whether CI is preventive or detective; the console's approve queue when serve exists; deliverable drift as feedback when a manifest exists. ROLES are the view's stable ids; an authored Controller or ControlledProcess named for the role decorates it with title and id, and authored ProcessModels render with their beliefs and the Issues those beliefs cite; a project that has authored none computes the same actions with null anchors. The safety viewpoint's renderer is this lens, bound by a committed D0067 transform because the registry is human-owned.";
        :>> rationale = "WHY COMPUTED AND NOT AUTHORED, beyond Invariant 1: the structure changes whenever a hook is added, a workflow step lands or a command is dispatched, and an authored diagram would be wrong by the next sprint with nothing to say so. Tested: removing UserPromptSubmit from a scaffold's settings.json removes its action on the next run with no model file touched. WHY ROLES AND NOT ANCHOR NAMES: a fresh project has authored nothing and still has every authority; the view must describe it, so identity lives in the view and the model may decorate it. WHY THE REMOTE IS FETCHED AND NEVER STORED: branch protection is the one fact here that lives outside the repository, and a copy would be a claim about the remote that the remote can falsify silently - the same reason the view says unverified offline instead of guessing. WHAT THE LIVE RUN SAYS ABOUT THIS REPOSITORY, computed not asserted: 44 actions, 76 feedback paths, no inert controller; CI is DETECTIVE - no status check and no review is required on main, force-push is blocked - so a red build reports a commit already on the shared history; the deliverable is acted on by no keel command, which is true and now visible; a fresh scaffold has an inert decision channel, because the channel is a unit a project imports. Those four readings are the first input to UCA analysis (dcStpaProcessForKeel), and none of them was written by hand.";
        :>> consequences = "The safety viewpoint stops reading planned; viewpoint-renderer warns on two viewpoints instead of three. dcControlStructureIsComputed is delivered and nKeelIsADefinedSystem has its measurable half. The STPA process (dcStpaProcessForKeel) and the verification revamp (dcVerificationByAuthority) have the structure they bind to and can now be written as forks. What is NOT delivered: a graph render through keel render - the JSON is the contract and the console can draw it; and UCAs, which are the next process's output, not this view's. REMOVAL PATH (D0163): delete the lens, its fact and its dispatch arm together (the cli-surface-declared guard refuses a partial removal), rebind the safety renderer to planned by a transform, and the authored residue stands on its own as it did in sprint 518.";
    }

    // acceptance event (D0121 review-queue sign-off; D0066/D0106 — human-judged, not fabricated)
    verification d0284Accept : Test { :>> id = "c6e4f378-9d0e-4f78-bf62-ac38620dd22c"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0284AcceptR1 : TestResult { :>> id = "60f9010f-11a7-4559-a397-ec0a713f8f09"; :>> outcome = VerdictKind::pass; :>> judgedAgainst = "f63bbf2"; :>> judgedAt = "2026-09-02"; :>> judgedBy = "wweatherholtz"; }
}
