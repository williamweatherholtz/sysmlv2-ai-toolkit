// D0258 (status: the `status` field below is the truth) — Priority assessment joins Backlog Refinement: rank is reassessed against computed signals, and inversion warnings are discharged rather than accumulated
// Recorded via `keel record decision` (D0105 RMWX axis; issue054). Acceptance is a separate explicit
// human gate (method=confirmation, D0106): flip status + add the d0258Accept event on sign-off.
package Decision0258 {
    private import EngineElement::*;
    private import EngineWork::*;
    private import EngineVerification::*;
    private import EngineRelationships::*;

    // #ProspectiveChange (D0070) - this Decision governs a process/schema change; the co-committed
    // change rides the process-change guard's hard lock.
    #ProspectiveChange part d0258 : Decision {
        :>> id = "4ea8862d-3705-4c43-8b04-6a0d4e5dc75b";
        :>> title = "Priority assessment joins Backlog Refinement: rank is reassessed against computed signals, and inversion warnings are discharged rather than accumulated";
        :>> createdAt = "2026-08-29";
        :>> createdBy = "claudeOpus5";
        :>> status = DecisionStatus::accepted;
        :>> context = "The human, on seeing the frontier's head (st035, verbatim): 'reorder - assessing priority should be part of our agile process.' The computed evidence behind the instruction: the priority-inversion guard carried SIX standing warnings naming exactly the inversions - kg/recall items outranking High-issue resolvers - and the severity map showed a CRITICAL resolver (dcRenameIsAChange, issue273) at rank 16, below two items resolving nothing. D0052 makes declaration order the priority mechanism, and add-task APPENDS, so an unattended backlog's order encodes ARRIVAL, not judgment. The guard had been saying so for weeks; a warning nobody acts on is arrival order with extra steps. A second defect surfaced by the same pass: sprint 483's story sat on the ready frontier because its DoD result was never stamped when the sprint closed - the frontier itself was carrying a bookkeeping error as work.";
        :>> decision = "Two clauses. CLAUSE A - THE STEP. Backlog Refinement gains refineAssessPriority: whenever refinement touches the backlog, or the priority-inversion guard carries a standing warning, rank is REASSESSED against the computed signals - resolver severity first (Critical > High > Medium > none; the guard's warnings ARE this signal), then the human's standing direction, then stability within class. Every inversion warning is discharged by the reorder or explicitly justified in the block comment. The reorder comment names the signal that drove it, so the next reader can disagree with the judgment rather than reverse-engineer it. CLAUSE B - THE REORDER PERFORMED UNDER IT. Twenty ready backlog items re-ranked by the rule: the Critical resolver first, thirteen High-issue resolvers (the double-High resolver dcIntakeHasAWritePath ahead of single-High peers), five Mediums, no-issue items last. Inversion warnings: six -> zero. The stale sprint-483 story is stamped with its long-since-earned result.";
        :>> rationale = "WHY A PROCESS STEP AND NOT A GUARD ESCALATION. The tempting fix is to make priority-inversion blocking - and it would be the over-strict failure again: severity is ONE signal, and a deliberate inversion (a quick Medium unblocking three Highs) is legitimate, so a hard gate would train bypasses (D0197). The warning is the right tier; what was missing was a process step OBLIGED to read it. Judgment stays with the assessor, the signal stays computed, and an ignored warning now has a named owner. WHY SEVERITY LEADS THE SIGNAL ORDER. It is the one ranking input the model already computes per item, it is exactly what the guard compares against, and this pass's own evidence shows arrival order inverting it badly - Critical below no-issue is not a judgment anyone made, it is entropy. COST OF NOT DECIDING. The frontier keeps decaying toward arrival order between human interventions, the guard keeps warning into the void, and auto-follow (D0052) faithfully executes the wrong order.";
        :>> consequences = "The agile-workflow definition carries the step (this Decision rides the keystone lock for that edit). The backlog is reordered under it; zero standing inversion warnings. Auto-follow now serves dcRenameIsAChange (Critical) first. The step binds the AI as refiner; it imposes nothing on the human (their standing direction is an INPUT to the ranking, not a duty). NOT changed: D0052's mechanism. Declaration order remains the priority; this step is about keeping that order MEANT rather than inherited.";
    }

    // acceptance event (D0121 review-queue sign-off; D0066/D0106 — human-judged, not fabricated)
    verification d0258Accept : Test { :>> id = "70d985c9-366f-4b8d-a202-f19e8da522dc"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0258AcceptR1 : TestResult { :>> id = "36d493e6-ca4c-489f-9841-4006a3d67f0e"; :>> outcome = VerdictKind::pass; :>> judgedAgainst = "616d613"; :>> judgedAt = "2026-08-30"; :>> judgedBy = "wweatherholtz"; }
}
