// D0399 (status: the `status` field below is the truth) — cliVerbCountTarget: D0273 promised under 25 visible verbs and the lens collapse landed at 70 - collapse the remaining families too, or amend the clause to the measured number
// Recorded via `keel record decision` (D0105 RMWX axis; issue054). Acceptance is a separate explicit
// human gate (method=confirmation, D0106): flip status + add the d0399Accept event on sign-off.
package Decision0399 {
    private import EngineElement::*;
    private import EngineWork::*;
    private import EngineVerification::*;
    private import EngineRelationships::*;

    // RESEARCH: Measured 2026-09-09 against .engine/cli/commands.sysml at 649b433 (grep over the CliCommand facts, re-runnable): 107 facts, of which 37 are family lens (reached as keel show <lens>) and 70 are top-level verbs; keel show hardening helpCoverage.dispatched reads 71 arms in main.rs. By family the 70 verbs are gating 14, orientation 12, authoring 10, integration 8, governance 7, rendering 6, distribution 6, channel 6, knowledge 1. By effect 34 of the 70 are read-only (gating 12: adoption-check assured audit audit-adherence audit-ci-runs audit-history check check-engine gate guard rules validate; orientation 11 beyond show itself; rendering 4; distribution 2; channel 2; governance advance; integration projects; knowledge recall), 19 write, 11 read and write, 6 are tooling. Folding every read-only verb into a router still leaves 36 verbs plus the routers, so under 25 is reachable only by also collapsing the writers (authoring 9 into record, channel 3, distribution 2) and the read-write set. Call-site census for the gating family alone: git grep of keel followed by one of its 12 verbs matches 428 files and 1244 occurrences outside target/, including .githooks and .github/workflows - the enforcement surface, so each such collapse is a #SafetyChange Decision under D0209 clause 2, not only a rename.
    part d0399 : Decision {
        :>> id = "7a5644b1-e2a3-4c9d-8bbe-9eb1a3769206";
        :>> title = "cliVerbCountTarget: D0273 promised under 25 visible verbs and the lens collapse landed at 70 - collapse the remaining families too, or amend the clause to the measured number";
        :>> createdAt = "2026-09-09";
        :>> createdBy = "claudeOpus5";
        :>> status = DecisionStatus::accepted;
        :>> context = "D0273 (accepted) removed 43 top-level lens names into keel show <lens> in one commit with its 118 call-site rewrites, and its consequences promised that the visible verb count falls from roughly 111 dispatch arms to under 25. The number was written without deriving it from the measurement in the same Decision's context: 43 lenses out of about 111 arms already implied roughly 66 remaining, and the tree today holds 70 verb facts and 71 arms. issue338 records the miss; dcRemainingCliFamilies exists so that one of two honest resolutions happens rather than leaving a criterion nobody revisits. Every number above is from the facts file and the source at HEAD; the estimate of effort per family is my judgment from sprint 512, which did the lens collapse.";
        :>> decision = "OPTION A (collapse the remaining families the way sprint 512 collapsed the lenses): gating becomes keel gate <check> or keel audit <kind> (12 verbs to 2), the read-only orientation verbs join show (11 to 0), rendering becomes keel render <what> (4 to 1), the authoring writers become keel record <what> (9 to 1), channel becomes keel github <verb> (5 to 2). Each family is its own D0067 transform with a byte-equality baseline and its call-site rewrites in the same commit; no alias window, per D0273's own rule. COST: five breaking changes to a surface that hooks, CI, 428 files of docs and skills, and the human's own hands call by name; the gating and channel families sit on the enforcement surface so two of the five are #SafetyChange Decisions awaiting the human's word each; estimate one day per family from sprint 512's shape, five days total, and every downstream project holding skills that name these verbs must update engine and skills together. Lands the verb count at roughly 20 and makes D0273's clause true as written. OPTION B (amend the clause to the measured number): this Decision carries a #SupersedeClause edge to d0273 reversing only the under-25 consequence, and states what the collapse achieved - 111 arms to 70 verbs and 37 lenses behind one router - and that the target was a wish written without a derivation. COST: one Decision and no code; the 34 read-only verbs stay separate verbs, so a newcomer still reads 70 names in keel --help rather than about 20, and the half-connection D0273 named (a lens that is also a verb) is closed only for lenses, not for gate-shaped reads. VERIFY on either: keel show hardening helpCoverage.dispatched reads back the number the standing Decision states, and the two agree - 71 under B, the post-collapse count under A. Do-nothing is not offered as an option because the DoD of dcRemainingCliFamilies is exactly the refusal to leave a recorded criterion unmet and unrevisited.";
        :>> rationale = "WHY NOT DECIDE THIS AUTONOMOUSLY: option A is a second breaking rename of the commands the human types every day and of the hooks and CI that gate their commits; the value of a shorter help screen against the cost of relearning twelve gating verbs is theirs to weigh, and the DoD says in so many words that A is not started on my initiative. WHAT I RECOMMEND, AND WHAT WOULD CHANGE IT: OPTION B. The measurement shows under 25 was never implied by the change D0273 actually made - the lens collapse could only ever reach about 66 - so the clause is a miscalculation to correct, not a promise to keep at the cost of five more breaking changes; the gating verbs in particular are the names in every hook, CI step and skill, and their separateness (validate is not guard is not gate) is what CLAUDE.md section 5 teaches. It would change to A if the human wants the typed surface itself small - if they find themselves reading keel --help to recall a verb, or if a downstream adopter's onboarding names the verb count as friction - both observables only they or an adopter hold. It would also change to A for the gating family alone if issue419 (validate reads clean over a tree it does not judge) is resolved by merging validate and check-engine, since that is already one collapse in that family; that is the one sub-option I would take on my own under B, as a resolver of issue419 rather than of this Decision.";
        :>> consequences = "On A: five sprints in the sprint 512 shape, each a D0067 transform with a control-total dry run and its call-site rewrite in one commit, two of them (gating, channel) carrying #SafetyChange and waiting for the human's word; CLAUDE.md sections 2, 4 and 5, guards.md, every skill and the hook and CI files are rewritten in the same commits; dcRemainingCliFamilies is done when hardening reads the post-collapse count and the Decision states it. On B: a #SupersedeClause edge from this Decision to d0273 lands with it and reverses the under-25 consequence only - d0273's removal of the 43 names, its one-commit rule and its no-alias rule all stand; issue338 is resolved by dcRemainingCliFamilies with hardening reading 71 and this Decision stating 71; the verb families keep their names and future consolidation, if any, is a new Decision with its own measurement.";
    }

    // acceptance event (D0121 review-queue sign-off; D0066/D0106 — human-judged, not fabricated)
    verification d0399Accept : Test { :>> id = "a8e54301-3c11-4f73-bbd5-49122b3e6dfc"; :>> method = VerificationMethod::confirmation; :>> procedureText = "Selected on the decision brief copy-out (fifteenth publish), pasted into chat 2026-09-11; d0399 option A chosen over the recommended B. No note added. - their words, verbatim: “A: fold the gating, orientation, rendering, authoring and channel families into gate, audit, show, render, record and github - one breaking transform each”"; }
    part d0399AcceptR1 : TestResult { :>> id = "8a79166e-05c6-48e7-bfa1-37f5d7397485"; :>> outcome = VerdictKind::pass; :>> judgedAgainst = "3e6c518"; :>> judgedAt = "2026-09-11"; :>> judgedBy = "wweatherholtz"; :>> createdBy = "claudeOpus5"; }
}
