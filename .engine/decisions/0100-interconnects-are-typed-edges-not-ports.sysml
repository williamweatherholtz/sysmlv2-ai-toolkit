// =====================================================================
// D0100 — interconnect modeling is the typed-relationship layer, NOT ports; and the sr19 white/black-box
// design follows from it. Triggered by reframing sr19ServeWhiteboxBoundary (white-box = critique a
// system's internals; black-box = critique interconnectivity between systems) and the question "should
// interconnects be SysML ports — have we been reinventing the wheel?". Researched against SysML v1/v2 +
// INCOSE + Friedenthal: SysML keeps TWO distinct layers — the relationship/traceability layer
// (satisfy/verify/derive/refine/allocate/dependency/:>) and the structural-interconnect layer
// (ports/interfaces/item-flows). Our edge algebra IS the first layer (standard, not reinvented); ports
// are the second (runtime payload-bearing flows = deliverable architecture, out of engine scope, D0054).
// Accepted 2026-06-24 by wweatherholtz.
// =====================================================================
package Decision0100 {
    private import EngineElement::*;
    private import EngineWork::*;
    private import EngineVerification::*;
    private import EngineRelationships::*;

    part d0100 : Decision {
        :>> id = "00a1b0c1-4100-42a3-ab5c-516273849700";
        :>> title = "D0100: interconnects are typed relationship edges, not ports (ports = deliverable-domain, D0054); sr19 white/black-box critiques existing boundaries, no schema change";
        :>> createdAt = "2026-06-24";
        :>> createdBy = "wweatherholtz";
        :>> status = DecisionStatus::accepted;
        :>> context = "Refining sr19ServeWhiteboxBoundary, the human reframed it to standard SE terms: WHITE-BOX = critique the INTERNALS of a (sub)system for correctness (component/unit level, cohesion, intra-component); BLACK-BOX = critique the INTERCONNECTIVITY between systems (integration level, coupling, inter-component). This raised a foundational question: should the engine's interconnects be SysML PORTS/interfaces (to give edges identity + defined meaning) — i.e. have we been 'reinventing the wheel' with our own typed-edge 'linked-list'? Researched across SysML v1.6/v2+KerML, INCOSE, IREB, and Friedenthal 'A Practical Guide to SysML' (three independent web sweeps). FINDING (unanimous): SysML maintains TWO distinct metamodel branches — (1) the RELATIONSHIP/TRACEABILITY layer (satisfy/verify/derive/refine/trace/allocate/dependency, all UML-Dependency subtypes; specialization :>/:>>) which asserts accountability/derivation/coverage between named model elements with NO payload (the edge KIND is the meaning); and (2) the STRUCTURAL-INTERCONNECT layer (ports, interface definitions, item flows, connectors, ICDs) which models a PAYLOAD (matter/energy/data/signal) crossing a boundary under a contract. SysML v2/KerML keeps both and makes RELATIONSHIPS first-class (identity + metadata + specializable). The discriminator: can you name the payload crossing the boundary and its direction? -> port/interface; can you only name the kind of relationship between two model elements? -> typed dependency.";
        :>> decision = "(1) ARCHITECTURE CONFIRMED: the engine's interconnects ARE and SHALL REMAIN typed directed RELATIONSHIP edges (the CLAUDE.md §2.2 algebra :>, satisfy, verify, allocate, dependency, supersede, + markers #Resolves/#DerivedFrom/#CharteredBy/#Covers). This is a faithful subset of the SysML relationship vocabulary — NOT reinvention. PORTS/interfaces/item-flows shall NOT be used for engine interconnects: nothing flows across a traceability edge, so a port would be a category error (it falsely asserts a runtime channel + a payload contract that does not exist). Ports/interfaces belong to the DELIVERABLE's runtime architecture (what its components exchange) — deliverable-domain, out of the work-engine's scope (D0054). The edge KIND already defines 'what the interconnect means'; that is sufficient and standard. (2) sr19 DESIGN (supersedes the sprint155 spike's lens-fork conclusion): white-box and black-box critique run over boundaries taken from our EXISTING STRONG STRUCTURE — Need-slices (a Need + its satisfying SRs + allocated Components + verifying Tests = a vertical 'system') and declared views (sr18) — boundaries are RECURSIVE/HIERARCHICAL (a subsystem is a System-of-Interest at a lower tier; ISO 15288 SoI is viewpoint-relative). WHITE-BOX = critique a boundary's INTERNAL elements, reusing the EXISTING CritiqueLens (correctness/completeness/consistency/necessity) — NO new lenses, NO schema/core change. BLACK-BOX = critique the boundary's CUT EDGES (the interfaces) for necessity/minimality/completeness/contract; a black-box finding is an Issue REFERENCING the cut edge (endpoints + kind); the cut-edge count is a free coupling signal. First sweep target = the tier-satisfaction comprehensiveness analysis (per Need-slice), per D0098. (3) GRAPH CLUSTERING DECLINED (now and via other means): DSM/modularity/community-detection auto-decomposition is the standard method for a PHYSICAL architecture graph, but our work/requirements graph already has stronger, more meaningful structure (tiers + concerns); clustering would mangle it (Tests/backlog dominate, low modularity) for high build cost. The 'AI-proposed clusters' clause of sr19's statement is RESCOPED to 'human-declared + structural boundaries'. (4) BLACK-BOX EDGE IDENTITY: edges stay lightweight (from/to/kind, no UUID); a finding references the edge via its endpoints + kind. v2 makes first-class edge identity possible, but giving every edge a UUID is high authoring friction (D0054) for no current need — defer unless many findings per edge are needed.";
        :>> rationale = "ALTERNATIVES on the interconnect model: (i) adopt SysML ports/interfaces for engine interconnects — REJECTED as a category error (no payload flows across traceability edges; INCOSE/IREB/Friedenthal keep the two layers separate; ports would inject phantom flow contracts + heavy authoring friction, the dominant MBSE failure mode, D0054). (ii) make edges first-class relationship elements with identity (v2-legitimate) — DEFERRED (idiomatic in v2 but unneeded now; friction without payoff). (iii) CHOSEN — keep typed directed edges (standard SysML relationship layer); reserve ports for the deliverable's runtime architecture (out of scope). On sr19 lenses: the sprint155 spike proposed ADDING concision/requirementPurity/indicatorQuality to the frozen CritiqueLens enum (a schema CHANGE); SUPERSEDED — the reframing shows white-box critique is internal-element correctness (existing lenses suffice) and black-box is an interface concern (an Issue on the cut edge), so NO schema change is needed. On boundaries: AI-proposed graph clustering — REJECTED for this graph (strong existing structure; clustering high-cost/low-value here, human declined). CRITERIA: standards-alignment (match SysML, don't reinvent or misuse) x friction (D0054, no port/UUID overhead) x scope-discipline (D0054 deliverable-domain stays out) x reuse (lean on sr18 boundaries + sr16 recording + existing lenses).";
        :>> consequences = "sr19 is realized WITHOUT a schema/core change (the frozen CritiqueLens enum is untouched; the spike's add-lenses CHANGE is dropped). sr19Deliver is refocused to the white/black-box-over-existing-boundaries design and split: sr19a (white-box internal-element critique + black-box cut-edge interface critique over a Need-slice/view boundary + the tier-satisfaction sweep, reusing sr18+sr16); AI-proposed clustering is descoped (not a deliverable). sr19ServeWhiteboxBoundary's 'AI-proposed clusters' clause is reinterpreted as 'human-declared + structural boundaries' (this Decision refines that SR's scope). Black-box findings are Issues referencing a cut edge (endpoints+kind). No ports/interfaces enter schema/core. doc-sync: none required to schema (no change); this Decision is the architectural record that the typed-edge interconnect model is intentional + standard (future 'why not ports?' is answered here). No .engine/processes edit, so no #ProspectiveChange keystone. The deliverable-domain interface modeling (ports/flows) remains explicitly out of scope per D0054.";
    }

    verification d0100Accept : Test { :>> id = "00a1b0c1-4100-42a3-bb5c-516273849700"; :>> method = VerificationMethod::confirmation; :>> procedureText = "wweatherholtz attests acceptance of d0100 (engine interconnects are typed relationship edges, not ports — ports are deliverable-domain per D0054; sr19 white/black-box critique runs over existing structural boundaries with no schema change; graph clustering declined; black-box finding = Issue referencing the cut edge) via the explicit choice of 'Yes — record + build sr19a' on 2026-06-24, after three independent research sweeps confirmed SysML keeps the relationship and structural-interconnect layers distinct and our edge algebra mirrors the relationship layer."; }
    part d0100AcceptR1 : TestResult { :>> id = "00a1b0c1-4100-42a3-cb5c-516273849700"; :>> outcome = VerdictKind::pass; :>> judgedAgainst = "19a77b5"; :>> judgedAt = "2026-06-24"; :>> judgedBy = "wweatherholtz"; }
}
