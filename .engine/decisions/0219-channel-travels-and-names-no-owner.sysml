// D0219 (status: the `status` field below is the truth) — channelTravelsAndNamesNoOwner: the decision channel moves as a unit, and who may decide is per-project data - never the repo owner
// Recorded via `keel record decision` (D0105 RMWX axis; issue054). Acceptance is a separate explicit
// human gate (method=confirmation, D0106): flip status + add the d0219Accept event on sign-off.
package Decision0219 {
    private import EngineElement::*;
    private import EngineWork::*;
    private import EngineVerification::*;
    private import EngineRelationships::*;

    // #ProspectiveChange (D0070) - this Decision governs a process/schema change; the co-committed
    // change rides the process-change guard's hard lock.
    #ProspectiveChange part d0219 : Decision {
        :>> id = "ed67e9f6-8c6c-4c35-b512-b34da276e5f1";
        :>> title = "channelTravelsAndNamesNoOwner: the decision channel moves as a unit, and who may decide is per-project data - never the repo owner";
        :>> createdAt = "2026-08-24";
        :>> createdBy = "claudeFable5";
        :>> status = DecisionStatus::accepted;
        :>> context = "The human asked whether the GitHub decision channel is in place and said they want to activate it on another project (asirobots/penumbra), with the explicit constraint: 'don't force me to be owner of every new project. be modular and careful.' Investigating found four defects, three of which would have broken or misfired on the first adoption. (1) TRANSFER: produced three files - definition, skill, unit.toml - while the five files that ARE the channel (two workflows, two scripts, the decider table) stayed home; the guard travelled BY NAME and the machinery not at all, so adoption meant hand-copying. That violates srPortModularProcessUnit, an accepted MUST that a unit move 'without leaving its enforcement behind', and is the same class as issue241 and issue245. (2) OWNER: the issue opener assigned to , which is NOT A PERSON - for asirobots/penumbra it is an ORG, and fails outright, so the mechanism would have broken rather than degraded. (3) IDENTITY IN SOURCE: the decider's login was a literal in decision-record.yml in three places, so every adopting project would have had to edit the workflow - a fork of the mechanism and an edit to its own frozen enforcement surface. (4) WORST, found by round-trip test: shipped THIS project's github-actors.toml verbatim, so every new project silently inherited MY login as its authorized decider and would have recorded acceptances in my name.";
        :>> decision = "FOUR changes. (a) A unit carries its declared EXTRAS: names, per unit, the files it needs to RUN plus the prerequisites the receiving project must satisfy; export carries them and lists both, so an importer is TOLD rather than discovering it when nothing records. Engine files stay engine-relative in the bundle and extras keep their repo-relative path, restored by ONE shared mapper used by both the fresh-import and --update loops. (b) WHO MAY DECIDE is the committed table and nothing else: a mapped login may decide, an unmapped one is refused. is the single implementation - the workflow gate and the recorder can no longer drift apart - and the workflow's job condition is now STRUCTURAL only (decision label, human commenter), with authorization a step that reads the table. An outsider's comment leaves the run GREEN and posts an explanation, because a bystander is not a build failure. (c) Assignment goes to the DECLARED DECIDERS, or to nobody; is never treated as a person. The label is what makes an issue findable, so assignment is a convenience. (d) joins the instance contracts RESETS (the issue243 fix), starting as an empty commented template: the repo owner is not automatically a decider and an ORG can never be one.";
        :>> rationale = "The two goals turned out to be the same goal. A mechanism cannot travel while it has one project's identity welded into it, so de-hardcoding the decider was a PRECONDITION of transferability rather than a separate courtesy - which is why the human's modularity constraint and the portability requirement close together. Declaring extras as data rather than Rust follows the D0184 rule-owners precedent so a project adds its own units without a fork. Keeping the decider table as the single authorization source honours D0105: 'who may decide' and 'whose judgment is attributable' are one fact, and the recorder had always enforced exactly that - only the workflow disagreed with it.";
        :>> consequences = "The decision-channel unit now exports 6 files + unit.toml and round-trips: verified by importing into a throwaway inited project, where the workflows and scripts land in .github/ and the project's own keel-gate.yml survives. Two real bugs were found and fixed by that round trip, both of which had been reporting success: export computed a destination by stripping , and for an extra the strip FAILED and the absolute-path fallback made discard the base, so it tried to copy the file ONTO ITSELF and died with 'used by another process'; and the --update loop had its own -join, so it wrote .github/workflows/x.yml to .engine/.github/workflows/x.yml - inert, in the wrong place, while printing '6 file(s) from upstream'. Both loops now share one mapper. A fresh declares NO decider and refuses any login with the remedy; a regression test pins that no login is inherited. GUARD_NAMES is unchanged. Doc-sync: CLAUDE.md and the decision-channel skill ride this commit.";
    }

    // acceptance event (D0121 review-queue sign-off; D0066/D0106 — human-judged, not fabricated)
    verification d0219Accept : Test { :>> id = "fd396910-23fd-4654-8e73-6102c7d4e5f5"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/17."; }
    part d0219AcceptR1 : TestResult { :>> id = "e309c4ad-2ec4-4c03-a986-3121b1e7c88b"; :>> outcome = VerdictKind::pass; :>> judgedAgainst = "d129343"; :>> judgedAt = "2026-08-24"; :>> judgedBy = "wweatherholtz"; }
}
