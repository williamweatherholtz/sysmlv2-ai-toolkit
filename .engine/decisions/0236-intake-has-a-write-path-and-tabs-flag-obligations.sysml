// D0236 (status: the `status` field below is the truth) — intakeWritePath: the human's words get a sanctioned write path, and a console tab flags what waits on them instead of counting lenses
// Recorded via `keel record decision` (D0105 RMWX axis; issue054). Acceptance is a separate explicit
// human gate (method=confirmation, D0106): flip status + add the d0236Accept event on sign-off.
package Decision0236 {
    private import EngineElement::*;
    private import EngineWork::*;
    private import EngineVerification::*;
    private import EngineRelationships::*;

    // #ProspectiveChange (D0070) - this Decision governs a process/schema change; the co-committed
    // change rides the process-change guard's hard lock.
    #ProspectiveChange part d0236 : Decision {
        :>> id = "9602e114-b83b-459b-b5c0-1ca439a5c2db";
        :>> title = "intakeWritePath: the human's words get a sanctioned write path, and a console tab flags what waits on them instead of counting lenses";
        :>> createdAt = "2026-08-26";
        :>> createdBy = "claudeFable5";
        :>> status = DecisionStatus::accepted;
        :>> context = "Two reports from the human in one sitting, both about the gap between what the engine CAN do and what its surfaces actually offer. FIRST: they asked whether the claim that there is no write API for Statements or UserStories was accurate. It was. `keel record` covered decision and issue only, so every Statement in this repository - including five from this session - was hand-edited into a file. That is the record type where it matters most, because D0216 makes the VERBATIM Statement the precondition for every Need: a Need with no cited utterance cannot be checked against what the human actually said, which is how one comes to be written wider than the demand (D0157). The record with the strictest rule had the weakest path. SECOND: the console's navigation tab printed the number of VIEWPOINTS on a surface - assurance (11) - and they said plainly that a tab should flag actionable items, because when they open the console they are trying to resolve things. The console already computed what awaits them per viewpoint and rendered a different number.";
        :>> decision = "`keel record statement` and `keel record story` join the write API. A Statement's `text` is escaped ONLY as a one-line literal requires and otherwise passed through untouched - deliberately NOT the existing field sanitiser, which collapses runs of whitespace and would silently alter a quote. An unknown channel or implication is REFUSED rather than defaulted. A story's `#DerivedFrom` edge to the Statement it translates is authored WITH it, and a story citing a Statement that does not exist is refused with nothing written. `--from FILE` carries prose. In the console, a surface tab shows a badge counting items WAITING ON THE HUMAN and nothing at all when none; the viewpoint count moves to the tooltip; each viewpoint card carries the same badge so the surface says which lens holds the work.";
        :>> rationale = "Both halves are the same defect wearing different clothes: a capability existed and the surface a human touches did not expose it. For intake the consequence is sharper than inconvenience - a hand-typed field labelled verbatim is a paraphrase waiting to happen, and the whole point of recording their words first is that my paraphrases demonstrably drift. Splitting the escaping is the load-bearing detail: a title should collapse whitespace and a quote must not, so the two cannot share a function, and a test asserts they behave differently on the same input. For the tab, their framing is the correct specification: a tab is a call to act, not an inventory. Two honesty properties survive the change - a class with no bound counter renders unknown and never zero, and a FAILED obligations fetch renders unknown on every tab rather than showing no badge, because an absent badge means nothing is waiting and that would be a false all-clear on the one surface whose purpose is telling the human what they owe.";
        :>> consequences = "Every future Statement carries actor validation, the write lock, a refused default date, and a verbatim guarantee the path enforces rather than the author remembering. The existing hand-written Statements are NOT migrated: they are true records made by a weaker path, and rewriting them would be editing recorded human words to satisfy a convention introduced afterwards. Five of six tabs now show no badge, which is correct and worth stating - obligation classes are derived only from viewpoints declaring surface=act, so a human obligation declared on another surface would not be badged; that is the declaration mechanism and not an oversight. Verified live rather than asserted: the human's own message recorded and read back BYTE-IDENTICAL including its double spaces, the same input through the title sanitiser collapsing to prove the escapings differ, a story citing st999 refused leaving no trace, the edge present in the file, and the tabs reading act 140 with the other five blank while the three non-empty act classes badge 50, 50 and 40. Resolves issue288 and issue289.";
    }

    // acceptance event (D0121 review-queue sign-off; D0066/D0106 — human-judged, not fabricated)
    verification d0236Accept : Test { :>> id = "68832a84-0a80-40c6-91e9-93e97908fc0f"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0236AcceptR1 : TestResult { :>> id = "30088c58-82b1-45a5-9add-16ccba9573b6"; :>> outcome = VerdictKind::pass; :>> judgedAgainst = "bcf2d74"; :>> judgedAt = "2026-08-27"; :>> judgedBy = "wweatherholtz"; }
}
