// D0158 — ACCEPTED (wweatherholtz, 2026-08-17): supersedes D0115's "single-user" phrasing. The engine
// has ONE BOUND ACTOR PER MACHINE and collaborates by git; the CONSOLE is local-only and
// unauthenticated. Those are two scopes and D0115 named them as one.
// #ProspectiveChange (D0070): restates a scope boundary; derives no new work and removes none.
package Decision0158 {
    private import EngineElement::*;
    private import EngineWork::*;
    private import EngineVerification::*;
    private import EngineRelationships::*;

    #ProspectiveChange part d0158 : Decision {
        :>> id = "8f52d7a0-3c14-4e89-b26d-5901af7e3cb4";
        :>> title = "D0158: one bound actor per machine, collaboration by git, console local-only — superseding D0115's 'single-user'";
        :>> createdAt = "2026-08-17";
        :>> createdBy = "claudeOpus5";
        :>> status = DecisionStatus::accepted;
        :>> context = "issue137. D0115 clause 1 reads 'the viewer is single-user + unauthenticated', and that phrase is now false of the engine and imprecise about the console. WHAT SHIPPED SINCE: D0108 and D0129 gave keel one BOUND ACTOR PER MACHINE (`keel actor set`, or KEEL_ACTOR per session, or an explicit --judged-by, and the write REFUSES otherwise), per-actor claim files so two contributors' claims do not contend for the same line, merge-only integration that gates the MERGED tree because two contributions passing alone can fail together, and contention recorded as an Issue for human adjudication. Several humans on several machines therefore already collaborate — through git, not through a session. The human named the distinction on 2026-08-17: 'it's not single user altogether, it's a single user per machine - this service app is local only at the moment.' ISSUE132 SITS DIRECTLY DOWNSTREAM of the conflation: N-8's statement was judged against 'single-user' when the accurate boundary was 'no accounts, no server-side session', and four proposed resolutions were all framed around the wrong one of the two scopes.";
        :>> decision = "ACCEPTED, superseding D0115's clause-1 PHRASING and nothing else in it: the boundary is (a) IDENTITY — one bound actor per machine, never inferred and never defaulted; an AI is an Actor with kind=ai, never a Person; (b) COLLABORATION — by git, with merge-only integration, ownership by createdBy, and contention adjudicated by a human; multiple contributors are IN scope and already implemented; (c) THE CONSOLE — local-only, unauthenticated, no server-side per-user state, and out of scope for accounts. Every scope claim must now name WHICH of these three it constrains. D0115's substantive scope decisions stand untouched: N-7, N-9, N-11 and N-14 remain superseded, and nothing here revives auth or multi-user access to a running service, which D0157 holds as a deferred direction with the human as its trigger.";
        :>> rationale = "WHY SUPERSEDE THE PHRASE RATHER THAN EDIT D0115: its text carries an accepted attestation (d0115Accept, 2026-07-14) and rewriting attested words leaves the attestation naming words the human never saw — the same reason N-8 was superseded instead of narrowed (D0156). WHY THE THREE-WAY SPLIT IS THE FIX AND NOT JUST BETTER WORDING: 'single-user' is one phrase doing three jobs, and a reader can only be wrong about it. It reads as 'one human total' (false — D0108 exists for the plural case), or 'no authentication' (true, but only of the console), or 'no concurrent editing' (false — claim files exist precisely so concurrent editing works). Splitting identity from collaboration from deployment means a future scope claim has to say which one it means, which is what would have prevented issue132. WHAT I DID NOT DO: I did not touch N-7's superseded statement, the sprint records that name the old phrase, or the historical comment describing what D0115 did — those are history and correct as history. The single LIVE claim asserting the old phrase, a comment in requirements/keel-viewer.sysml authored by me, is corrected in the same commit as this Decision, because doc-sync rides every change.";
        :>> consequences = "issue137 resolves. No requirement changes, no Need changes, no work is added or removed — this makes an existing boundary sayable rather than moving it. THE COST: one more Decision to read before the viewer's scope is fully known, and D0115 must be read with D0158 beside it. A future reader who finds only D0115 will still be misled, which is why the supersession is a typed edge the computed views follow rather than a note. NOT SETTLED HERE: whether the console should ever be reachable beyond localhost — that is D0157, deferred with the human as its trigger.";
    }

    #SupersedeClause dependency from d0158 to d0115;
    #Resolves dependency from d0158 to issue137;

    // acceptance event (D0121 review-queue sign-off; D0066/D0106 — human-judged, not fabricated)
    verification d0158Accept : Test { :>> id = "4c07e9b1-6d83-4520-a7f4-e18b25c60d97"; :>> method = VerificationMethod::confirmation; :>> procedureText = "wweatherholtz, 2026-08-17. THE CORRECTED BOUNDARY IS THEIR OWN STATEMENT, verbatim: 'we want to support users on different computers running keel, the real need is to be able to transfer processes to them easily. so it's not single user altogether, it's a single user per machine - this service app is local only at the moment.' That sentence is the whole of what this Decision records; my contribution is splitting it into the three scopes it distinguishes and naming which shipped artifacts implement each. Their instruction in the same exchange — 'Otherwise, keep pursuing... Keep going until you are done or reach a legitimate blocker (not just approval)' — authorizes acting on it without a further round trip. This attests the SCOPE STATEMENT they made, not a review of this Decision's prose."; }
    part d0158AcceptR1 : TestResult { :>> id = "e6b4139c-08a7-4d61-95f2-3ca70be2f851"; :>> outcome = VerdictKind::pass; :>> judgedAgainst = "32a0a31"; :>> judgedAt = "2026-08-17"; :>> judgedBy = "wweatherholtz"; }
}
