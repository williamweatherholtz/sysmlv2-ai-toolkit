// D0435 (status: the `status` field below is the truth) — ceremonyStepBindsToItsWorkflowGate: a ProcessStep's checkedBy may name a workflow phase as gate:<phase>, its check is that run's <Phase>Gate result, and the ceremony order the engine enforces is read from the workflow's declared successions instead of a compiled table
// Recorded via `keel record decision` (D0105 RMWX axis; issue054). Acceptance is a separate explicit
// human gate (method=confirmation, D0106): flip status + add the d0435Accept event on sign-off.
package Decision0435 {
    private import EngineElement::*;
    private import EngineWork::*;
    private import EngineVerification::*;
    private import EngineRelationships::*;

    // #ProspectiveChange (D0070) - this Decision governs a process/schema change; the co-committed
    // change rides the process-change guard's hard lock.
    #ProspectiveChange part d0435 : Decision {
        :>> id = "781b200e-1a13-4839-9282-18dd7a394536";
        :>> title = "ceremonyStepBindsToItsWorkflowGate: a ProcessStep's checkedBy may name a workflow phase as gate:<phase>, its check is that run's <Phase>Gate result, and the ceremony order the engine enforces is read from the workflow's declared successions instead of a compiled table";
        :>> createdAt = "2026-09-10";
        :>> createdBy = "claudeOpus5";
        :>> status = DecisionStatus::accepted;
        :>> context = "D0434 gave a ProcessStep the attribute checkedBy, resolving to a guard or a declared rule: tree-wide predicates that run at any moment. The agile-workflow's ceremony steps are checked by something with a different shape - a PER-RUN result, the sprint's `<...>RefineGate : Test` and its passing TestResult - so on 2026-09-10 they are the steps `keel advance` already refuses on, and the only enforced steps in the engine that cannot say so: stepEnforcement reports every agile-workflow step as undeclared. The order advance, orient and the `ceremony` guard enforce is a compiled constant `GATE_ORDER` in orient.rs and a second copy in guards.rs, a third in `audit` (algo.rs CEREMONY_GATES), held to the chain `first refine then standup; ... first closeOut then retro;` declared in .engine/workflows/delivery.sysml only by an include_str test - four homes for one sequence (D0105). D0321 option A's second half, dcAdvanceRefusesAnyBoundStep, is the item; this Decision is the vocabulary clause it needs, and depends on D0434.";
        :>> decision = "NOT A FORK: D0321 option A chose the attribute on the step and this extends what it may hold to the one check shape the ceremony has. A checkedBy of the form `gate:<phase>` names an `action <phase>` declared in a succession chain (`first A then B;`) of a workflow under .engine/workflows/, and means: in a run of this process (a sprint's delivery file), the step is done when the run's `<...><Phase>Gate : Test` has a passing TestResult, where `<Phase>` is the phase name with its first letter upper-cased (`closeOut` -> `CloseOutGate`). Guard step-check-resolves resolves `gate:<phase>` against the phases those chains declare and FAILS one no chain names, for the same EHZ5 reason a ghost guard name fails. The ceremony order the engine enforces - `keel advance`, `orient`'s in-progress sprints, the `ceremony` guard and `new sprint`'s scaffold - is the declared succession chain of the WORKFLOW whose phases some step binds, read from the tree at run time and linearised in declaration order (all of that workflow's phases, so a chain is never partially enforced); the compiled constants in orient.rs, guards.rs and algo.rs and the test that held them to the file are deleted: one home. The agile-workflow's steps carry their bindings: refineLink gate:refine, standupGate gate:standup, implDo gate:implement, implReview gate:review, implClose gate:closeOut, retroIdentify gate:retro - the step whose completion each gate records.";
        :>> rationale = "The ceremony steps ARE enforced today, per run, in-loop; the lens that reports enforcement per step says otherwise because the vocabulary D0434 chose could only name tree-wide predicates. Naming the gate makes the lens true, and it makes the order data: once every ceremony step says which gate records it, the chain that orders those gates is the fact advance reads, and a compiled table beside it is the third copy that a future CR edits or forgets. The `gate:` prefix keeps the two check shapes distinct where they are read - a guard binding is evaluated on the tree now, a gate binding needs a run to evaluate against - so `keel advance <process>` can say which of a process's steps it can judge without a run. Resolving against the workflow chains rather than accepting any identifier is what keeps the binding a fact a control reads: `gate:closeout` (lower-case, no phase of that spelling) fails, as `marker-census` did in D0434's first live run.";
        :>> consequences = "Process-change (D0337): proposed until the human's word. orient.rs gains `gate_order(root)` reading .engine/workflows/*.sysml chains and the three constants go; cursor.rs, guards.rs (`ceremony`), algo.rs (`audit`), scaffold.rs and orient's in-progress computation read it; the include_str binding test is deleted with the fact it bound. Six agile-workflow steps carry `:>> checkedBy = 'gate:<phase>';` through the D0067 transform of D0434 extended for a second run, so stepEnforcement reports 13 of 185 checked and the agile-workflow leaves undeclared. step-check-resolves gains the `gate:` class with a positive and a negative fixture. STATED: a project whose process steps bind no gate has no ceremony order - advance, orient and the ceremony guard then report the sprint as unenforceable-by-step rather than enforcing a default nobody declared; the engine ships delivery.sysml with its chain, so on this tree behaviour is unchanged and the existing cursor and ceremony tests hold.";
    }
    #DependsOn dependency from d0435 to d0434;

    // acceptance event (D0121 review-queue sign-off; D0066/D0106 — human-judged, not fabricated)
    verification d0435Accept : Test { :>> id = "ef7ee7e2-4c1d-44ca-80bb-26ba8e07bec6"; :>> method = VerificationMethod::confirmation; :>> procedureText = "Selected on the decision brief copy-out (fifteenth publish), pasted into chat 2026-09-11: the set of 33 HELD process-change ratifications accepted with one word, this record being one member (D0406 named it in the table). No note added. - their words, verbatim: “Accept the set: each of the 33 rules named in the table is recorded accepted on its own, quoting these words (recommended)” WARN: read-back - the quoted words do not name d0435 (D0201 B); recorded as given (D0423)."; }
    part d0435AcceptR1 : TestResult { :>> id = "cade0a5e-b211-42e6-a927-364589aa4c9c"; :>> outcome = VerdictKind::pass; :>> judgedAgainst = "3e6c518"; :>> judgedAt = "2026-09-11"; :>> judgedBy = "wweatherholtz"; :>> createdBy = "claudeOpus5"; }
}
