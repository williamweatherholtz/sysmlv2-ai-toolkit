// D0364 (status: the `status` field below is the truth) — aTwoHopArmForTheRecallBench: the benchmark gains a set whose queries are drawn two edges from the target, because a set of one-hop cases cannot choose a two-hop mechanism
// Recorded via `keel record decision` (D0105 RMWX axis; issue054). Acceptance is a separate explicit
// human gate (method=confirmation, D0106): flip status + add the d0364Accept event on sign-off.
package Decision0364 {
    private import EngineElement::*;
    private import EngineWork::*;
    private import EngineVerification::*;
    private import EngineRelationships::*;

    part d0364 : Decision {
        :>> id = "e23a4f90-06a6-45ca-a3b0-87a6853ca98f";
        :>> title = "aTwoHopArmForTheRecallBench: the benchmark gains a set whose queries are drawn two edges from the target, because a set of one-hop cases cannot choose a two-hop mechanism";
        :>> createdAt = "2026-09-07";
        :>> createdBy = "claudeOpus5";
        :>> status = DecisionStatus::accepted;
        :>> context = "recallRanksLinkedRecordsAsWellAsGrepDoes requires its mechanism to be CHOSEN on recall_bench.py's 50-case set and only then read against the eight hand-written questions, never fitted to them. That rule is right and is not in question. What was found while trying to satisfy it is that the arbiter set cannot answer the question the criterion asks it. Every case in that set draws its query from a record ONE edge from the target (recall_bench.py builds `src` as `sorted(m for m in adj[name] if m in with_body)[0]`), so a mechanism that reaches further is structurally invisible to it. Measured: the dominant-source second hop moved neither hits (49/50) nor median position (3) at DOMINANCE 1.5, 2.0, at DOM_HOP2 0.4, 0.7 and 1.0, and at DOM_HOP1 0.6 - six configurations, all identical to the arm with the mechanism switched off. The same neutrality is what D0325 met with the rare-term narrowing and read as grounds for rejection; read correctly, it is the set declining to answer. A criterion that says 'choose it on this set' while the set contains no case the mechanism applies to leaves only two moves, and both are wrong: choose by the eight questions, which is the fitting the criterion forbids, or reject every mechanism the set cannot see.";
        :>> decision = "recall_bench.py takes `--hops 2`: the query's words are drawn from a record exactly two edges from the target, through an intermediate whose words are removed along with the target's and the source's, so the query can never name the stepping stone the traversal has to cross. Sampling uses the same seed and the same mechanical rule as the default arm - candidates are every bodied element with at least one bodied two-hop record, shuffled by Random(20260828) and truncated - so no case is picked by hand and the set is reproducible. Both controls, the rarest-word grep and grep-plus-one-hop, run unchanged against it. A mechanism that reaches past one hop is now chosen on this arm, subject to no regression on the default arm; the eight hand-written questions of recall_ab.py are still read only afterwards and are still never fitted to.";
        :>> rationale = "The measurement was denied the one field the question came from, which is defect 1 of issue296 recurring one level up: there, the control searched name and title while the queries were drawn from bodies; here, the arbiter contains only one-hop cases while the criterion asks about two hops. The remedy is the same remedy - give the measurement the shape it is being asked to judge - and it is a generated set rather than a hand-picked one for the same reason the neighbour set is generated: a case chosen because it exhibits the problem is an argument, not evidence. The intermediate's words are excluded because leaving them in would hand the second hop its own stepping stone, and the case would then measure a one-hop retrieval wearing a two-hop label. Keeping the default arm as a no-regression gate rather than replacing it matters: a two-hop mechanism that buys far cases with near ones is worse than no mechanism, and only running both arms makes that trade visible.";
        :>> consequences = "The two-hop arm reads 15/50 with the second hop off, against grep-plus-one-hop's 8/50 - so the corpus's two-hop questions were being answered less than a third of the time and nothing said so. Any future recall mechanism is now measured on both arms and its record carries both numbers. The arm costs about 40 seconds a run and is not wired into any gate, because it is an instrument for choosing a mechanism, not a threshold anything must clear. NOT A FORK: this Decision chooses one course; the configurations it names are measurements, not options put to a reader.";
    }

    // acceptance event (D0121 review-queue sign-off; D0066/D0106 — human-judged, not fabricated)
    verification d0364Accept : Test { :>> id = "dfe1f4f5-7e79-45e9-b925-f026a4b68524"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0364AcceptR1 : TestResult { :>> id = "9172cda6-a4bd-401b-b4bb-716cee455308"; :>> outcome = VerdictKind::pass; :>> judgedAgainst = "018315a"; :>> judgedAt = "2026-09-07"; :>> judgedBy = "wweatherholtz"; :>> createdBy = "claudeOpus5"; }
}
