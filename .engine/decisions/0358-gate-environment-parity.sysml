// D0358 (status: the `status` field below is the truth) — gateEnvironmentParity: two workflows that run the same gate must supply the same environment
// Recorded via `keel record decision` (D0105 RMWX axis; issue054). Acceptance is a separate explicit
// human gate (method=confirmation, D0106): flip status + add the d0358Accept event on sign-off.
package Decision0358 {
    private import EngineElement::*;
    private import EngineWork::*;
    private import EngineVerification::*;
    private import EngineRelationships::*;

    // #SafetyChange (D0070) - this Decision governs a process/schema change; the co-committed
    // change rides the process-change guard's hard lock.
    #SafetyChange part d0358 : Decision {
        :>> id = "8dd27ec4-1060-413a-8995-d3d8ddd84f5f";
        :>> title = "gateEnvironmentParity: two workflows that run the same gate must supply the same environment";
        :>> createdAt = "2026-09-06";
        :>> createdBy = "claudeOpus5";
        :>> status = DecisionStatus::accepted;
        :>> context = "The tag v0.4.0 was pushed at 2c288d8 with a locally green suite, 562 passed 0 failed. Its release gate ran cargo test --workspace --release with no env block. The federation suite's live-upstream claim shells out to gh api, and gh refuses inside GitHub Actions without GH_TOKEN, printing the instruction to set it. The gate concluded failure at 10 passed 1 failed, needs: gate skipped the whole build matrix, and no release object was ever created - gh release view v0.4.0 returns 'release not found'. The same test passes on every push, because ci.yml supplies github.token with a comment recording that the alternative, declaring the path offline, is strictly weaker. Guard 51 exists because the release gate had already been red for a whole release cycle undetected (issue260); it checks that a gating workflow checks out full history, not that two gating workflows running the same command agree on the environment they run it in. A precondition supplied in the surface that runs constantly and omitted in the surface that runs quarterly is green wherever anyone is looking and red only where nobody is. It also mattered beyond one tag: this project's own engine pin was already committed as 0.4.0 and keelw resolves that pin to a release asset, so a pin naming a version whose release does not exist means a fresh clone cannot obtain the binary its own gates require.";
        :>> decision = "A workflow that runs the test suite supplies every environment variable its sibling gating workflows supply, and guard 64 gate-environment-parity enforces it forward. NOT A FORK: the only other shapes are to leave the release gate without the token, which is the defect itself, or to declare the live-upstream path offline in the release workflow, which ci.yml's own comment already records as strictly weaker - it would leave the only assertion touching real GitHub unexercised in the very surface that publishes.";
        :>> rationale = "Adding the token is a patch; the recurrable gap is that these two files drift, and manual vigilance over a workflow that runs quarterly is not a control. The guard derives its expectation from the tree rather than from knowledge written down once: a variable that any gating workflow supplies is one the gate is known to need, so a sibling that omits it is running the same suite in a different world, while a project whose gate needs nothing declares nothing and is never accused. That derivation is why it cannot go stale as the workflows change, and why it is safe to ship to adopters whose suites never touch the network. It is a SAFETY-CHANGE because it edits the enforcement surface - guard source and a gating workflow - so it waits for the human's word rather than standing consent.";
        :>> consequences = "A release can no longer fail on a precondition the everyday gate quietly supplies, and the failure mode that hid for a whole release cycle in issue260 now fails at the commit that introduces it rather than at the tag that needed it. v0.4.0 is NOT re-cut: the tag stays where it is and the next release is v0.4.1, because a tag that moves makes every judgement recorded against it unreadable (D0129/D0357) and the Release record already names the tagged commit. The cost is one version number; what it buys is that the failed attempt stays visible as history rather than being erased, and the Release record for v0.4.0 states plainly that it published nothing and why. RESIDUAL: the check is file-level, because there is no YAML parser in the binary, so a variable set on a non-gating job in the same file counts as present - the same stated limitation gating-workflow-history carries. It catches the real class, a gating workflow with the variable nowhere in it, and nothing finer.";
    }

    // acceptance event (D0121 review-queue sign-off; D0066/D0106 — human-judged, not fabricated)
    verification d0358Accept : Test { :>> id = "e2c20a96-bd4f-4ebd-bd4c-5edbdcfdc2f2"; :>> method = VerificationMethod::confirmation; :>> procedureText = "recorded from the decision brief copy-for-AI digest, their words verbatim: '- [x] Accept the rule ... (answers: d0358)'"; }
    part d0358AcceptR1 : TestResult { :>> id = "adb4dae4-a31e-491f-9b0f-caa6e8627290"; :>> outcome = VerdictKind::pass; :>> judgedAgainst = "50b2cdb"; :>> judgedAt = "2026-09-07"; :>> judgedBy = "wweatherholtz"; :>> createdBy = "claudeOpus5"; }
}
