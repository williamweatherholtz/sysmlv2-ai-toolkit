// D0431 (status: the `status` field below is the truth) — guardPoolStaysInDeclarationOrderOnMeasurement: longest-first dispatch was built and A/B-timed, bought nothing measurable, and is not adopted; the guard receipt keeps every guard's ms so the next such claim is judged against history
// Recorded via `keel record decision` (D0105 RMWX axis; issue054). Acceptance is a separate explicit
// human gate (method=confirmation, D0106): flip status + add the d0431Accept event on sign-off.
package Decision0431 {
    private import EngineElement::*;
    private import EngineWork::*;
    private import EngineVerification::*;
    private import EngineRelationships::*;

    // #ProspectiveChange (D0070) - this Decision governs a process/schema change; the co-committed
    // change rides the process-change guard's hard lock.
    #ProspectiveChange part d0431 : Decision {
        :>> id = "2d9c4d27-a4ec-4b09-a997-7b67cf9c9773";
        :>> title = "guardPoolStaysInDeclarationOrderOnMeasurement: longest-first dispatch was built and A/B-timed, bought nothing measurable, and is not adopted; the guard receipt keeps every guard's ms so the next such claim is judged against history";
        :>> createdAt = "2026-09-10";
        :>> createdBy = "claudeOpus5";
        :>> status = DecisionStatus::accepted;
        :>> context = "issue455 (dcGuardPoolDispatchesLongestFirst) observed that the guard pool in guards.rs run_in_parallel is greedy list scheduling in GUARD_NAMES order, so a long guard declared late starts late and bounds the wall clock. The item's DoD said PROBE FIRST. scripts/probes/guard_dispatch_order.py simulated list scheduling over three measured runs and said declaration order 1849 ms against a longest-first 1314 ms - ORDER MATTERS. Longest-first was then built from the receipt's per-guard durations and timed. Two timings in separate windows read 2147-2252 ms before and 2600-2991 ms after - which, re-run on identical code later the same day, turned out to be host drift of thirty percent with no code change at all (Defender and thirteen stale kernel JVMs were the load). Six interleaved pairs on one host state, the same binary with the order switched by an env var, then measured wall medians 2567 ms for declaration order against 2544 ms for longest-first - 22 ms, inside a run-to-run spread of 300 ms - while the guard sum rose 21.3 to 23.3 s, git x40 rose 5.2 to 7.3 s, and the longest guard, acceptance-binds-to-text, stretched from 1.55-1.68 s to 2.16-2.34 s. The simulation assumed each guard's duration is independent of what runs beside it; the heavy guards spawn git and walk the tree, and dispatched together they contend, so the lower bound grows by what the schedule saves.";
        :>> decision = "NOT A FORK: the measurement decides it. The guard pool keeps dispatching in GUARD_NAMES declaration order; the longest-first scheduler is not adopted and its code is removed. What stays is the measurement's instrument: each guard's wall clock is recorded on every run (guards::last_durations) and written into the guard receipt as ms per guard beside critical_path (receipt.rs StoredGuard), so the set's per-guard profile is history on disk rather than a number re-derived when someone next asks. The probe script keeps its simulation but states in its verdict that the assumption of independent durations was falsified on this set, and gains --ab, which summarises two interleaved sets of timed runs and reports NO MEASURED DIFFERENCE when the medians sit inside the spread. The wall-clock floor of the parallel set is named as shared-resource contention among the git-spawning and tree-walking guards, and that bound is already the object of dcGitReadsStayInProcess and dcBatchGitReads; this Decision adds no third item for it.";
        :>> rationale = "A scheduling change that a simulation promises and a measurement cannot show is complexity with no return, and the pool is on the enforcement surface (D0209 clause 2), where every line is a line a future reader has to trust. The instrument is worth keeping because it is the only part that produced knowledge: without per-guard ms in the receipt the next reader would re-simulate from the same independent-duration model and arrive at the same wrong ORDER MATTERS, which is exactly how this sprint started. The interleaved A/B is recorded because the two-window comparison was not merely imprecise but wrong in sign - it read longest-first as thirty percent slower, and that number had already been written into a code comment before the like-for-like run replaced it. A claim about this pool's order is therefore judged by interleaved pairs, and the probe script carries the command that does it.";
        :>> consequences = "guards.rs run_all dispatches to_run as declared, with a comment naming the A/B numbers and the mechanism; dispatch_order and receipt::durations are gone; a unit test asserts every guard that ran is timed. .keel/metrics/guard-receipt.toml carries ms per guard, zero for a guard the run did not time; a receipt written before this change parses with ms defaulting to zero. CLAUDE.md section 5 states the order and why. issue455 resolves through dcGuardPoolDispatchesLongestFirst on this evidence: the floor is MEASURED and NAMED, not lowered. The two hosts of the bound stay dcGitReadsStayInProcess and dcBatchGitReads. issue458 - the thirty-percent penalty read from two windows and written down before the A/A case ran - resolves here: the probe's --ab refuses two sets whose files do not interleave in time, and this Decision states that a claim about the pool's order is judged by interleaved pairs. This Decision touches guards.rs and so carries the process-change marker; it waits for the human.";
    }

    // acceptance event (D0121 review-queue sign-off; D0066/D0106 — human-judged, not fabricated)
    verification d0431Accept : Test { :>> id = "c9753daa-8f24-4fd1-a106-5e2b6eae5357"; :>> method = VerificationMethod::confirmation; :>> procedureText = "Selected on the decision brief copy-out (fifteenth publish), pasted into chat 2026-09-11: the set of 33 HELD process-change ratifications accepted with one word, this record being one member (D0406 named it in the table). No note added. - their words, verbatim: “Accept the set: each of the 33 rules named in the table is recorded accepted on its own, quoting these words (recommended)” WARN: read-back - the quoted words do not name d0431 (D0201 B); recorded as given (D0423)."; }
    part d0431AcceptR1 : TestResult { :>> id = "3a13df87-6eee-4852-a6a7-51222e5f14a3"; :>> outcome = VerdictKind::pass; :>> judgedAgainst = "3e6c518"; :>> judgedAt = "2026-09-11"; :>> judgedBy = "wweatherholtz"; :>> createdBy = "claudeOpus5"; }
}
