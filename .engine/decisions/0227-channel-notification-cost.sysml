// D0227 (status: the `status` field below is the truth) — notificationCost: how should the channel stop spending your attention on decisions that need nobody?
// Recorded via `keel record decision` (D0105 RMWX axis; issue054). Acceptance is a separate explicit
// human gate (method=confirmation, D0106): flip status + add the d0227Accept event on sign-off.
package Decision0227 {
    private import EngineElement::*;
    private import EngineWork::*;
    private import EngineVerification::*;
    private import EngineRelationships::*;

    // RESEARCH: Measured this repo rather than reasoning about it. 22 GitHub issues exist and 20 were opened in a single day, one per proposed Decision, each ASSIGNED to the decider by the opener. 94 workflow runs landed the same day; 148 CI runs across the sampled window, 28 of them failing, and GitHub emails the pusher on each failure. The decision-record sweeper fires on a 30-minute cron (29 runs sampled). Read the opener and the channel's own docs: the skill states 'One issue per decision - the human's own requirement, to keep the gesture unambiguous', which is why this is a fork rather than a fix - the change reverses something you asked for. Also checked what the decider table actually controls: it governs who may DECIDE and who gets ASSIGNED, not who gets notified; anyone watching the repo receives new-issue notifications regardless, which is why 'leave me as the only decider' does not by itself protect a colleague on another repository. No external research: this is a property of this repo's own configuration.
    // #ProspectiveChange (D0070) - this Decision governs a process/schema change; the co-committed
    // change rides the process-change guard's hard lock. Added when the human chose OPTION A and
    // the change became real; the fork was recorded before it was known that anything would change.
    #ProspectiveChange part d0227 : Decision {
        :>> id = "4602f247-337a-450d-83c1-d930fc0c1066";
        :>> title = "notificationCost: how should the channel stop spending your attention on decisions that need nobody?";
        :>> createdAt = "2026-08-24";
        :>> createdBy = "claudeFable5";
        :>> status = DecisionStatus::accepted;
        :>> context = "You said you did not want a second decider on penumbra barraged with GitHub notifications the way you are getting now. Measured: 20 issues in one day, one per auto-accepted Decision, each assigned to you, for decisions that BY DEFINITION need nobody - that is what standing consent means. The decider table does not fix this for a colleague either: it controls who may decide and who is assigned, not who is notified, so anyone watching the repository gets every issue. This is the D0054 adoption-friction class landing on the author of the control, and it is the first friction report about one of these. It also blocks a clean penumbra adoption, because adopting the channel there would replicate it. THE REASON THIS IS A FORK AND NOT A FIX: the channel's own skill records 'One issue per decision - the human's own requirement, to keep the gesture unambiguous'. That was you. The barrage complaint is also you. I am not going to quietly reverse one of your stated requirements with the other, so you choose. OPTION A (one standing thread for auto-accepted decisions) - every non-fork becomes a COMMENT on a single forever-open thread that assigns nobody; a fork still opens its own issue and still assigns you, so it notifies through a mute of the standing thread. Per-decision issues drop to zero. OPTION B (keep one issue per decision, assign nobody for non-forks) - your prior requirement survives intact and the gesture stays unambiguous; only the assignment and its mobile push go away. OPTION C (make it a declared per-project policy) - keel keeps today's behaviour, penumbra declares the quieter one, and each adopting project chooses in its own contracts file.";
        :>> decision = "FORK - awaiting your letter. A: one standing thread. B: keep one issue per decision but assign nobody. C: declare it per project. Implemented in advance either way, because it is useful under all three: a gesture may now NAME the decision it reverses (reject d0225 too wide), which is what lets one thread carry several decisions unambiguously, and is harmless where each decision has its own issue. The behavioural half is NOT implemented and will follow your choice.";
        :>> rationale = "The measurement is what makes this answerable rather than a matter of taste: 20 issues a day is not a tuning question, and it grows with every Decision this engine records, which means it gets worse exactly as the engine gets used more. What must not change is the override surface itself - it is your only route to reverse a Decision that was auto-accepted under standing consent, so any option that weakens it is off the table, and all three preserve it. What differs is how much of your attention the surface costs to exist. The reason I will not just pick A, which is the option I would choose, is that it reverses a requirement you stated and the skill recorded, and this session has twice shown that declining to act on a premise - rather than accepting it - is what surfaced the real problem. COST OF A: the gesture must name its decision, so a bare 'reject' on the standing thread no longer resolves, and three months of one-issue-per-decision habit stops matching what the thread looks like. COST OF B: the issue count and the emails from watching the repository are unchanged, so if watching is what is barraging you rather than assignment, B fixes almost nothing. COST OF C: a third activation-style knob and two behaviours to keep tested, on a channel that is already the most mechanism-heavy unit here.";
        :>> consequences = "Whichever you pick, the override thread survives and no accepted Decision loses its reversal route - that is the invariant. Until you answer, the channel behaves exactly as it does today, so the cost continues to accrue; that is the price of asking rather than acting, and it is the right price here. The capability half has landed and is inert under today's behaviour. It also means the penumbra adoption waits on this, because adopting the channel there before choosing would inflict the barrage on the colleague you specifically said to protect.";
    }

    // acceptance event (D0121 review-queue sign-off; D0066/D0106 — human-judged, not fabricated)
    verification d0227Accept : Test { :>> id = "22d37be0-41a6-4686-9fa0-3fd9f591e0ba"; :>> method = VerificationMethod::confirmation; :>> procedureText = "OPTION A - their words, verbatim: 'A' (GitHub comment https://github.com/williamweatherholtz/sysmlv2-ai-toolkit/issues/25#issuecomment-5404939096, id 5404939096, authenticated login williamweatherholtz)"; }
    part d0227AcceptR1 : TestResult { :>> id = "b0ae6b5d-bdf2-4ab9-a7c2-d7a8b2f4e017"; :>> outcome = VerdictKind::pass; :>> judgedAgainst = "5242997"; :>> judgedAt = "2026-08-25"; :>> judgedBy = "wweatherholtz"; }
}
