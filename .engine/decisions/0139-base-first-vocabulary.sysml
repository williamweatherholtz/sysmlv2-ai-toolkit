// D0139 — BASE-FIRST vocabulary: a custom edge is a last resort requiring recorded justification, and
// the relationships base SysML v2 already provides are used in preference to markers that shadow them.
// PROPOSED: touches the frozen edge algebra (§2.2) and implies a 613-occurrence migration.
package Decision0139 {
    private import EngineElement::*;
    private import EngineWork::*;
    private import EngineVerification::*;
    private import EngineRelationships::*;

    #ProspectiveChange part d0139 : Decision {
        :>> id = "1b6d92f4-3e57-4c08-a7b1-8f2049c63e5d";
        :>> title = "D0139: base SysML v2 relationships come first; a custom marker requires recorded justification and an automated control";
        :>> createdAt = "2026-08-14";
        :>> createdBy = "claudeOpus5";
        :>> status = DecisionStatus::accepted;
        :>> context = "Raised by the human 2026-08-14: 'should process -> controls live with typed edges? I'd like a more semantic description of processes generally. Minimum custom connections, maximum using real relationships defined in base sysmlv2. anytime we use something custom, it should be strongly critiqued.' The prompting instance was mine: sprint 265 put the process-to-controls mapping in a TOML contract when `assert constraint` was available and semantically exact. MEASURED (issue095, each construct written to a probe and run through `keel check` on 2026-08-14): `verify X by Y`, `refine X by Y`, `assert constraint`, `require constraint`, `perform action` and `include use case` ALL parse clean in the rust authority, and ALL are used zero times — while the custom `#Verify` marker has 613 uses and `#DerivedFrom` has 91. Meanwhile `satisfy` (263) and `allocate` (69) are used properly. So the model expresses satisfaction with the real relationship and verification with a custom marker, and no record shows base `verify` was ever tried. The justification on file was narrower than its use: the notes said only that `dependency def` does not exist, which is true for genuinely NEW edge kinds and silent about base relationships. A contributing doc defect compounded it — the multi-valued `:>> x = (a, b, c)` form was recorded as confirmed when it had only been confirmed against the KERNEL, months before the rust parser existed, and the rust authority rejects it. A keel-parser gap was therefore recorded as a SysML v2 limitation, which removed `ref` features from consideration and made markers look like the only option.";
        :>> decision = "(A) BASE-FIRST RULE: authoring reaches for a base SysML v2 relationship before inventing anything. A custom `metadata def` edge is permitted only as a last resort and only with a recorded justification naming the base constructs considered and why each fails. (B) An AUTOMATED CONTROL enforces it, not a reminder (D0047): every PROJECT-declared marker must carry that justification as a `doc` clause. The engine's own 17 markers are GRANDFATHERED to warnings (forward-only, issue068) and that list must not be extended. (C) The five CLASSIFIER markers — #ProspectiveChange, #SafetyChange, #Capability, #ProcessDefect, #View — are RETAINED as legitimate: they stereotype elements, which is exactly what `metadata def` is for, and no base relationship expresses 'this element is of this kind'. The distinction the rule draws is between classifying an element and connecting two, and only the second has base alternatives. (D) Process-to-controls moves to `assert constraint` (dcProcessAssertsConstraints), retiring process-units.toml. (E) `#Verify` migrates to base `verify` and `#DerivedFrom` to base derivation, each under D0067's gated expand/migrate/contract with a committed transform and reconciled control totals — never ad hoc, never with fabricated history. (F) sysmlv2-syntax-notes.md lists the verified base relationships FIRST, so the next author meets them before the marker workaround. (G) For `#DerivedFrom` the target is decided by measurement before any file changes: the notes call `:>` the idiomatic replacement for deriveReqt/refine/trace, while `refine` also parses — that disagreement is resolved and recorded, not guessed.";
        :>> rationale = "Three reasons this is worth a migration rather than a note. FIRST, semantics: a base relationship is parsed AS a relationship, so a misspelling is a parse error. A marker is metadata — `#Verifyy` validates clean and silently removes that item from the consuming guard's view, which is precisely the D0133 argument for the marker-vocabulary guard. Using base relationships makes that guard's job smaller instead of guarding against a hazard we introduced. SECOND, traceability: a TOML table cannot be reached by `keel trace`, a declared view, or any viewpoint, so putting the process-to-controls mapping there made an engine fact invisible to the engine's own lenses — the model should be able to answer 'which controls does this process bring?' the same way it answers every other structural question. THIRD, portability: keel's value proposition is that its truth is standard SysML v2 text. Every custom marker is a dialect another tool cannot read, so the custom surface is the size of the lock-in, and 613 uses of a shadowing marker is a large one. WHY THE CLASSIFIERS SURVIVE THE SAME SCRUTINY: `metadata def` exists in base SysML v2 for stereotyping, so using it to classify is base usage, not custom vocabulary — the objection is to inventing an EDGE, and a classifier is not an edge. ALTERNATIVES: (i) leave it and document the preference — REJECTED, that is a reminder, and D0047 holds that manual vigilance is not a control; the current state is exactly what a documented preference produces, since the notes already recorded `:>` as the idiomatic derivation replacement and #DerivedFrom was used 91 times anyway; (ii) migrate everything including the classifiers — REJECTED, there is no base relationship for 'this Decision is a prospective change', so it would replace a legitimate construct with a worse one; (iii) migrate now without D0067 — REJECTED, 613 occurrences across load-bearing guard inputs is exactly the case the migration process exists for; (iv) CHOSEN. WHY PROPOSED: §2.2 fixes the edge algebra and §2.5 freezes schema/core, so changing how edges are expressed is not self-acceptable, and the migration is large enough that its sequencing deserves a human decision rather than my judgment.";
        :>> consequences = "Four tracked items, all at frontier top and all blocked on this acceptance: dcBaseFirstVocabulary (the rule + its control), dcProcessAssertsConstraints (retires process-units.toml, correcting sprint 265), dcMigrateVerifyToBase (613 occurrences), dcMigrateDerivedFromToBase (91). issue095 resolves with the first. The marker-vocabulary guard stays, since project markers remain possible and the typo class remains real for them, but its exposure shrinks as shadowing markers retire. Already applied ahead of acceptance, being pure doc correction of false claims rather than a change of rule: sysmlv2-syntax-notes.md now qualifies the sequence form as kernel-only and lists the verified base relationships. D0138's core-vs-process-bound split is preserved unchanged by (D) — the mapping moves from TOML into the model, and the safety property does not depend on where it is stored. NOT ADDRESSED HERE, and deliberately: whether `#DependsOn` on a `dependency` is pure redundancy, since an unmarked dependency already means dependency. That is 91 occurrences of possible no-op markup and deserves its own measurement rather than being folded in on suspicion.";
    }

    // acceptance event (D0121 review-queue sign-off; D0066/D0106 — human-judged, not fabricated)
    verification d0139Accept : Test { :>> id = "b1772954-56b6-471c-9e37-049f68a957cc"; :>> method = VerificationMethod::confirmation; :>> procedureText = "wweatherholtz, 2026-08-14, supplying the attestation for this acceptance in their own words: \"justification needs to be explicit\". Asked in the same breath whether a NEW decision should dictate the correctness of items authored under OLDER processes — answered: it must not, and does not. D0139(B) grandfathers the engine's 17 existing markers to WARNINGS under the forward-only rule (issue068), so the base-first control applies to what is authored NEXT. Changing existing items is a separate, deliberate act under D0067's gated migration, never a guard retro-failing work that was correct when written."; }
    part d0139AcceptR1 : TestResult { :>> id = "dea8efdf-0898-4189-93bb-de34e77de4de"; :>> outcome = VerdictKind::pass; :>> judgedAgainst = "36187ea"; :>> judgedAt = "2026-08-14"; :>> judgedBy = "wweatherholtz"; }
}
