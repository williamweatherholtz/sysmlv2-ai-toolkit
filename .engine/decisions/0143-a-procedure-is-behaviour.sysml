// D0143 — A procedure is BEHAVIOUR: Process/ProcessStep become `action def`, and step sequence becomes
// native `first..then` succession instead of an `order : Integer` sort key.
// #ProspectiveChange (D0070): every step survives with its order preserved; no sprint is invalidated.
package Decision0143 {
    private import EngineElement::*;
    private import EngineWork::*;
    private import EngineVerification::*;
    private import EngineRelationships::*;

    #ProspectiveChange part d0143 : Decision {
        :>> id = "6a2f81d4-97c3-4e50-b86a-1d0947fe3b28";
        :>> title = "D0143: Process and ProcessStep are `action def`; step order becomes native succession";
        :>> createdAt = "2026-08-14";
        :>> createdBy = "claudeOpus5";
        :>> status = DecisionStatus::accepted;
        :>> context = "Panel finding (c), raised by the antagonist and rated High confidence by the dispassionate correctness critic — the only finding all three critics ranked above the marker count the human originally asked about. `Process` and `ProcessStep` were `part def :> Element` with their behaviour in String attributes (`actionText`, `producedArtifact`, `triggerCondition`) and their sequence in `attribute order : Integer`. process.sysml:5-6 records exactly WHY, and it is the whole diagnosis in one line: 'Reserved words renamed: action -> actionText, output -> producedArtifact, trigger -> triggerCondition'. The author reached for `action def`, hit reserved keywords, and renamed the FIELDS instead of using the constructs those keywords belong to. The repo already models behaviour correctly elsewhere — `.engine/workflows/business.sysml:9-21` is a clean `action def` with typed in/out parameters, `first..then` successions and `flow` — so it held TWO mechanisms for an ordered procedure, and the 93 ProcessStep instances used the weaker one. A `part def` also renders as structure in a standard viewer, so the layer most likely to render WELL was rendering as inert boxes.";
        :>> decision = "(A) `Process` and `ProcessStep` become `action def`, specializing a new `abstract action def TrackedAction` in element.sysml — the fourth per-metaclass tracked base, added for exactly the cross-metaclass reason the requirement / use-case / verification bases already exist (D0055). (B) `attribute order : Integer` is DELETED. Sequence is native `first <step> then <step>` succession, emitted per Process group. (C) All 115 instances retype from `part x : Process` to `action x : Process`; the 71 orderings become successions. (D) The parser gains what reading this requires: typed action usages (`action x : T { }`), untyped action usages with parameter bodies (`action x { out y : T; }`), `:>` on an `action def`, member features inside action-def bodies, and `in`/`out` as member kinds. (E) `keel activation` reads `assert constraint` from an ActionUsage as well as a Part, so D0141's 14 asserts survive the retype.";
        :>> rationale = "The change is small in meaning and large in reach, which is the usual shape when a metaclass is wrong: nothing about what a process IS changes, but everything that reads it does. Two properties were treated as non-negotiable and both were verified rather than argued. FIRST, the target shape had to be valid SysML v2 BEFORE anything was rewritten — `_spike_process_as_action.py` kernel-checked every shape the migration would emit: `action def Proc :> Base`, a typed action usage with attributes, `assert constraint` inside both an action usage and an action def, successions between package-level usages and inside a def, and an abstract action def carrying tracked attributes. All valid. Building first and discovering the shape afterwards is the issue097 failure and it would have been far more expensive here than it was there. SECOND, D0141's asserts had to survive: they had been attached to the very parts being retyped, so a careless migration would silently drop 14 controls. `keel activation` output is IDENTICAL before and after — 6 units, same guard counts — which is the proof. WHY DELETE `order` RATHER THAN KEEP BOTH: an integer sort key alongside a succession is dual truth, and the engine's whole premise is that state is computed from one authored fact rather than restated. The 71 successions carry exactly the orderings the 93 `order` values carried; a control total, not a judgement. WHAT THIS DOES NOT DO: `actionText`, `producedArtifact` and `triggerCondition` remain Strings. Converting `producedArtifact` to a typed `out` parameter plus a `flow` is the natural next step and is genuinely valuable — it is what would let a process connect to its neighbours by typed item flow rather than by prose — but it requires deciding what each artifact's TYPE is, which is modelling work per step rather than a mechanical transform, and bundling it here would have made a mechanical migration into a judgement-heavy one.";
        :>> consequences = "element.sysml gains `abstract action def TrackedAction`; process.sysml retypes both definitions and drops `order`; 17 process files retype 22 Process + 93 ProcessStep usages and gain 71 successions. keel-parser gains ActionUsage, action-def specialization, action-def members, and in/out member kinds — four increments that also make the parser correct for any future behavioural modelling, not just this one. `parser-coverage` fell from 7 to 1 during this work as each gap surfaced; the single residue is a nested action shape and stays VISIBLE rather than being silently tolerated. Marked #ProspectiveChange (D0070): no sprint is invalidated, since every step keeps its identity, its text and its position — only the metaclass and the encoding of order change. Frozen-schema sign-off is carried by the human's acceptance in the d0143Accept event.";
    }

    verification d0143Accept : Test { :>> id = "8c15b3e7-0d42-4a96-97fb-2e58061cd4a3"; :>> title = "Human acceptance of d0143 (frozen schema/core, §2.5)"; :>> createdAt = "2026-08-14"; :>> createdBy = "claudeOpus5"; :>> method = VerificationMethod::confirmation; :>> procedureText = "wweatherholtz, 2026-08-14, verbatim: '#3 is important. required to consider this work finished. fix and proceed please.' Item #3 as presented named exactly this change and its sibling: 'retyping Process/ProcessStep to action def, and converting ~3000 provenance strings to ref Actor … both are migrations over instance data needing D0067 gated expand/migrate/contract', explicitly listed as the work I had EXCLUDED from the leanness sweep and offered for their review. They read that summary and directed both to be done. This attestation covers the Process-as-behaviour half; the provenance migration carries its own record."; }
    part d0143AcceptR1 : TestResult { :>> id = "d94e0f68-71ba-4c25-8039-5a1e72cb60df"; :>> outcome = VerdictKind::pass; :>> judgedAgainst = "dbf486f"; :>> judgedAt = "2026-08-14"; :>> judgedBy = "wweatherholtz"; }
}
