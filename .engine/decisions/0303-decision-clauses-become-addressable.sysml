// D0303 (status: the `status` field below is the truth) — clauseAddressable: a multi-clause Decision is chartered per clause, so decision-scaffolding can see partial delivery
// Recorded via `keel record decision` (D0105 RMWX axis; issue054). Acceptance is a separate explicit
// human gate (method=confirmation, D0106): flip status + add the d0303Accept event on sign-off.
package Decision0303 {
    private import EngineElement::*;
    private import EngineWork::*;
    private import EngineVerification::*;
    private import EngineRelationships::*;

    // RESEARCH: Measured on this tree 2026-09-04: 40 accepted Decisions enumerate two or more clauses '(1) ... (2) ...' in their decision text and are chartered by fewer Stories than clauses - and the count is NOT a signal, because one Story routinely delivers every clause (d0302: four clauses, one sprint). The only thing that separates d0252's nine-day partial delivery from d0302's complete one is WHICH clause each edge covers, and no edge carries that. Prior art in this tree: issue331 and the D0278 registry entry; D0102 (typed links, not prose); the control-map's per-hazard edges, which are the same shape one level down. Outside: requirements tools address clauses by identifier (a 'shall' per id); SysML v2 allows an attribute on a dependency usage, so option A is native.
    part d0303 : Decision {
        :>> id = "bb85d7c3-8e8b-48e4-9ad9-67aeb470fdc0";
        :>> title = "clauseAddressable: a multi-clause Decision is chartered per clause, so decision-scaffolding can see partial delivery";
        :>> createdAt = "2026-09-04";
        :>> createdBy = "claudeOpus5";
        :>> status = DecisionStatus::accepted;
        :>> context = "issue331 (D0278 registry, direction under): decision-scaffolding passes a Decision the moment ONE #CharteredBy edge reaches it, so a compound Decision half-delivered reads as covered - d0252 clause A's command half sat unbuilt for nine days while clause B's rollback work carried the inbound edge. The fix needs a Decision's clauses to be ADDRESSABLE and an edge to say which clause it charters; today clauses are prose enumerations inside one String field, and the schema (frozen, invariant 5) has no place for either. A heuristic without that identity - clauses counted against Stories - was measured at 40 hits with the delivered cases indistinguishable from the partial ones, so it was not built. This is a schema question and therefore a FORK.";
        :>> decision = "OPTION A (edge attribute): #CharteredBy dependencies gain an optional `clause` attribute naming the clause they cover ('A', '1'); a Decision declares its clause identifiers in a `clauses` list attribute; decision-scaffolding reports any declared clause with no chartering edge. COST: a schema change to the Decision type and the relationship metadata, a migration that declares clauses on the ~40 multi-clause Decisions (or grandfathers them by absence of the list), and every future compound Decision authored with the list. OPTION B (clause items): a `DecisionClause` item type, one part per clause under the Decision's package, chartered like any item; the Decision itself stays whole. COST: a new item type in the frozen schema, a heavier authoring shape, and every view that reads Decisions learning a child type - but the strongest identity, since a clause becomes an addressable element with its own edges and verification. OPTION C (convention): no schema change - a compound change is recorded as one Decision PER clause going forward, so every Decision is single-clause and the existing guard is exact; existing multi-clause Decisions are grandfathered and listed once by a census. COST: more Decision records per change (D0301 makes recording cheap), a loss of the one-record narrative for a layered change, and the past 40 stay invisible to the guard.";
        :>> rationale = "WHY NOT DECIDE THIS AUTONOMOUSLY: invariant 5 freezes the schema and D0207's standing consent covers non-forks only; A and B both change the schema, and C changes how every compound Decision is written - each is a direction the human owns. WHAT I RECOMMEND, and what would change it: OPTION C now, because it needs no schema change, the existing guard becomes exact for every new Decision, and D0301 has just made a Decision record cheap to write - and because the last nine days of Decisions (D0296-D0302) were each a layered change that WOULD have read better as one record per layer with edges between them. It stops recommending C if the human wants the past 40 covered, which only A or B can do, or wants the one-record narrative kept, which C gives up. A is the smallest native change if a schema change is acceptable; B is the strongest identity and the largest authoring cost.";
        :>> consequences = "Until accepted: issue331 stays open, registered in control-defects.toml with its stated reason, and dcDecisionClausesAreAddressable carries its #Resolves edge, blocked on this Decision. On acceptance of C: a convention line in CLAUDE.md, a census view listing the grandfathered multi-clause Decisions, and the registry entry leaves. On A or B: a schema Decision, a migration under D0067, and the guard learns clauses.";
    }

    // acceptance event (D0121 review-queue sign-off; D0066/D0106 — human-judged, not fabricated)
    verification d0303Accept : Test { :>> id = "eb8c640c-2a5f-40a0-b9fb-724570f3eeec"; :>> method = VerificationMethod::confirmation; :>> procedureText = "OPTION C chosen. their words: 'i do like C the best'"; }
    part d0303AcceptR1 : TestResult { :>> id = "224dc2cf-8c75-40e8-a5ff-cda1759429ee"; :>> outcome = VerdictKind::pass; :>> judgedAgainst = "fcd56db"; :>> judgedAt = "2026-09-04"; :>> judgedBy = "wweatherholtz"; :>> createdBy = "claudeOpus5"; }
}
