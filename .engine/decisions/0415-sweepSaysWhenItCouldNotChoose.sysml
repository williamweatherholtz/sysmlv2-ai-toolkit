// D0415 (status: the `status` field below is the truth) — sweepSaysWhenItCouldNotChoose: a knob sweep on recall_bench.py ends with a verdict derived from the measured numbers - DISCRIMINATED naming the spread, or COULD NOT CHOOSE naming the statistic that never moved and whether any case's outcome changed at all
// Recorded via `keel record decision` (D0105 RMWX axis; issue054). Acceptance is a separate explicit
// human gate (method=confirmation, D0106): flip status + add the d0415Accept event on sign-off.
package Decision0415 {
    private import EngineElement::*;
    private import EngineWork::*;
    private import EngineVerification::*;
    private import EngineRelationships::*;

    part d0415 : Decision {
        :>> id = "ab22c2a2-ff6a-44c3-a93d-0aa02944b6ed";
        :>> title = "sweepSaysWhenItCouldNotChoose: a knob sweep on recall_bench.py ends with a verdict derived from the measured numbers - DISCRIMINATED naming the spread, or COULD NOT CHOOSE naming the statistic that never moved and whether any case's outcome changed at all";
        :>> createdAt = "2026-09-09";
        :>> createdBy = "claudeOpus5";
        :>> status = DecisionStatus::accepted;
        :>> context = "issue405, tracked as dcSweepSaysWhenItCouldNotChoose. Six settings of the dominant-source second hop were swept by hand on recall_bench.py's default 50-case arm in sprint 593 and every one returned 49/50 hits at median position 3, byte-identical to the mechanism switched off, because every case in that arm draws its query from a record one edge from the target and the arm contains no case a second hop applies to. That neutrality was read as a verdict twice in opposite directions: D0325 recorded the rare-term narrowing as neutral at every threshold and rejected it on this same evidence, and the criterion governing the second hop pressed toward choosing on the eight hand-written questions instead. D0364 built the two-hop arm, on which the same mechanism moved 15/50 to 22/50, and resolved that instance - but a sweep was still a loop the operator ran by hand, so nothing stopped the next mechanism being swept on an arm that cannot see it and the neutrality being read again.";
        :>> decision = "NOT A FORK: the DoD names one mechanism and its verdict rule. recall_bench.py takes --sweep KNOB=v1,v2,... naming one KEEL_RECALL_* knob (prefix optional) and runs the chosen arm once per value with that knob set in the environment the recall subprocess sees. It prints the per-value numbers (hits, median position, top-3, mean rows, latency) and ends with one verdict line computed from those numbers and from nothing the caller passed. DISCRIMINATED when hits or median position took more than one value across the sweep, naming the spread of each statistic per value. COULD NOT CHOOSE when neither moved, naming both, and then one of two derived clauses: no case's outcome (the target's shown position) changed at any value, so this set contains no case the knob applies to and the sweep says to run it on an arm that does; or the knob moved N named cases' positions without moving either statistic, so the set has too few cases the knob applies to for these statistics to choose. The verdict function is pure and --probe runs it on its known cases before any sweep - D0364's measured two-hop numbers must read DISCRIMINATED, issue405's default-arm numbers must read COULD NOT CHOOSE with the no-case clause, and equal totals with one shifted case must read COULD NOT CHOOSE without it - and a sweep refuses to run if a probe case fails.";
        :>> rationale = "A number a set cannot move is not a measurement of the knob, and the reader of a per-value table has no way to tell 'the knob does nothing' from 'this set has nothing the knob touches' unless the tool says which it saw. The per-case outcome vector is what separates them: two values with equal outcomes on every case did not touch the set, which is a fact about the set; equal totals over shifted cases is a fact about the statistics. Deriving the verdict from the numbers rather than a flag is what keeps it from being asserted - the same rule D0388 applies to every check, and the probe pair is that rule applied to the verdict itself, run before the tree is read so a wrong first answer is caught on cases chosen in advance.";
        :>> consequences = "recall_bench.py gains --sweep and --probe, run_arm returns the statistics the summary prints plus the per-case outcomes, and the plain run's numbers are unchanged. The knowledge-graph-memory skill's step-7 row tells an adopter that a sweep ends with this verdict. STATED LIMIT: the verdict compares hits and median position because those are the two statistics issue405 saw held; a knob whose only effect is on precision or on rows shown reads COULD NOT CHOOSE with the touched-cases clause, which names the cases so the reader can look. The recall binary is deterministic on a fixed tree, so a shifted case is the knob's doing and not noise; a sweep across a tree that changes mid-run is not a sweep.";
    }

    // acceptance event (D0121 review-queue sign-off; D0066/D0106 — human-judged, not fabricated)
    verification d0415Accept : Test { :>> id = "2e7a462d-90c9-490a-ae50-f7fabae85612"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0415AcceptR1 : TestResult { :>> id = "dc4fac38-4ddf-4786-a5f9-b547fc3c53ea"; :>> outcome = VerdictKind::pass; :>> judgedAgainst = "ae58328"; :>> judgedAt = "2026-09-09"; :>> judgedBy = "wweatherholtz"; :>> createdBy = "claudeOpus5"; }
}
