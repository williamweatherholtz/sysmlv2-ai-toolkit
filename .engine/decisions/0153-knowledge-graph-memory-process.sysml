// D0153 — ACCEPTED (wweatherholtz, 2026-08-16): adopt Knowledge-Graph Memory as a portable process
// unit, adapted from an external artefact. Process-definition change (§3a / D0070) — sign-off is the
// d0153Accept event below.
package Decision0153 {
    private import EngineElement::*;
    private import EngineWork::*;
    private import EngineVerification::*;
    private import EngineRelationships::*;

    #ProspectiveChange part d0153 : Decision {
        :>> id = "e5a92c71-04f8-4b36-9d15-7c380ab24e69";
        :>> title = "D0153: adopt Knowledge-Graph Memory as a shareable process unit";
        :>> createdAt = "2026-08-16";
        :>> createdBy = "claudeOpus5";
        :>> status = DecisionStatus::accepted;
        :>> context = "The human supplied an external artefact — 'Applying Knowledge Graphs', Glitch Cat Club, captured 16 Aug 2026, github.com/Glitch-Cat-Club/graph-memory-starter — and asked for it to be built as 'a generateable shareable process'. In this engine that phrase has a precise meaning, set by nProcessPortability: a process is a self-contained unit of DEFINITION + DEPLOYING SKILL + its declared rules/guards + metadata, which a project can import, export, activate or disable from a palette rather than inheriting the whole engine's process set at `keel init`. THE ARTEFACT'S CONTENT, faithfully: the distinction between PULL (the model searches during the conversation — cost grows with the corpus, accuracy depends on model strength) and PUSH (code finds the facts before the model is involved); a tiered implementation path where the tier changes but two jobs never do — seeding and walking; an ontology method that starts from the QUESTIONS rather than from the documents; identity computed as a hash of type plus normalised name so re-extraction merges instead of duplicating; injection through a prompt-submit hook so retrieval never costs a model call; verification on a deliberately hard multi-hop case; and an honest limits table whose axes are density, size, vagueness and ambiguity rather than depth.";
        :>> decision = "ACCEPTED: adopt it as `.engine/processes/knowledge-graph-memory.sysml` (a Process with eight sequenced ProcessSteps) plus its deploying skill at `.engine/skills/knowledge-graph-memory/`, registered in the skills registry so the process-skill guard can see the pairing. The step ORDER is the load-bearing part and is preserved from the source: questions, then vocabulary, then logical model, then extraction — a vocabulary derived from documents describes the documents, and a vocabulary derived from questions answers them. Ownership is assigned per step, and the two the human owns are deliberate: the questions and the closed vocabulary. The rest is the AI's.";
        :>> rationale = "WHY A PROCESS AND NOT CODE OR A DOC: the method's failure modes are all ORDERING and OWNERSHIP failures — surveying the corpus before writing the questions, letting the vocabulary grow open during extraction, letting the model choose the types, demonstrating on a question keyword search could already answer. A process step with a declared owner and a declared predecessor is exactly the shape that prevents those, and a prose write-up is exactly the shape that does not. WHY IT SHIPS WITH NO GUARDS, stated because a portable unit is defined as bringing its rules: every candidate guard — the graph is fresh with respect to the corpus, the vocabulary is closed — depends on a store this engine does not own and cannot read, so it would be either unenforceable or an engine gating on a file it has no business knowing. A project that wants freshness enforced declares that guard in its own `.engine/`, where the corpus lives. THE SOURCE'S MEASUREMENTS ARE ITS OWN AND ARE NOT ADOPTED AS THIS ENGINE'S CLAIMS: the artefact reports a small model going from a wrong answer to a correct one with zero tool calls and millisecond retrieval, and injected context roughly fixed in size against searches that grew with the corpus. Those were measured on one corpus and one question by its authors. This process reproduces the METHOD; a project that adopts it measures its own results, and the skill says so. ALTERNATIVES: (i) implement it directly against keel's own model, whose typed items and edges already ARE a graph — REJECTED for now as a conflation: keel's model is an instance of the pattern rather than the pattern, and building the instance first would produce something unshareable, which is the opposite of the request; (ii) record it as a doc under `.engine/docs/` — REJECTED, an inert write-up is what D0059 exists to prevent and nothing would deploy it.";
        :>> consequences = "If ACCEPTED: one new process unit in the palette, activatable per project; the engine's process count rises by one and the skills registry by one entry; no existing process, guard or schema changes, and nothing is enforced on any project that does not activate it. keel's own model becomes an obvious future application of the pattern — its items and typed edges are already entities and relations — and that remains deliberately unbuilt here. If REJECTED: the artefact stays an external document, and the ordering discipline that makes the method work stays unenforceable. Recorded either way because the human asked for it and the evaluation is itself the useful artefact.";
    }

    // acceptance event (D0121 review-queue sign-off; D0066/D0106 — human-judged, not fabricated)
    verification d0153Accept : Test { :>> id = "4b8bc881-e631-4e6f-8e03-1ec2adc6368a"; :>> method = VerificationMethod::confirmation; :>> procedureText = "wweatherholtz, 2026-08-16, verbatim: 'proposed and accepted'. Given in direct reply to the D0153 proposal, which set out the process unit as built (definition + deploying skill + registry pairing), stated that it ships with NO guards and why — every candidate depends on a store this engine does not own and cannot read — recorded the source artefact's measurements as ITS claims rather than this engine's, and named the rejected alternative of implementing against keel's own model first as producing the instance rather than the pattern. The files were committed as proposed specifically so they could be read before this gate rather than judged from a summary."; }
    part d0153AcceptR1 : TestResult { :>> id = "a8ef99d6-ff5d-44ce-a0f8-ce4e5bbd94fc"; :>> outcome = VerdictKind::pass; :>> judgedAgainst = "2f15319"; :>> judgedAt = "2026-08-16"; :>> judgedBy = "wweatherholtz"; }
    part d0153AcceptR2 : TestResult { :>> id = "28397291-d734-4b70-a0cf-4942dda6285f"; :>> outcome = VerdictKind::pass; :>> judgedAgainst = "eb0adcf"; :>> judgedAt = "2026-09-04"; :>> judgedBy = "wweatherholtz"; :>> createdBy = "claudeOpus5"; :>> notes = "REBOUND (D0308): AUTO-RE-BOUND under standing consent (D0207/D0308): decision wording PROPOSED to ACCEPTED at 8507239 - editorial, the agreed substance unchanged. Their standing words, verbatim: 'issues raised are automatically accepted. they can be customizedly changed post-fact.'"; }
}
