// D0240 (status: the `status` field below is the truth) — the channel's decision id round-trips: one join, one split, one marker
// Recorded via `keel record decision` (D0105 RMWX axis; issue054). Acceptance is a separate explicit
// human gate (method=confirmation, D0106): flip status + add the d0240Accept event on sign-off.
package Decision0240 {
    private import EngineElement::*;
    private import EngineWork::*;
    private import EngineVerification::*;
    private import EngineRelationships::*;

    // #ProspectiveChange (D0070) - this Decision governs a process/schema change; the co-committed
    // change rides the process-change guard's hard lock.
    #ProspectiveChange part d0240 : Decision {
        :>> id = "10967f7d-ea39-48e5-a931-d989a1865d46";
        :>> title = "the channel's decision id round-trips: one join, one split, one marker";
        :>> createdAt = "2026-08-27";
        :>> createdBy = "claudeOpus5";
        :>> status = DecisionStatus::accepted;
        :>> context = "D0234 qualified the channel's decision id as `alpha/d0001`, because `dNNNN` is unique only within a project while the channel's marker and its GitHub search are repo-scoped. The qualification was incomplete in four places, all verified by the panel, and the verification that accompanied it tested the join function in ISOLATION and never checked what actually gets written into an issue body. 1. The DURABLE marker was written BARE — `keel-decision: {c['name']}` — while every lookup in the same file used the QUALIFIED `c['cid']`. So no lookup could match what the opener had just written: the standing thread re-posts on every run, the backfill posts a duplicate, and two projects write byte-identical markers, which is the exact collision the qualifier exists to remove. `ensure_override_threads` in the same file already wrote the qualified form, so the two writers disagreed with each other. 2. `decision_in_gesture` split on every non-alphanumeric character, so a reject naming `alpha/d0001` yielded the bare `d0001` — silently retargeting a human's REJECTION to the root project. The opener instructs the human to type exactly that qualified form. 3. The recorder's HUMAN branch never called the splitter its own AUTO branch calls six lines earlier, so a fork acceptance — the one decision class that genuinely needs a human — was recorded against the wrong tree or refused outright. 4. The decider table was read from the root, and at a workspace root there is no project and therefore no table, so the channel authorised NOBODY on any project in the repository.";
        :>> decision = "1. The opener writes the QUALIFIED id into the marker. 2. `decision_in_gesture` reads the `label/dNNNN` form and returns it whole, staying strict: `d` then exactly four digits, and a label of non-empty `[A-Za-z0-9._-]` segments. A URL is not a label. 3. The recorder's human branch splits the id and enters the project exactly as the auto branch does, and the decider is resolved AFTER the split, in the project the decision belongs to. 4. `keel github-decider` takes `--root PATH`, and the opener reads deciders from every project in the repository for assignment. Who may RECORD against a given project is re-checked per project. 5. The JOIN moves into the binary beside the split it must invert (`keel github-decision-id --join`), and the opener delegates to it.";
        :>> rationale = "Clause 5 is the one that matters beyond this defect. Four gaps, and three of them are the same shape: two implementations of one fact, disagreeing. The join lived in Python while the split lived in Rust and nothing compared them; the marker had two writers in one file and they differed; the decider had one reader asking the wrong tree. D0105 says one canonical home per fact, and the join/split pair now has one home and one test (`join_and_split_are_inverses`) that would have failed on the shipped code. ALTERNATIVES for the marker: (A) make every lookup read the bare form — rejected: it re-opens the collision D0234 closed, because two projects' markers become identical again. (B) write both forms — rejected: two markers per decision is two truths, and the reader would have to choose. (C) write the qualified form — CHOSEN, and it is what the readers already expected. Single-project repositories are unchanged and this is measured, not assumed: `join_decision_id` returns the BARE name when the repo holds one project, and also when the label is the root project in a multi-project repo — verified through the opener's own `qualify` (`d0240` stays `d0240`, `alpha/d0001` qualifies, root-in-multi `d0007` stays bare). Every issue already open in every existing repo carries the bare form and keeps resolving. Clause 3's ordering is load-bearing and was not obvious: the decider lookup used to run BEFORE the gesture was parsed, so it could not know which project the decision belonged to. Resolving it after the split fixes gap 4 for the recorder as a consequence rather than as a separate patch — asking the ROOT project's table about another project's decision would be the mirror error of asking a table that does not exist.";
        :>> consequences = "Two of the four gaps live in scripts that NOTHING read before, which is precisely how a writer and a reader in the same file came to disagree. Both are one-line facts about a text file, so both are now checked from `github.rs`: the marker must be qualified and must not be bare; the human branch must split, and the decider lookup must FOLLOW the split. A defect nothing checks is a defect that ships. Verified: 16 github tests pass, 11 suites green, clippy clean, and the opener's `qualify` exercised live against the binary in all three cases. `keel github-decider` behaves correctly with no argument, with a login, with `--root` plus a login, and with `--root` alone; and a nonexistent root still authorises NOBODY, which is the safe direction and is exactly what the workspace root was doing to everyone. NOT claimed: an end-to-end run of the channel against GitHub. These fixes are verified by unit tests, by static checks over the two scripts, and by exercising the binary and the opener's Python directly. The channel's live behaviour in a real multi-project repository is unexercised, because doing so means opening real issues in a real repository; the first workspace that adopts the channel is where that gets its first live test, and this Decision is the record of what was and was not exercised.";
    }

    // acceptance event (D0121 review-queue sign-off; D0066/D0106 — human-judged, not fabricated)
    verification d0240Accept : Test { :>> id = "df7f39f4-a77e-45c6-b410-d51978e7d45b"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0240AcceptR1 : TestResult { :>> id = "8d73cb30-aadb-4f7e-acc3-ad3529805177"; :>> outcome = VerdictKind::pass; :>> judgedAgainst = "3bb8e77"; :>> judgedAt = "2026-08-27"; :>> judgedBy = "wweatherholtz"; }
}
