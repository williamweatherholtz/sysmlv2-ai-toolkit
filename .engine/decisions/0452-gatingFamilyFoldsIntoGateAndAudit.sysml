// D0452 (status: the `status` field below is the truth) — gatingFamilyFoldsIntoGateAndAudit: the twelve gating verbs become sub-verbs of keel gate and keel audit, each keeping its word; the hooks, CI workflows and every call site are rewritten in the same commit that removes the names
// Recorded via `keel record decision` (D0105 RMWX axis; issue054). Acceptance is a separate explicit
// human gate (method=confirmation, D0106): flip status + add the d0452Accept event on sign-off.
package Decision0452 {
    private import EngineElement::*;
    private import EngineWork::*;
    private import EngineVerification::*;
    private import EngineRelationships::*;

    // RESEARCH: Measured 2026-09-11 against .engine/cli/commands.sysml, keel-cli/src/main.rs, .githooks and .github/workflows at 1419069 (re-runnable census over the CliCommand facts and a grep for keel followed by a family verb). The gating family holds twelve facts, all reads and stable: validate, check, check-engine, guard, gate, rules, audit, audit-history, audit-adherence, audit-ci-runs, assured, adoption-check. Call sites outside target/: engine-authored surface 93, .claude generated 37, root docs 50, Rust source 56, Rust tests 83, hooks and CI workflows 30 (validate 5, check-engine 7, guard 4, gate 2, rules 3, audit-history 3, audit-adherence 2, audit-ci-runs 2, adoption-check 2), .engine/decisions 103 and .tracking 1566 (the last two not rewritten). validate is named in 300 files and guard in 283 - the two most cited verbs in the tree. Inside the binary, keel land runs the touched test set and the eol check from a copy of itself (D0422) and the hooks resolve the binary by one probe (D0230): every hook line that names a gating verb is on the enforcement surface the keystone lock covers (D0209 clause 2), which is why this Decision carries the safety marker and waits for the human's own word, as d0399 said it would.
    // #SafetyChange (D0070) - this Decision governs a process/schema change; the co-committed
    // change rides the process-change guard's hard lock.
    #SafetyChange part d0452 : Decision {
        :>> id = "64181195-550b-4d7c-bdd5-abf1022c0d44";
        :>> title = "gatingFamilyFoldsIntoGateAndAudit: the twelve gating verbs become sub-verbs of keel gate and keel audit, each keeping its word; the hooks, CI workflows and every call site are rewritten in the same commit that removes the names";
        :>> createdAt = "2026-09-11";
        :>> createdBy = "claudeOpus5";
        :>> status = DecisionStatus::accepted;
        :>> context = "d0399 option A, the human's own word on 2026-09-11, folds five CLI families into their routers in the sprint 512 shape (D0273): a D0067 transform, a byte-equality baseline captured from the pre-fold binary, call-site rewrites in the SAME commit, no alias window. d0399 also said that the gating and channel families sit on the enforcement surface and that each is a safety Decision awaiting the human's word - the plan named the step but chose not to cover it. This is that Decision for gating: the verbs the pre-commit hook, the stop hook, keel land and the CI workflows call by name to decide whether a commit may land. A wrong rewrite here does not print a wrong answer; it lets a commit through ungated, or blocks every commit until repaired.";
        :>> decision = "The twelve gating verbs fold into two routers, each verb keeping its word as the sub-verb and its arguments unchanged. Under keel gate: keel validate [ROOT] becomes keel gate validate [ROOT]; check FILE..., check-engine [ROOT], guard [--no-receipt], rules [ROOT], assured [ROOT] and adoption-check [ROOT] become keel gate <word> with the same trailing arguments; keel gate itself, bare or with --fast or --workspace, keeps its meaning as the tiered gate, and the router resolves a reserved sub-verb before it reads a positional as a root. Under keel audit: keel audit [ROOT] keeps its meaning bare; audit-history, audit-adherence and audit-ci-runs become keel audit history, keel audit adherence and keel audit ci-runs with the same trailing arguments. The ten top-level names are REMOVED from the dispatch, from COMMAND_NAMES, from the CliCommand facts and from cli_facts.rs; the gate and audit facts' invocations name their sub-verbs. Each arm is MOVED verbatim, its function untouched, and the criterion is byte equality of stdout, stderr and exit code against outputs captured from the pre-fold binary over a green tree, a red tree and a workspace root, because a gate's exit code is its answer. Every hook under .githooks, every CI workflow under .github/workflows, every call site under .engine, .claude, the root docs, the Rust source and tests is rewritten by the committed transform or by hand in the ONE commit that removes the names, and that commit passes its own rewritten pre-commit hook and its own rewritten CI before it is called landed. .engine/decisions and .tracking are not rewritten. NOT A FORK: d0399 option A chose the course; this Decision states the mapping that course lands on for one family and waits for the human's own word because of where the verbs sit.";
        :>> rationale = "The gating verbs are the names in every hook, CI step and skill, and CLAUDE.md section 5 teaches them as separate words because they answer different questions - validate is not guard is not gate. The fold keeps every word and changes only where it sits, so the vocabulary the section teaches survives with one verb in front of it. The one-commit rule matters most here of all five families: a hook naming a verb the binary lacks blocks every commit including the fix, and a CI step naming one turns every push red, so the rewritten hooks and workflows must land with the removal and be exercised by it. The marker is carried and the plan cover is NOT used because d0399's own text reserved this family for the human's word; a covered acceptance would have been within the letter of D0396 and against the plan's stated intent.";
        :>> consequences = "One sprint, eight points, the largest of the program: the transform under .engine/tools/migrations/ with a dry run that reconciles counts before --apply, the dispatch, cli_surface and cli_facts edits by hand, the hook and workflow rewrites, the Rust test fixtures by hand, and the three-tree byte comparison. keel show hardening helpCoverage.dispatched falls by ten and the sprint's implement gate reads the number back. CLAUDE.md sections 4 and 5 and guards.md name the new spellings in the same commit; keel sync-claude regenerates .claude. Every downstream project's hooks and CI that name a gating verb break by name on the next engine update and must update engine, hooks and skills together; the D0252 clause A handshake names the missing command. Until the human's word lands this Decision is proposed and no gating verb moves.";
    }

    // D0303 layering: the mapping for one family under the program d0399 option A chose
    #DependsOn dependency from d0452 to d0399;

    // acceptance event (D0121 review-queue sign-off; D0066/D0106 — human-judged, not fabricated)
    verification d0452Accept : Test { :>> id = "03c091d8-ca60-4e16-997c-57d8bf7622a1"; :>> method = VerificationMethod::confirmation; :>> procedureText = "Selected on the decision brief copy-out (seventeenth publish), pasted into chat 2026-09-12; the recommended course. Their note recorded with the answer, verbatim as a statement in the same commit: hooks must check bespoke processes granularly, not hardcoded ones. - their words, verbatim: “Accept: the twelve gating verbs become sub-verbs of keel gate and keel audit, each keeping its word; hooks, CI and every call site rewritten in the commit that removes the names (recommended)”"; }
    part d0452AcceptR1 : TestResult { :>> id = "5fecdb0a-4c0e-4402-9072-faf0aadecb46"; :>> outcome = VerdictKind::pass; :>> judgedAgainst = "36715a2"; :>> judgedAt = "2026-09-12"; :>> judgedBy = "wweatherholtz"; :>> createdBy = "claudeFable5"; }
}
