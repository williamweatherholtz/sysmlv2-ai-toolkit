// D0277 (status: the `status` field below is the truth) — There is ONE inventory of the command surface, and the renderer guard resolves the lens, not the verb
// Recorded via `keel record decision` (D0105 RMWX axis; issue054). Acceptance is a separate explicit
// human gate (method=confirmation, D0106): flip status + add the d0277Accept event on sign-off.
package Decision0277 {
    private import EngineElement::*;
    private import EngineWork::*;
    private import EngineVerification::*;
    private import EngineRelationships::*;

    // #SafetyChange (D0070) - this Decision governs a process/schema change; the co-committed
    // change rides the process-change guard's hard lock.
    #SafetyChange part d0277 : Decision {
        :>> id = "9f0a909a-81f9-44e1-8cd6-c017a4c4b67c";
        :>> title = "There is ONE inventory of the command surface, and the renderer guard resolves the lens, not the verb";
        :>> createdAt = "2026-09-01";
        :>> createdBy = "claudeOpus5";
        :>> status = DecisionStatus::accepted;
        :>> context = "Landing D0273's collapse required changing guards.rs, which is on D0209 clause 2's enforcement surface, so this Decision is co-committed with it. Two things forced the change. FIRST, the viewpoint-renderer guard diffed renderer strings against VIEW_SUBCOMMANDS - a SECOND hand-maintained list of command names, separate from the cli_surface inventory built one step earlier. Its own comments recorded the cost of being hand-maintained: one entry carried the note 'real since D0129 sync work; never added here, so the first viewpoint naming it failed'. Two inventories of one fact is one too many, and the second had already failed once. SECOND, every renderer now reads `keel show <lens>`, and the guard extracted only the first token after `keel `, so every viewpoint went red the moment the collapse landed.";
        :>> decision = "cli_surface is the single inventory. It gains LENS_NAMES (the 35 lenses reachable through the router) beside COMMAND_NAMES, plus renderer_command, which splits a renderer string into its verb and following token. classify_renderer now calls into it and VIEW_SUBCOMMANDS is DELETED. When the verb is the router, the LENS is what must resolve; for any other verb the command must resolve. Both lists are held equal to what they describe by test - the_command_inventory_matches_the_dispatch parses main's match, the_lens_inventory_matches_the_router parses cmd_show's.";
        :>> rationale = "WHY THE LENS AND NOT JUST THE VERB, which is the substantive half. Accepting `keel show` as sufficient would let `keel show frobnicate` pass the renderer guard and then fail for whoever ran it - the identical hole the guard exists to close, with one extra word in it. The guard's whole claim is that a declared viewpoint names a renderer that actually works, and after the collapse the lens IS the thing that might not exist. WHY DELETE THE SECOND LIST RATHER THAN UPDATE IT. It could have been extended with the 35 lens names and left in place, which is the smaller diff and the wrong answer: the failure mode of a hand-maintained mirror is not that it is hard to update, it is that nobody knows to. The list's own apologetic comment is the evidence - a name was 'never added here, so the first viewpoint naming it failed'. A single inventory with a test holding it equal to the dispatch cannot fail that way. WHY THIS IS A SAFETY CHANGE AND NOT MERELY PROSPECTIVE: it edits guard SOURCE, and it makes a guard's verdict depend on a list that now has two consumers. A wrong LENS_NAMES would make the renderer guard confidently wrong in both directions, which is why the inventory test is not optional decoration.";
        :>> consequences = "The renderer guard passes over the collapsed surface, and a viewpoint naming a lens that does not exist still fails - verified by running the guard before and after, where it went from 6+ violations to zero without weakening the predicate. THE ENFORCEMENT SURFACE GREW A DEPENDENCY: guards.rs now reads cli_surface, so cli_surface is load-bearing for a control even though it is not itself on the locked list. That is worth stating rather than discovering later, and it is the same shape as the gap named in D0276 - migrate's refusals satisfy a SystemRequirement while migrate.rs sits outside the locked set. Two instances now suggest the locked set is drawn around FILE KINDS where it should be drawn around what controls actually read; not fixed here, and the honest form is deriving the locked set from what enforcement code depends on, which is a real proposal rather than a note. ALSO RECORDED: the call-site rewrite initially edited 27 accepted Decision files, changing command names inside procedureText a human had attested. That was caught before commit and reverted - tool-reference scans processes, skills, docs, contracts, workflows and rules, never decisions, so those files never needed rewriting. A Decision's recorded text is what the signer signed; it names the commands that existed when they signed it, and keeping it current is not a goal.";
    }

    // acceptance event (D0121 review-queue sign-off; D0066/D0106 — human-judged, not fabricated)
    verification d0277Accept : Test { :>> id = "5c6722cc-b08a-4120-85a4-b9296fb5ea0b"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0277AcceptR1 : TestResult { :>> id = "dcc29ab1-739f-49e3-a397-6cc07ecf5b36"; :>> outcome = VerdictKind::pass; :>> judgedAgainst = "24dcc73"; :>> judgedAt = "2026-09-02"; :>> judgedBy = "wweatherholtz"; }
}
