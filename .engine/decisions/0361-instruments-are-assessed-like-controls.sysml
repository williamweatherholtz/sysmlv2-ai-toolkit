// D0361 (status: the `status` field below is the truth) — instrumentsAreControls: the propriety inventory covers MEASUREMENT INSTRUMENTS, not only enforcement mechanisms
// Recorded via `keel record decision` (D0105 RMWX axis; issue054). Acceptance is a separate explicit
// human gate (method=confirmation, D0106): flip status + add the d0361Accept event on sign-off.
package Decision0361 {
    private import EngineElement::*;
    private import EngineWork::*;
    private import EngineVerification::*;
    private import EngineRelationships::*;

    // #ProspectiveChange (D0070) - this Decision governs a process/schema change; the co-committed
    // change rides the process-change guard's hard lock.
    #ProspectiveChange part d0361 : Decision {
        :>> id = "fa457c0e-96b1-4eeb-ac4f-ae331f81d7d2";
        :>> title = "instrumentsAreControls: the propriety inventory covers MEASUREMENT INSTRUMENTS, not only enforcement mechanisms";
        :>> createdAt = "2026-09-06";
        :>> createdBy = "claudeOpus5";
        :>> status = DecisionStatus::accepted;
        :>> context = "The control-propriety panel assesses enforcement mechanisms under five lenses, and it works: 40 findings stand against guards, hook probes, launcher probes and the pre-push fix. Every target ever assessed is a thing that BLOCKS. Nothing that MEASURES has ever been assessed - not the computed-facts script the standing brief is built from, not the retrieval benchmark, not the report renderers, not the chart builders, not the new routing probe. That is where this project's defects have actually been coming from. In one day: the facts script typed the release tag it measured against, so every since-the-release number would have described a superseded release behind a provenance string that named a real git command (issue389); a figure legend overprinted itself and a note was cut mid-word, so a figure carrying correct data told the reader something false (issue390); a diagnostic clipped the first forty lines of a gate run and hid the one violation that caused a revert (issue384); a suite that could not start reported a file lock as '0 passed, 0 failed' in the field where a verdict about the code belongs (issue386); a retrieval bar counts an element that answers the question as a miss (issue391); and a routing probe's verdicts flipped on two of four cases between identical runs, so a one-sample number would have looked authoritative and moved on re-run (issue392). Six defects, all in instruments, none in the inventory - and the five lenses would have caught most of them had they ever been pointed there. A wrong number is not softer than a wrong refusal: a refusal announces itself and gets argued with, while a number gets believed, quoted, and acted on.";
        :>> decision = "A measurement instrument is a propriety target: anything that computes a number, a verdict or a figure this project publishes or acts on is inventoried and assessed under the same five lenses as a guard, and an instrument with no assessment is reported as UNASSESSED rather than assumed sound. NOT A FORK: the alternative is a second process with its own lenses for instruments, and the evidence says the existing lenses already cover the observed failures - the typed tag is changeRobustness, the flipping verdicts are measurability, the ground-truth question is overfit - so a parallel process would duplicate the panel and split its practice.";
        :>> rationale = "The lenses transfer without modification, which is the argument for extending the inventory rather than inventing anything: overfit asks whether an instrument is fitted to the example that motivated it, classCoverage whether it measures the class or one instance, changeRobustness whether it survives ordinary evolution or depends on an incidental like a version literal, circumventability whether a result can be routed around or fitted to, and measurability whether a third party re-running it gets the same answer - which is precisely the question a stochastic probe fails and a seeded benchmark passes. The panel's existing guardrails also transfer and matter more here: never assess a copy (an instrument's shipped form, not a scratchpad variant), and the defeater is the deliverable (naming what was tried against the number, not restating that it looked right).";
        :>> consequences = "The propriety inventory grows by the instruments that already exist - the computed-facts script, the retrieval benchmark and its A/B harness, the routing probe, the chart and logic-exhibit builders, the report renderers, the census tool written today - and each is UNASSESSED until a round covers it, which is the honest starting state rather than a clean bill. Rounds stay tranched, so this is a queue rather than a stall. The first tranche should take the instruments whose numbers currently reach a human: the facts script and the chart builders feed the standing brief, and both have already produced a false picture from true data. IMPLEMENTED 2026-09-06, in the commit that carries this line: .engine/contracts/instruments.toml declares 20 instruments (12 hand-written, 8 found by the guard below) and guard 65 instruments-declared holds the declaration against the tree in both directions, shipping with its own proof test per D0360. The manifest is engine-dev-only: migrating it gave every adopter seventeen dead references and turned tool-reference red across 18 tests, which is the mirror defect the guard exists to catch. WHAT THIS DOES NOT DO: it does not make an assessed instrument correct, and it does not turn a judgment into a computation - measurability can be argued and cannot be counted, which is why the output is findings with named defeaters rather than a score.";
    }

    // acceptance event (D0121 review-queue sign-off; D0066/D0106 — human-judged, not fabricated)
    verification d0361Accept : Test { :>> id = "2085b367-bc5e-4831-a9bd-406ac5bd10d5"; :>> method = VerificationMethod::confirmation; :>> procedureText = "their words, 2026-09-08, the copy-for-Claude text of the published brief with their selections marked: '[x] Ratify: measures are assessed too / [ ] Reverse it, keep the panel to controls / [ ] Discuss (answers: d0361)'"; }
    part d0361AcceptR1 : TestResult { :>> id = "eb654f7b-b618-407f-970c-5609537b47c3"; :>> outcome = VerdictKind::pass; :>> judgedAgainst = "a08f2a1"; :>> judgedAt = "2026-09-08"; :>> judgedBy = "wweatherholtz"; :>> createdBy = "claudeOpus5"; }
}
