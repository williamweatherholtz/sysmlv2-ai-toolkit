// D0273 (status: the `status` field below is the truth) — The 43-command lens family collapses into one router, with NO deprecation aliases
// Recorded via `keel record decision` (D0105 RMWX axis; issue054). Acceptance is a separate explicit
// human gate (method=confirmation, D0106): flip status + add the d0273Accept event on sign-off.
package Decision0273 {
    private import EngineElement::*;
    private import EngineWork::*;
    private import EngineVerification::*;
    private import EngineRelationships::*;

    // #ProspectiveChange (D0070) - this Decision governs a process/schema change; the co-committed
    // change rides the process-change guard's hard lock.
    #ProspectiveChange part d0273 : Decision {
        :>> id = "bc33a381-65dd-4380-b967-d49100ecbaaa";
        :>> title = "The 43-command lens family collapses into one router, with NO deprecation aliases";
        :>> createdAt = "2026-09-01";
        :>> createdBy = "claudeOpus5";
        :>> status = DecisionStatus::accepted;
        :>> context = "Measured, not estimated: 111 dispatch arms, of which roughly 43 are read-only lenses performing one act - compute a view of the model and print it. 16 of the 32 declared viewpoints ALSO have a same-named top-level command, and the two mechanisms are only half-connected (keel view orphans fails while keel orphans works). 118 references in .engine skills and processes invoke these commands BY NAME, and guard 39 (tool-reference) fails a process naming a tool it did not receive. The human named the problem twice in their own words - tons of commands when a smaller subset should do, a lot of these seem to be variations of an idea cemented as separate cli hooks - and on the fork they chose the CLEAN BREAK over my recommended alias window.";
        :>> decision = "One keel show <lens> command routes to the existing lens implementations, and the 43 old top-level names are REMOVED in the same change that rewrites the 118 call sites. No alias window, no deprecation period, no dual naming at any commit. Two constraints make this landable rather than merely decided. FIRST, the rename and the call-site rewrite are ONE commit: at no point does a tree exist in which a skill names a command the binary does not have, so guard 39 stays green throughout rather than being suspended. SECOND, and this is a PREREQUISITE rather than a nicety, D0252 clause A's command-capability declaration ships FIRST: unit.toml gains the commands a unit invokes, and an install whose target engine lacks one REFUSES naming the missing command.";
        :>> rationale = "THE HUMAN OVERRODE MY RECOMMENDATION AND THAT IS RECORDED AS SUCH. I argued for aliases on the ground that the 118 call sites live in skills that TRAVEL to other projects, so a same-day cut breaks downstream trees that never asked for the rename. They chose the clean break with that cost stated on the page: breaks 118 call sites the day it lands, every skill needs editing first. Their reason, in their own selection: one surface, no dual-naming period, nothing to remember to retire. That is a coherent preference and the alias window's own weakness is real - an alias list that shrinks as call sites move has no forcing function, and this project's evidence is that undated cleanups do not happen. WHAT I FOUND AFTER THEY DECIDED, which strengthens the sequencing rather than the decision: D0252 clause A already anticipated exactly this. It records that renaming a guard, a schema type or a command is now a breaking change for units that declare it, recorded so a future rename is not made casually, and promises an install-time refusal naming the missing capability. That half is NOT BUILT - the token commands appears nowhere in process_cmd.rs and unit.toml carries only skills, rules, guards and extras. So today the downstream failure mode of a rename is not a named refusal but a broken tree, which is WORSE than the cost stated on the fork page. Building the declaration first converts the accepted cost into the loud one D0252 already promised, and it is unbuilt work under an already-accepted Decision rather than new scope. REJECTED, the alias window: chosen against by the human. REJECTED, cementing the 90 in the ICD without collapsing: their words were an instruction to act, and recording sprawl is not reducing it.";
        :>> consequences = "The visible verb count falls from roughly 111 dispatch arms to under 25. Every lens is reached as keel show <lens>, and the viewpoint/command half-connection disappears because there is one mechanism. BREAKING, and stated plainly: any project holding skills that name the old commands must update its engine and its skill units together; there is no version of keel in which both spellings work. The install-time refusal makes that a named error rather than a silent failure, which is why it ships first. VERIFICATION IS BYTE-EQUALITY, not merely that it runs: every lens reachable through the router must return output identical to its old command, because a consolidation that changes an answer is a rewrite wearing a rename's clothes. guard 39 must stay green at every commit, since a half-migrated skill reference is exactly what it exists to catch. THE ICD FOLLOWS: the 90 CliCommand items D0271 provides for are authored against the POST-collapse surface, so the cemented interface is the one that will exist rather than the one being retired, and the two-way guard then holds it - every dispatched command declared, every declared command dispatched.";
    }

    // NOT auto-accepted (D0207 covers NON-FORK decisions only). This was a three-way FORK put to the
    // human, and they answered it AGAINST my recommendation — so the acceptance is their judgment and
    // carries their id, with my transcription of their words held separately in the quote receipt.
    verification d0273Accept : Test {
        :>> id = "f6a2c058-4b19-47d3-9e81-2a70c3d5b8e4";
        :>> title = "The clean break chosen over the alias window (human adjudication)";
        :>> createdAt = "2026-09-01"; :>> createdBy = "claudeOpus5";
        :>> method = VerificationMethod::confirmation;
        :>> procedureText = "wweatherholtz, 2026-09-01, via the Unattended Distribution decision page returned as a Copy-for-AI digest. They selected, verbatim, 'Yes, and cut the old names immediately - one clean break' on a three-way fork whose recommended option was the alias window, with the cost of their choice stated on the page in the option's own text. THIS IS AN OVERRIDE, recorded as one: I recommended aliases and argued the downstream case for them, and they chose otherwise. The choice is not a misreading - the page named the breakage, the count of affected call sites, and the alternative - so it is an adjudication. WHAT IS THEIRS AND WHAT IS MINE: the DECISION to cut without aliases is theirs. The SEQUENCING constraint in the decision field - that D0252 clause A's command declaration ships before the cut - is mine, added after they answered, on the finding that the install-time refusal D0252 promised does not exist yet. It does not soften their choice; it makes the break they chose loud downstream instead of silent. Their verbatim selection is quoted in d0273Attest1.";
    }

    verification d0273Attest1 : Test {
        :>> id = "07b3d914-8e26-4f57-a0c9-51d8264ef397";
        :>> title = "Quote receipt for d0273Accept (D0198)";
        :>> createdAt = "2026-09-01"; :>> createdBy = "claudeOpus5";
        :>> method = VerificationMethod::inspect;
        :>> procedureText = "Their selection, verbatim from the returned digest. Tab 'Collapse the CLI?', question 'Do I collapse the 43-command lens family into one router?': [x] 'Yes, and cut the old names immediately - one clean break'. The UNSELECTED recommended option was 'Yes - keel show <lens>, all 43 names kept as declared aliases for a deprecation window - RECOMMENDED'; the third was 'No - cement the 90 in the ICD and leave the surface alone'. Their reinforcing note, verbatim, entered on the digest: 'remove cruft from CLI. tons of commands, when a smaller subset should do, and parentheticals embedded in descriptions. tighten it up - what core functional hooks do we need in the CLI? a lot of these seem to be variations of an idea cemented as separate cli hooks. and critique all descriptions to trim them down to the real root of what is being done and what a user needs to know to run it'. NOTED RATHER THAN CORRECTED: that note was entered in the SECOND tab's note field, which belongs to a different subject (the unaccepted Need). It repeats their earlier CLI instruction verbatim, so it is read as reinforcement of THIS tab's choice; it changed nothing about the Need, and that reading is recorded in unattendedCurrencyAcceptAttest1 as well so the same fact is not told two different ways in two places.";
    }

    part d0273AcceptR1 : TestResult { :>> id = "1c84f7a2-95e0-4b36-8d71-6ea0392fc5b8"; :>> outcome = VerdictKind::pass; :>> judgedAgainst = "ac8bdf6"; :>> judgedAt = "2026-09-01"; :>> judgedBy = "wweatherholtz"; }
    part d0273Attest1R1 : TestResult { :>> id = "2d95a8b3-06f1-4c47-9e82-7fb1403ad6c9"; :>> outcome = VerdictKind::pass; :>> judgedAgainst = "ac8bdf6"; :>> judgedAt = "2026-09-01"; :>> judgedBy = "claudeOpus5"; }
}
