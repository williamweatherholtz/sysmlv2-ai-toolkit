// D0346 (status: the `status` field below is the truth) — remainingCliFamilies: whether the remaining read-only and writer families collapse behind routers to reach D0273's promised count, or D0273 is amended to the number the lens collapse achieved
// Recorded via `keel record decision` (D0105 RMWX axis; issue054). Acceptance is a separate explicit
// human gate (method=confirmation, D0106): flip status + add the d0346Accept event on sign-off.
package Decision0346 {
    private import EngineElement::*;
    private import EngineWork::*;
    private import EngineVerification::*;
    private import EngineRelationships::*;

    // RESEARCH: Measured 2026-09-06 from the CLI facts (keel-cli/src/cli_facts.rs, the same rows .engine/cli/commands.sysml declares; guard cli-surface-declared PASS 105): 105 facts, of which 37 are `show` lenses and 68 are top-level verbs (3 deprecated channel verbs, so 65 live). By family - gating 13 verbs, 12 read-only (validate, check, check-engine, guard, gate, rules, audit, audit-history, audit-adherence, audit-ci-runs, assured, adoption-check; hook is the one tool); orientation 12, all read-only (orient, whats-next, status, show, view, item, arch, attestation, actor-trace, governing-version, reprocess-candidates, enforcement-report); authoring 10 writers (add-task, record, new, mint, append-result, append-gate-result, apply-review, record-measurement, snapshot-indicators, reverify); integration 8; governance 6; rendering 6 (4 read-only); distribution 6 (2 read-only); channel 6 (3 deprecated); knowledge 1. 34 of the 65 live verbs are read-only lenses that are not under `show`. D0273's consequences promised the visible verb count falls BELOW 25; the lens collapse (sprint 512) delivered 66 and the criterion was never derived from the measurement (issue338). Prior art in this tree: D0273 (the lens collapse and the 25), sprint 512's byte-equality baseline and D0067 transform shape, D0271 (the CLI surface is an authored fact - every command a CliCommand with family and effect), issue338 (the criterion is a wish with a number attached). Outside: git's porcelain/plumbing split keeps ~20 user-facing verbs over ~150 commands by nesting, and cargo keeps 30 by treating everything else as a plugin - both chose a small top level and a router, neither promised a number before counting.
    part d0346 : Decision {
        :>> id = "e0f2aebe-ee96-4ff1-be6c-1e3adfa8b7b5";
        :>> title = "remainingCliFamilies: whether the remaining read-only and writer families collapse behind routers to reach D0273's promised count, or D0273 is amended to the number the lens collapse achieved";
        :>> createdAt = "2026-09-06";
        :>> createdBy = "claudeOpus5";
        :>> status = DecisionStatus::accepted;
        :>> context = "D0273 promised the top-level verb count falls below 25 and the lens collapse delivered 66; issue338 records that the 25 was written without deriving it from the measurement it sat beside, and dcRemainingCliFamilies exists so the miss is decided rather than left standing as a criterion nobody revisits. The measurement above is the deciding fact: 65 live verbs, 34 of them read-only lenses outside show, and three families (gating 13, authoring 10, orientation 12) that are each one idea with many names. Either resolution is honest; only one of them is a second breaking change to a surface that hooks, CI workflows, downstream CLAUDE.md files and the human's own habits call by name, and D0273 does not authorise it on my initiative.";
        :>> decision = "OPTION A (collapse the remaining families): the 12 read-only gating verbs become `keel check <validate|engine|guard|gate|rules|audit|history|adherence|ci-runs|assured|adoption>` behind one router (13 to 2, hook stays); the 12 orientation lenses fold under `show` except orient, whats-next and status (12 to 3); the 10 authoring writers become `keel record <task|sprint|result|gate-result|review|measurement|indicators|reverify>` (10 to 2, mint stays); rendering's 4 read-only verbs fold under show (6 to 2); channel's 3 deprecated verbs are removed. Top level lands at about 28 live verbs plus show - the count is derived here, not promised, and the criterion becomes the number the transform reconciles to. COST: a second BREAKING change to the CLI surface within a month - every hook command in claude_surface.rs, .githooks, three CI workflows, keelw's callers, the downstream CLAUDE.md, every skill's command text, and the human's muscle memory, rewritten in one commit under a D0067 transform with byte-equality baselines per family as sprint 512 did (about 3 sprints); every downstream project on v0.3.1 meets the rename at its next migrate, and a release must carry compatibility aliases for one version or their hooks break silently - which is issue378's class again. OPTION B (amend D0273 to the achieved number): a superseding Decision states 65 live verbs after the lens collapse, withdraws the 25, and makes the criterion the one the transform actually reconciled; the `show` router stays the only collapse; the three deprecated channel verbs are removed at the next breaking release. COST: the top level stays wide - 34 read-only lenses outside show, three families that are one idea each under many names - and `keel --help` keeps needing family grouping to be readable; the promise D0273 made in prose is withdrawn rather than met, and hardening's helpCoverage.dispatched reads 65, which is the honest number but not the small one. OPTION C (collapse the gating family only): the 12 read-only gating verbs become `keel check <validate|engine|guard|gate|rules|audit|history|adherence|ci-runs|assured|adoption>`; orientation, authoring and rendering are left alone; the top level lands near 54. COST: the same breakage class as A on the MOST-CALLED verbs in the surface - validate, guard and gate are what every hook, every CI workflow, every skill's command text and the human's own habits invoke - for a quarter of A's consolidation; a project pays the rename cost once and still meets a wide top level afterwards, which is the worst of both. RECOMMEND B now, and A only as a release boundary decision: the surface was broken once this month, the downstream reports of the last two days are all about pinned projects meeting engine change underneath them, and a second rename lands on exactly those projects; the collapse is right in shape and wrong in timing until a release with aliases can carry it. What would change it: a v0.4.0 release being planned anyway, or the human saying the wide top level is the thing they trip on.";
        :>> rationale = "Why a fork and not a choice: D0273 said below 25 and the human accepted that number; withdrawing it is theirs to do, and performing a second breaking rename is not started on my initiative - the DoD says so in as many words. Why the measurement leads: the 25 was the defect (a number without its derivation), so the fork carries the derivation first and the options second. Why B is recommended: the cost of A falls on downstream projects, and this week's six GitHub issues were all downstream projects meeting the engine moving underneath them.";
        :>> consequences = "Whichever option is accepted, dcRemainingCliFamilies verifies that `keel hardening` helpCoverage.dispatched reads back the number the accepted Decision states. Under B a superseding Decision is recorded on acceptance and the three deprecated channel verbs are removed at the next breaking release; under A three sprints of measured consolidation follow with a compatibility-alias release plan first.";
    }

    // acceptance event (D0121 review-queue sign-off; D0066/D0106 — human-judged, not fabricated)
    verification d0346Accept : Test { :>> id = "0e0673a3-cf3f-46b6-9648-b308a70ab234"; :>> method = VerificationMethod::confirmation; :>> procedureText = "recorded from the decision brief copy-for-AI digest, their words verbatim: '- [x] Sign all eight ... (answers: d0337, d0340, d0343, d0344, d0345, d0346, d0355, d0356)'"; }
    part d0346AcceptR1 : TestResult { :>> id = "176d41b8-2a4e-4381-9367-afb31d156b61"; :>> outcome = VerdictKind::pass; :>> judgedAgainst = "50b2cdb"; :>> judgedAt = "2026-09-07"; :>> judgedBy = "wweatherholtz"; :>> createdBy = "claudeOpus5"; }
}
