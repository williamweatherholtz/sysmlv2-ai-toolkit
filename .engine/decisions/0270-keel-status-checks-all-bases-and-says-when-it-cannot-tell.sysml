// D0270 (status: the `status` field below is the truth) — keel status: every base in one screen, and 'I cannot tell' never renders as 'nothing to report'
// Recorded via `keel record decision` (D0105 RMWX axis; issue054). Acceptance is a separate explicit
// human gate (method=confirmation, D0106): flip status + add the d0270Accept event on sign-off.
package Decision0270 {
    private import EngineElement::*;
    private import EngineWork::*;
    private import EngineVerification::*;
    private import EngineRelationships::*;

    // #ProspectiveChange (D0070) - this Decision governs a process/schema change; the co-committed
    // change rides the process-change guard's hard lock.
    #ProspectiveChange part d0270 : Decision {
        :>> id = "0293d1a9-caad-4995-835a-5038d667eb58";
        :>> title = "keel status: every base in one screen, and 'I cannot tell' never renders as 'nothing to report'";
        :>> createdAt = "2026-08-31";
        :>> createdBy = "claudeOpus5";
        :>> status = DecisionStatus::accepted;
        :>> context = "Four decisions were adjudicated on the summary page (st062) and all four took the recommendation. One carried a NOTE that widened its scope beyond what I had proposed: 'I really want a full status output for state of everything including versioning, library update new processes, etc. a command I can run to check all bases.' I had proposed a unit-drift report. That is one line of what they asked for. Answering 'where does this project stand' previously meant running `version`, `library list`, `process show` per unit, `orient`, `open-issues` and `gh run list`, then comparing six outputs by hand - which is the friction itself, not the information. THE STOP-HOOK NAG WAS REMOVED IN THE SAME BREATH, and the two are connected. That hook appended a count of items waiting on the human to every turn and then prescribed how to look at them, branching on an env var as a proxy for whether they were at a terminal or on a phone. Their verdict: I cannot tell where they are reading, the proxy was never evidence, and the line carried almost no value even when correct. State is now something they ASK for and a decision page they are LINKED to - not a count appended to every message.";
        :>> decision = "`keel status [ROOT]` reports five sections, each with a verdict: ENGINE - the binary's version against the project's binding pin, naming SKEW explicitly since under skew writes and gates refuse. LIBRARY - units available versus installed here, listing what is BEHIND with its update command and what is AVAILABLE BUT NEVER IMPORTED, which is the 'new processes' half of their ask; plus the cache's age, because every line is as-of the last sync. MODEL - tracked files, guard count, violations and warnings. WORK - ready count, open issues, and the next item on the assessed frontier. CI - the verdict for the commit at HEAD. This is where the asynchronous CI surfacing they chose in the same digest lands: land records the push, and the next command reports what became of it. THE RULE EVERY LINE OBEYS, and the reason there are three states rather than two: 'nothing to report' and 'I CANNOT TELL' must never render the same. An unreachable library reports UNKNOWN, not zero drift. A commit with no run reports UNKNOWN, not passed. The closing line counts attention and unknown SEPARATELY.";
        :>> rationale = "WHY UNKNOWN IS A FIRST-CLASS STATE. A status screen exists to be trusted at a glance, which makes it the worst possible place for the pass-at-zero hazard this codebase has now caught four times - a guard scanning nothing and reporting PASS, a lens timing out and returning empty, a phantom directory gating green. Folding 'I could not determine this' into 'clean' would turn the one screen meant to be believed into a comfort blanket. Held by three probes that assert the UNKNOWN path specifically, not the happy path. WHY IT ONLY READS. No section syncs the library, migrates, or writes anything. A status command that changes what it reports cannot be run to find out where you stand. WHY NOT FOLD IT INTO orient. `orient` answers 'what should I work on next' for the AI following the frontier. This answers 'is anything wrong across versioning, distribution, honesty and CI' for a human deciding whether to intervene. Same tree, different question, different audience - merging them would make both worse.";
        :>> consequences = "One command replaces six. On this repository it immediately surfaced something I did not know: the library holds SEVEN units, two of which this project has never imported. The drift report task (dcLibraryStatusShowsDrift) is delivered by this, wider than its DoD asked. REMOVED: the stop hook's oversight advisory and the dead console probe it used. The turn boundary now speaks only when the model is dishonest. STILL PENDING and carried per D0269: nUnattendedCurrency has never been contested or accepted - it was not the subject of the fork they adjudicated, so it stays on the decision page rather than being treated as accepted by proximity.";
    }

    // acceptance event (D0121 review-queue sign-off; D0066/D0106 — human-judged, not fabricated)
    verification d0270Accept : Test { :>> id = "ca094f62-df01-465b-9c5c-4b24431cab3a"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0270AcceptR1 : TestResult { :>> id = "da513441-b75f-4d3d-a2f9-a047c3400f0e"; :>> outcome = VerdictKind::pass; :>> judgedAgainst = "4097751"; :>> judgedAt = "2026-09-01"; :>> judgedBy = "wweatherholtz"; }
}
