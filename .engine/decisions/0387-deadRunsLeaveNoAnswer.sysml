// D0387 (status: the `status` field below is the truth) — deadRunsLeaveNoAnswer: an instrument claims its artefact before it computes - a JSON answer carries its own completion and every reader checks it, a page or drawing is removed - so a run that dies leaves nothing that reads as current
// Recorded via `keel record decision` (D0105 RMWX axis; issue054). Acceptance is a separate explicit
// human gate (method=confirmation, D0106): flip status + add the d0387Accept event on sign-off.
package Decision0387 {
    private import EngineElement::*;
    private import EngineWork::*;
    private import EngineVerification::*;
    private import EngineRelationships::*;

    // RESEARCH: Sweep of 2026-09-08 over every instrument in this repository that writes a file: scripts/exec_brief/facts.py (decision-facts.json, atomic write at the END only - the issue399 defect), the five brief builders and rebuild_2026_09_08.py (the page, written at the end), .engine/tools/routing_probe.py (routing-investigation.json, at the end), .engine/tools/stpa_diagram.py --out (the SVG, at the end), keel suite (suite-receipt.toml, written after cargo returns - a killed run leaves the previous verdict), and the guard receipt (.keel/metrics/guard-receipt.toml), which already has the property by construction: receipt.rs:232-239 honours it only when its stored key equals the digest of every input, and record_green writes it only after a green run over an unchanged key, so a killed run's leftover is honoured only for inputs it genuinely answered. deck_inbox_record.py and check_templates.py print and write nothing.
    part d0387 : Decision {
        :>> id = "59cee4a2-fce6-4509-a0bd-e7616f0fabbc";
        :>> title = "deadRunsLeaveNoAnswer: an instrument claims its artefact before it computes - a JSON answer carries its own completion and every reader checks it, a page or drawing is removed - so a run that dies leaves nothing that reads as current";
        :>> createdAt = "2026-09-08";
        :>> createdBy = "claudeOpus5";
        :>> status = DecisionStatus::accepted;
        :>> context = "issue399: the computed-facts script raised partway through a run and exited non-zero; the previous run's JSON stayed on disk - valid, timestamped, with a tree SHA - and is the file the standing brief is built from. dcInstrumentsLeaveNoStaleArtifact asks that every artefact-writing instrument get the property that a run which cannot complete removes or unmistakably marks its previous output, and that the choice between writing the run's outcome INTO the artefact and deleting it be weighed and recorded, because a file that says it failed is more useful than no file only if every reader checks the field.";
        :>> decision = "NOT A FORK: the two shapes the item weighs are each right for a different kind of artefact, and both are adopted where they fit. An instrument CLAIMS its artefact before it computes anything. A JSON answer carries its own completion: scripts/artefact.py begin_json replaces the previous answer with a running stub, an uncaught exception rewrites it as failed with the error, finish_json is the only writer of complete true, and require_complete is the only way a reader obtains the answer - it refuses running, failed, half-written, absent, and pre-D0387 files alike. A page or a drawing, which cannot carry a field a publisher would read, is removed by claim before the run starts, so a dead run leaves nothing to publish. keel suite writes a receipt with outcome running before cargo starts, so a killed run leaves a stub that is not green and not counted.";
        :>> rationale = "An exit code lives in the shell and the artefact outlives it, so the artefact itself has to say whether the run that produced it finished. For JSON the outcome written into the file is strictly more useful than deletion - the failed state carries the error, and a killed run is distinguishable from one that never ran - but only because the reader's single entry point checks the field; making require_complete the only reader is what makes that condition hold rather than hoping it does. For pages and drawings there is no reader that checks a field - the Artifact tool publishes whatever file exists - so the only honest shape is absence. The suite receipt already had an outcome field, so the running stub extends the vocabulary it had rather than adding a second file.";
        :>> consequences = "scripts/artefact.py exists with its probe (killed, raised, finished, pre-D0387, absent, claimed); facts.py claims decision-facts.json first and writes complete last, and treats a running suite receipt as no count; the six builders read facts through require_complete and claim their page; routing_probe.py and stpa_diagram.py remove their previous output at the start; suite.rs writes the running stub and land_refusal names it. Shown per instrument on 2026-09-08 by killing or breaking each and reading what it left. The probe runs by hand, like textpatch's, until dcScriptProbesRunInCi lands.";
    }

    // acceptance event (D0121 review-queue sign-off; D0066/D0106 — human-judged, not fabricated)
    verification d0387Accept : Test { :>> id = "d1fdac78-b16d-405c-9011-87b0c200680e"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0387AcceptR1 : TestResult { :>> id = "79f14322-cd2d-4b78-aa72-97959520fcaf"; :>> outcome = VerdictKind::pass; :>> judgedAgainst = "e0acb56"; :>> judgedAt = "2026-09-08"; :>> judgedBy = "wweatherholtz"; :>> createdBy = "claudeOpus5"; }
}
