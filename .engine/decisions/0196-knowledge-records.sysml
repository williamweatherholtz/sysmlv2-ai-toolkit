// D0196 (PROPOSED — NOT YET ACCEPTED) — D0196: generated knowledge becomes a tracked, replication-grade record - vanilla-SysML-first, version-pinned, edge-traced
// Recorded via `keel record decision` (D0105 RMWX axis; issue054). Acceptance is a separate explicit
// human gate (method=confirmation, D0106): flip status + add the d0196Accept event on sign-off.
package Decision0196 {
    private import EngineElement::*;
    private import EngineWork::*;
    private import EngineVerification::*;
    private import EngineRelationships::*;

    // #ProspectiveChange (D0070) - this Decision governs a process/schema change; the co-committed
    // change rides the process-change guard's hard lock.
    #ProspectiveChange part d0196 : Decision {
        :>> id = "56ca28ae-ecfe-4919-8b95-65c38462f1a0";
        :>> title = "D0196: generated knowledge becomes a tracked, replication-grade record - vanilla-SysML-first, version-pinned, edge-traced";
        :>> createdAt = "2026-08-22";
        :>> createdBy = "claudeFable5";
        :>> status = DecisionStatus::accepted;
        :>> context = "The human, on receiving the panel-consensus report, verbatim: 'keep this report, and others, as relevant knowledge generated and link with proper traceability to processes and their items. is this doable in vanilla sysmlv2? if so, please do so... i'd like to know the processes used, the versions of those processes (we have grandfathering, correct?) etc. - anything that could be used to replicate'. Today a process run's knowledge lives scattered: the final artifact as a doc file, verdicts in sprint prose, outputs as issues - nothing binds them into one queryable record naming the process and the VERSION of the process that produced them.";
        :>> decision = "(1) A knowledge record per generated-knowledge event, at .tracking/knowledge/<slug>.sysml: the run is a verification Test item with method=analyze whose procedureText carries the REPLICATION BLOCK - the process used, the process definition's version pin (the last commit touching the def file at run time, the same judgedAgainst idiom evidence already uses), the deploying skill, the governing Decision, the roster/inputs, round-by-round outcomes, and the preserved artifact paths; per-round TestResults pin their judgedAgainst SHAs. (2) Traceability is EDGES, vanilla-first per D0139: plain base-SysML dependency statements from the run record to the process action, the governing Decision, the executing sprint story, and every produced item - engine markers only where an existing lens computes over them. (3) The adversarial-panel-review process's aprRecord step gains this output (the process edit rides this Decision's D0070 marker); other knowledge-producing processes adopt the same shape as they recur (D0040). (4) VANILLA BY PROOF, not assertion: knowledge files use only base constructs (part and verification instances, attribute redefinition, plain dependency) and are checked through the kernel conformance lane where the kernel is available - the conformanceIndicator tracks the residue. (5) GRANDFATHERING, confirmed and stated: a record pins the def version it ran under; a later process supersession never invalidates it - governing-version resolves each item's governing definition per its charter or pin (D0068), reprocess-candidates propagates re-evaluation obligations forward (K10), and new obligations never retro-fail work correct when written (issue068). The pin makes the existing machinery answer which-version-produced-this for knowledge exactly as it does for evidence.";
        :>> rationale = "Invariants 1 and 2 already forbid the alternative (a prose knowledge-base document): atomic items plus typed edges are the repo's one shape for facts that must stay queryable, and the Test/TestResult form means knowledge records ride EVERY existing lens - drift suspicion, evidence resolvability, edge-endpoint checking - for free. Vanilla-first honors the human's portability question with a checkable answer instead of a yes.";
        :>> consequences = "IF ACCEPTED: .tracking/knowledge/ exists with the panel run as its first record; aprRecord's actionText names the output; future runs are one authored file each. COST: one more file per knowledge event, and the replication block is prose a reader must trust - mitigated by pinning every claim to SHAs and paths a reader can check. AUTHORING NOTE recorded for honesty: the first recording attempt of this very Decision was mangled by shell backtick substitution and re-recorded pre-commit - the transcription-defect class the replication blocks must guard against by quoting paths, never live syntax. REMOVAL PATH: delete the directory and the aprRecord sentence; nothing else reads them.";
    }

    // acceptance event (D0121 review-queue sign-off; D0066/D0106 — human-judged, not fabricated)
    verification d0196Accept : Test { :>> id = "bb2bd0cd-f206-42a5-b9f1-7fd649cb385e"; :>> method = VerificationMethod::confirmation; :>> procedureText = "Their words, verbatim: 'keep this report, and others, as relevant knowledge generated and link with proper traceability to processes and their items... if so, please do so' - an explicit, specific direction for exactly this convention, given in the same message that accepted D0194/D0195. Re-recorded once pre-commit (the first attempt's text was corrupted by shell substitution; nothing had been committed); this acceptance covers the clean text."; }
    part d0196AcceptR1 : TestResult { :>> id = "07e967be-bdc0-465d-a09a-737d916422c6"; :>> outcome = VerdictKind::pass; :>> judgedAgainst = "5207cbc"; :>> judgedAt = "2026-08-22"; :>> judgedBy = "wweatherholtz"; }
}
