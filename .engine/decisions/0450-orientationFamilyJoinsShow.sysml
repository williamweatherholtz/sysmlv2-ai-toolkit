// D0450 (status: the `status` field below is the truth) — orientationFamilyJoinsShow: the eleven read-only orientation verbs become lenses of keel show, each keeping its word; the top-level names are removed in the same commit as their call sites
// Recorded via `keel record decision` (D0105 RMWX axis; issue054). Acceptance is a separate explicit
// human gate (method=confirmation, D0106): flip status + add the d0450Accept event on sign-off.
package Decision0450 {
    private import EngineElement::*;
    private import EngineWork::*;
    private import EngineVerification::*;
    private import EngineRelationships::*;

    // RESEARCH: Measured 2026-09-11 against .engine/cli/commands.sysml and keel-cli/src/main.rs at 1419069 (re-runnable census over the CliCommand facts and a grep for keel followed by a family verb). The orientation family holds twelve facts, all reads and stable: show and the eleven this Decision folds - orient, whats-next, status, view, item, arch, attestation, actor-trace, governing-version, reprocess-candidates, enforcement-report. Call sites of the eleven outside target/: engine-authored surface 60, .claude generated 15, root docs 54 (CLAUDE.md, README, docs, scripts), Rust source 44, Rust tests 49, .engine/decisions 55 and .tracking 265 (the last two not rewritten: a record names the commands that existed when it was written). orient alone has 72 files naming it and status 46; the Rust source count for status is mostly the JSON field of that name, not dispatch, so the Rust rewrite is by hand against the dispatch and the test fixtures, not by the transform. keel show hardening helpCoverage.dispatched reads 72 before any fold and 69 after the rendering fold of D0449.
    // #ProspectiveChange (D0070) - this Decision governs a process/schema change; the co-committed
    // change rides the process-change guard's hard lock.
    #ProspectiveChange part d0450 : Decision {
        :>> id = "4e214af0-13e2-4310-affc-b5b3815e1d16";
        :>> title = "orientationFamilyJoinsShow: the eleven read-only orientation verbs become lenses of keel show, each keeping its word; the top-level names are removed in the same commit as their call sites";
        :>> createdAt = "2026-09-11";
        :>> createdBy = "claudeOpus5";
        :>> status = DecisionStatus::accepted;
        :>> context = "d0399 option A, the human's own word on 2026-09-11, folds five CLI families into their routers in the sprint 512 shape (D0273): a D0067 transform, a byte-equality baseline captured from the pre-fold binary, call-site rewrites in the SAME commit, no alias window. keel show already routes 40 lenses by name and lists them when called alone; the eleven orientation verbs are read-only answers about the tree that differ from a lens only in having kept a top-level name, and three of them - orient, whats-next, status - are the commands CLAUDE.md section 2 tells every session to type first. This Decision fixes the mapping so the transform has a stated target and the reader of keel --help finds every read-only answer under one verb.";
        :>> decision = "The eleven read-only orientation verbs join keel show as lenses, each keeping its own word as the lens name and its own arguments unchanged: keel orient [ROOT] [--html] becomes keel show orient [ROOT] [--html]; whats-next, status, item <name>, view <name>, arch <sub>, attestation, actor-trace <actor>, governing-version <item>, reprocess-candidates and enforcement-report likewise become keel show <word> with the same trailing arguments. The eleven top-level names are REMOVED from the dispatch, from COMMAND_NAMES and from cli_facts.rs; their CliCommand facts change family to lens and invocation to the show form, the way the 40 lenses were recorded under D0273, and LENS_NAMES grows by eleven. Each arm is MOVED verbatim into cmd_show, its function untouched, and the criterion is byte equality against outputs captured from the pre-fold binary for every verb and argument shape the tree exercises. Every call site under .engine (skills, processes, docs, contracts, views, tools), .claude, the root docs including CLAUDE.md section 2, the Rust source and tests is rewritten by the committed transform or by hand in the one commit that removes the names; .engine/decisions and .tracking are not rewritten. NOT A FORK: d0399 option A chose the course; this Decision states the mapping that course lands on for one family.";
        :>> rationale = "A lens and a read-only verb are the same thing with two spellings, and D0273 already said so for forty of them; keeping eleven more as top-level names because they are typed often is the half-connection D0273 named. Each verb keeps its word because the word is the vocabulary every skill and every Decision already uses - orient means orient - and a rename on top of a fold would be two breaking changes sold as one. The names are removed rather than aliased under D0273's own rule: an alias window is a tree in which a skill names a command that will disappear, and no gate reads a deprecation. Byte equality is the criterion because a consolidation that changes an answer is a rewrite wearing a rename's clothes.";
        :>> consequences = "One sprint, five points, the largest of the three non-safety families by call sites: the transform under .engine/tools/migrations/ with a dry run that reconciles counts before --apply, the dispatch, cli_surface and cli_facts edits by hand, the Rust test fixtures rewritten by hand, and the byte comparison against the captured baseline. keel show hardening helpCoverage.dispatched falls by eleven and the sprint's implement gate reads the number back. CLAUDE.md sections 2, 4 and 5 and guards.md name the new spellings in the same commit; keel sync-claude regenerates .claude from the rewritten skills. The human's first three commands of every session gain one word each - keel show orient, keel show whats-next, keel show status - which is the cost d0399 A priced and accepted. Downstream projects holding skills that name these verbs must update engine and skills together, which the D0252 clause A handshake makes visible by name.";
    }

    // D0303 layering: the mapping for one family under the program d0399 option A chose
    #DependsOn dependency from d0450 to d0399;

    // acceptance event (D0121 review-queue sign-off; D0066/D0106 — human-judged, not fabricated)
    verification d0450Accept : Test { :>> id = "525832f8-a741-4f86-92d5-0aac2538e15c"; :>> method = VerificationMethod::confirmation; :>> procedureText = "PLAN-COVERED under d0399 step 'the read-only orientation verbs join show': the human signed the plan itself and this enumerated step does not re-ask (D0375 option C / D0396). The plan's judge: wweatherholtz."; }
    part d0450AcceptR1 : TestResult { :>> id = "2dbdcf30-8ac7-434a-b148-cffeee68d07f"; :>> outcome = VerdictKind::pass; :>> judgedAgainst = "1419069"; :>> judgedAt = "2026-09-11"; :>> judgedBy = "wweatherholtz"; :>> createdBy = "claudeOpus5"; }
}
