// D0355 (status: the `status` field below is the truth) — decisionIsPresentedAsAnArguableChange: the decision surface's content contract is replaced so a reader meets a change with its mechanism, its state, its competing forces and its load-bearing claims, and every number on the page is computed rather than typed
// Recorded via `keel record decision` (D0105 RMWX axis; issue054). Acceptance is a separate explicit
// human gate (method=confirmation, D0106): flip status + add the d0355Accept event on sign-off.
package Decision0355 {
    private import EngineElement::*;
    private import EngineWork::*;
    private import EngineVerification::*;
    private import EngineRelationships::*;

    // RESEARCH: Three-panel review, 2026-09-06, all measured against this tree. EXTERNAL PRACTICE: the current contract is IBIS-shaped - a position with pro and con arguments hanging off it - which presents the reader with exactly one contestable object, so the only acts it affords are accept and defer; that is a property of the notation, not of the author's diligence. The replacement is QOC-shaped (MacLean et al., Design Space Analysis, HCI 6:3): criteria crossed with courses, each cell independently disputable. Nygard's original ADR required the forces at play to be called out AS being in tension, a clause every later template dropped in favour of a flat driver list. Rust's RFC template mandates both a guide-level and a reference-level mechanism section, a drawbacks section that names what becomes impossible rather than what costs money, and the impact of not doing the thing at all. Amazon's memo practice bans bullets on the ground that a bullet asserts a relationship the reader cannot audit; Bezos's one-way versus two-way door sets how much scrutiny a change deserves before it is read. Klein's premortem raises correct identification of failure causes by about thirty percent. Kepner-Tregoe's weighted scoring was REJECTED: a weight is itself an unsourced claim and laundering judgment into a total shrinks the disagreement surface; its binary musts were kept. MEASURED HERE: 4 of the 8 items on the published page already ship in the binary, each Decision's own consequences saying so, so the only act left on them is revert and no panel priced one; 0 of 5 panels offered a status-quo course; 2 of 12 course costs carried a quantity; 24 record ids appear in 14 of 80 reader-facing sentences, every one standing in for a quantity that was never computed; three of five figures in one diagram were wrong within a day of publication (105/68/34 typed against 106/69/33 authored) and one claim was simply false (the release workflow was said not to have run; it ran green on 2026-08-29 and cut the current release); 86 Decisions were written in seven days of which 61 carry a marker, so the page's 'roughly one Decision per sprint' understated the consent queue by an order of magnitude; and of the eight pending items, three state a flip condition nothing in the tree can observe. Prior art in this repository: issue234 (2026-08-23) is the same complaint one surface earlier and its fix rendered the Decision's own context and decision text, which is the administrative prose now rejected; D0215 forbids typing a computable number into a doc surface; the stpa-diagram rules already require ortholinear routing, labelled edges and computed rather than drawn figures, and all three of the page's diagrams violate them.
    // #ProspectiveChange (D0070) - this Decision governs a process/schema change; the co-committed
    // change rides the process-change guard's hard lock.
    #ProspectiveChange part d0355 : Decision {
        :>> id = "e2cfcb39-3cd7-48b8-93a4-09859d8e3ac3";
        :>> title = "decisionIsPresentedAsAnArguableChange: the decision surface's content contract is replaced so a reader meets a change with its mechanism, its state, its competing forces and its load-bearing claims, and every number on the page is computed rather than typed";
        :>> createdAt = "2026-09-06";
        :>> createdBy = "claudeOpus5";
        :>> status = DecisionStatus::accepted;
        :>> context = "The owner's verdict on the report published this morning, verbatim (st099): 'context is very lacking. these decisions aren't grappling strongly enough with the implications of these decisions, mostly just administrative justification for the decision. I think the skill needs to be reworked - a decision isn't really to accept A decision or B decision - i need to understand the implications and real technical changes much better. and the diagrams are so weak today.' And, correcting my first diagnosis (st100): 'it's not a citing issue - it's a logical clarity issue. there are already too many things that are referenced.' The page took its unit of presentation from the governance artifact - a record awaiting a signature - so every field argued for the request rather than describing the change: the contract has no field that says what changes, one criterion field where a set of competing pressures is needed, a single confidence adjective attached to the conclusion, and a cost budget of fourteen words that cannot hold a quantity and a causal path together. issue234 recorded the same complaint on the deck card in August and its fix added more of the record's own prose, which is why it returned.";
        :>> decision = "The content contract for the exec-summary decision surface is replaced: a decision reaches the reader as a CHANGE it can argue with rather than a request it can only approve, carrying its mechanism as prose that states what happens before and after and names a real artifact, its current state - whether the change already ships and what reversing it would cost - a status-quo course scored like every other course, the competing pressures as measured consequences each pointing at the course it favours with at least one pointing away from the recommendation, its load-bearing claims each with the basis that supports it and the observation that would falsify it, and what the change makes impossible later as distinct from what it costs now; every number in reader-facing prose is emitted by the builder from a computed facts block rather than typed, no record id appears in any reasoning field or diagram label, a diagram carries two states or is not drawn, and the checker enforces each of these shapes so a report that does not hold them cannot be delivered. NOT A FORK: the owner directed the rework, and each field's shape follows from a measured finding rather than from a choice between courses.";
        :>> rationale = "Why the unit of presentation changes rather than the wording: the notation, not the prose, is what limited the reader to accept-or-defer, and one contestable object per decision is a structural property of the IBIS shape the template inherited. Why a state chip: half the queue was already built, so the honest ask on those items was to price a revert, and a page that presents a fait accompli as a choice teaches the reader to stop reading. Why forces as measured consequences and not as citations: the owner's own correction - the references were already too many, and every id on the page stood in for a quantity nobody had computed. Why numbers must be computed: three of five figures in one diagram were wrong within a day, and this project already decided that a computable number may not be typed into a doc surface. Why claims carry a basis: a single confidence line leaves nothing to disagree with, while a claim resting on nothing measured is the one a reader should attack first. Arming: each shape lands as a rule in the contract checker the surface already runs on every build, and the harness runs over a report built to the new contract.";
        :>> consequences = "Every future decision report costs more to write - a mechanism paragraph and a claims ledger per decision cannot be composed from the record's own prose - and that is the intended trade of author effort for reader judgment. Reports become rebuildable rather than re-composable, because their numbers come from lenses. Three of the eight pending items will read differently once their state chip says the change already ships. Two findings this contract does NOT fix, recorded rather than absorbed: three pending items state a flip condition nothing in the tree can observe, and although 31 typed edges do run from a Decision to a Need or UseCase, they sit in two old clusters and no Decision recorded in the last year carries one, so the report cannot show which stated demand a recent change strains - the panel was explicit that inventing those edges would produce citations, which is what the owner asked to stop.";
    }
    #DerivedFrom dependency from d0355 to st099;

    // acceptance event (D0121 review-queue sign-off; D0066/D0106 — human-judged, not fabricated)
    verification d0355Accept : Test { :>> id = "da0a803b-c54d-4f7b-a927-a214f0a2c360"; :>> method = VerificationMethod::confirmation; :>> procedureText = "recorded from the decision brief copy-for-AI digest, their words verbatim: '- [x] Sign all eight ... (answers: d0337, d0340, d0343, d0344, d0345, d0346, d0355, d0356)'"; }
    part d0355AcceptR1 : TestResult { :>> id = "cf0ee829-0191-4987-9ab6-4ee42465e6f2"; :>> outcome = VerdictKind::pass; :>> judgedAgainst = "50b2cdb"; :>> judgedAt = "2026-09-07"; :>> judgedBy = "wweatherholtz"; :>> createdBy = "claudeOpus5"; }
}
