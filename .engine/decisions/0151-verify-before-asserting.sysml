// D0151 — ACCEPTED (wweatherholtz, 2026-08-15): a defect is not claimed until it is verified, and
// the claim names the check. Response-contract change (§3a) — sign-off is the d0151Accept event below.
package Decision0151 {
    private import EngineElement::*;
    private import EngineWork::*;
    private import EngineVerification::*;
    private import EngineRelationships::*;

    #ProspectiveChange part d0151 : Decision {
        :>> id = "9a3e7c48-1d60-4b25-8f07-3c91e5a2b6d4";
        :>> title = "D0151: verify before asserting — an unverified suspicion is never stated as a defect";
        :>> createdAt = "2026-08-15";
        :>> createdBy = "claudeOpus5";
        :>> status = DecisionStatus::accepted;
        :>> context = "Raised by wweatherholtz, 2026-08-15, verbatim: 'why is all the reporting seemingly so unsettled? every other chat I see oops I thought it was a problem but it wasn't, etc. what's the deal? how to tighten this up? am I wrong'. THEY ARE NOT WRONG, AND THE DATA SPLITS CLEANLY. Of 20 Issues recorded that day, ZERO were later dismissed or superseded — the MODEL holds no false findings, because recording one must pass validate and 33 guards. But roughly six false claims were made TO THE HUMAN in conversation and then retracted within a turn or two: two 'schema mismatches' that were artifacts of a throwaway extractor which knew five of the seven `def` kinds and keyed enum bodies by a first-line match; `verifiedByMethod` reported as returning None when it is emitted at the top level of the same JSON; the claim that `keel serve` must exist before its requirements could be verified, when 72 of this repo's SR verifications are `method=critique` and need no implementation at all; an orphan Story offered as a quick fix when two prior sprints had deliberately refused to fix it and said so in the file; `pendingAcceptances` read as empty from a wrong key. EVERY ONE was caught by verification — the control working — but the human watched the catching, because the claim was published before the check ran. The engine gates what reaches the model and nothing gates what is said about it.";
        :>> decision = "ACCEPTED: add a clause to the response contract in `.claude/output-styles/keel.md`, which is where the contract lives (D0130 — CLAUDE.md was demonstrably ignored, issue084/085). TWO PARTS. (1) An unverified suspicion is either SILENT or explicitly labelled as unverified — 'checking whether X' — and is never stated in a conclusion's grammar as 'X is broken'. The verification happens BEFORE the claim, not after it. (2) A defect claim made to the human NAMES THE CHECK that established it — the command run or the `file:line` read — exactly as §3 already requires for a claim about code. Part (2) is what makes the rule auditable by a reader who cannot have it machine-checked: a claim carrying its own evidence can be re-run, and a claim that names no check is visibly a suspicion.";
        :>> rationale = "WHY THE OUTPUT STYLE AND NOT A GUARD, stated plainly because the honest answer is uncomfortable: NO GATE CAN READ CONVERSATIONAL OUTPUT. Every other clause in the contract has a control behind it — the Stop hook, 33 guards, the edit gate — and this one has none. It is a stated rule plus the human noticing, which is the same category as the commit-gate bypass disclosed earlier the same day, and it should be labelled as such rather than presented as equivalent to an enforced rule. That is precisely why part (2) exists: naming the check does not enforce the rule, but it makes a violation VISIBLE in the sentence itself. WHAT IS NOT BEING CHANGED, deliberately: the underlying investigation. Presenting a hypothesis is not the fault; presenting it in a conclusion's grammar is. The same exploratory work found a 1287-violation downstream lockout and disproved a documented exclusion mechanism by two-clone test, and a rule that discouraged looking would cost far more than the retractions do. ALTERNATIVES CONSIDERED: (i) do nothing, since the model is already correct and only prose is affected — REJECTED, because the human acts on the prose, and a report that must be discounted is worth less than a slower one that need not be; (ii) never narrate work in progress, report only conclusions — REJECTED, it hides the reasoning the human has repeatedly used to correct the work, including this correction; (iii) require every defect claim to be recorded as an Issue first, so the gates apply — REJECTED, it would flood the issue set with unverified suspicions and degrade the one surface that is currently clean.";
        :>> consequences = "If ACCEPTED: the contract gains a clause; reports become slower to assert and quieter about dead ends; the risk is over-hedging, where everything is labelled provisional and the reader loses the signal that a claim is firm — which the naming-the-check requirement is meant to prevent, since a named check IS the firmness. Applied by dcVerifyBeforeAsserting. If REJECTED: the asymmetry stands — a model that cannot hold a false finding, reported by a narrator who can state one — and the human continues to absorb the cost by verifying my claims themselves, which is work they should not have to do. Tracked as issue134.";
    }

    // acceptance event (D0121 review-queue sign-off; D0066/D0106 — human-judged, not fabricated)
    verification d0151Accept : Test { :>> id = "6c888b7d-0e6d-431b-ab01-4f219dc7ebd1"; :>> method = VerificationMethod::confirmation; :>> procedureText = "wweatherholtz, 2026-08-15, verbatim: 'proceed'. Given in direct reply to the D0151 proposal message, which set out both parts of the clause (an unverified suspicion is silent or explicitly labelled, never stated in a conclusion's grammar; and a defect claim names the check that established it), stated plainly that NO GATE CAN READ CONVERSATIONAL OUTPUT so this clause alone among the contract has no control behind it, listed the three rejected alternatives including requiring every defect claim to be recorded as an Issue, and closed by stating that D0151 was the only item awaiting them. The human had raised the underlying problem themselves after observing repeated retractions across turns."; }
    part d0151AcceptR1 : TestResult { :>> id = "85a986cb-0688-4e0d-851a-383e13dbeabf"; :>> outcome = VerdictKind::pass; :>> judgedAgainst = "b82e777"; :>> judgedAt = "2026-08-15"; :>> judgedBy = "wweatherholtz"; }
    part d0151AcceptR2 : TestResult { :>> id = "4dea7f80-ae0e-48df-b95f-92b126287b51"; :>> outcome = VerdictKind::pass; :>> judgedAgainst = "eb0adcf"; :>> judgedAt = "2026-09-04"; :>> judgedBy = "wweatherholtz"; :>> createdBy = "claudeOpus5"; :>> notes = "REBOUND (D0308): AUTO-RE-BOUND under standing consent (D0207/D0308): decision wording PROPOSED to ACCEPTED at 1ba3c5c - editorial, the agreed substance unchanged. Their standing words, verbatim: 'issues raised are automatically accepted. they can be customizedly changed post-fact.'"; }
}
