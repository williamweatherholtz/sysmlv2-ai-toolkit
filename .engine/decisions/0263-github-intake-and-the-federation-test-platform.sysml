// D0263 (status: the `status` field below is the truth) — GitHub intake becomes a process, and nine federation claims get a suite that convicted the product twice
// Recorded via `keel record decision` (D0105 RMWX axis; issue054). Acceptance is a separate explicit
// human gate (method=confirmation, D0106): flip status + add the d0263Accept event on sign-off.
package Decision0263 {
    private import EngineElement::*;
    private import EngineWork::*;
    private import EngineVerification::*;
    private import EngineRelationships::*;

    // #ProspectiveChange (D0070) - this Decision governs a process/schema change; the co-committed
    // change rides the process-change guard's hard lock.
    #ProspectiveChange part d0263 : Decision {
        :>> id = "26901365-0bec-4af6-a029-b305420f6579";
        :>> title = "GitHub intake becomes a process, and nine federation claims get a suite that convicted the product twice";
        :>> createdAt = "2026-08-30";
        :>> createdBy = "claudeOpus5";
        :>> status = DecisionStatus::accepted;
        :>> context = "The human asked whether a NEW keel project actually works in a federation - seven questions, from numbering reset to whether the instantiated project confuses keel's purpose with its own - and specified the sequence: design a suite, panel-critique the design, implement, reapproach the panel with findings, with empirical evidence recorded at every step. Mid-work they added: a process and AI skill to ingest GitHub issues. The two are one story - ingestion is the INBOUND half of the upstream loop the first question asks about. RECONNAISSANCE ANSWERED TWO QUESTIONS BEFORE THE DESIGN EXISTED, and they disagreed. Numbering is fine: a fresh project allocates d0001 beside 261 ReferenceDecisionNNNN packages, duplicate-identity 361 scanned 0 violations - D0139/issue291's disjoint-prefix fix holds. Initialisation is not: at a 150-character parent path the shipped reference filenames reach 249 characters and `git add` fails, so the project cannot make its FIRST COMMIT (issue313). And the upstream issue path DID NOT EXIST - keel's entire GitHub surface was the decision channel.";
        :>> decision = "THE INGESTION PATH. `keel github-ingest` records a GitHub issue as a VERBATIM Statement, attributed to the reporter's GitHub LOGIN (not an enrolled actor - an outside reporter has none, and inventing one misattributes their words), carrying the issue URL as a new `sourceUrl` attribute which makes re-ingestion REFUSE inside the write lock. It records a Statement and NOT an Issue, for two reasons: a GitHub issue is someone's words and what they implicate is a judgment (D0216), and `record issue` requires a resolver that ingestion cannot know - an ingest-to-Issue path would have to invent one. `github` joins StatementChannel as a schema change through this Decision rather than a force-fit into `other`, because the intake process forbids exactly that force-fit. The githubIntake process and its skill carry the discipline: ingest, triage, route to a REAL resolver, and answer the reporter where they are standing. THE SUITE. Nine claims (D0262, as amended by its own panel), each with the observation that refutes it: first commit at four path shapes, numbering reset, namespace hygiene, a measurable vocabulary-leak check, library pickup, a downstream-authored unit reaching a sibling through an isolated library, the live upstream contract, verbatim idempotent ingestion, armed-not-merely-present controls, and migration when the engine moves underneath the project. THE PANEL RAN TWICE AND CHANGED THE WORK BOTH TIMES. Round 2 (pf41-pf45) returned four standing defeaters against the design, two UNSOUND: the eight original claims tested a project only at BIRTH, and the network policy would have reported green while never touching GitHub. F9 exists because of the first. Round 3 (pf46-pf50) assessed the built suite and returned a verdict WORSE than its predecessor on one lens: F3b's vocabulary check is a hand-picked list of four strings, which is the overfit lens applied to the measurability fix.";
        :>> rationale = "WHY THE PANEL EARNED ITS COST. F9 exists only because pf42 called the design unsound for testing the easy day, and F9 immediately found issue314 - `keel migrate` resyncing every shipped engine file over the project's copy, silently REVERTING a project's adoption choice. A project that deactivated a process had it switched back on by an engine upgrade; the same path can switch one off, which is an unsigned control change of exactly the kind the keystone lock exists to prevent, arriving through a path neither it nor audit-adherence watches. That defect was found by a claim that would not exist without the critique. WHAT THE FAILURES TAUGHT. Three of the suite's first-run failures were MY TESTS being wrong while the product was right: migrate refuses outside version control and refuses a dirty tree, both correctly, and F5 asserted on a title the command does not print. Recording that matters - a suite whose early failures are all product defects is usually a suite asserting what its author already believed. WHY INGESTION RECORDS WORDS AND NOT WORK. The alternative - a GitHub issue becoming a keel Issue directly - is what every other tracker does and it is wrong here for a reason this project has already paid for: my paraphrases drift, and the verbatim text is the only thing that cannot. The reporter's words now carry a URL a later reader can check the transcription against.";
        :>> consequences = "The engine gains a command, a process, a skill, a schema member and an attribute. The suite is a keel-cli integration binary; 11 cases pass, 430 tests overall, clippy clean. THREE DEFECTS FIXED IN THE COURSE OF BUILDING IT: issue313 (init now NAMES the path-limit risk and its remedy, since keel does not own the git repo and cannot set core.longpaths for it), issue314 (project-owned contracts are ADDED by resync, never overwritten - the rule is 'a keel COMMAND writes this file'), and issue315 (`record issue --description-from FILE`, after shell backticks in a description EXECUTED for the third time and injected tool output into issue314's own record while also running `keel deactivate` against this repository). STILL OPEN, named rather than implied: pf46's narrowing (a project at depth remains uncommittable and the suite records only that it was warned), pf49 (the manifest checks a case EXISTS, not that it RAN), and pf50 (the vocabulary list is hand-picked and must be derived).";
    }

    // acceptance event (D0121 review-queue sign-off; D0066/D0106 — human-judged, not fabricated)
    verification d0263Accept : Test { :>> id = "efe4535b-1dad-404b-b838-2bc589562a06"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0263AcceptR1 : TestResult { :>> id = "babafc0b-1394-4f50-8545-d4fda3c05018"; :>> outcome = VerdictKind::pass; :>> judgedAgainst = "000e461"; :>> judgedAt = "2026-08-30"; :>> judgedBy = "wweatherholtz"; }
    part d0263AcceptR2 : TestResult { :>> id = "9f9dc957-d447-4c92-a8c9-d3777772aa6d"; :>> outcome = VerdictKind::pass; :>> judgedAgainst = "eb0adcf"; :>> judgedAt = "2026-09-04"; :>> judgedBy = "wweatherholtz"; :>> createdBy = "claudeOpus5"; :>> notes = "REBOUND (D0308): AUTO-RE-BOUND under standing consent (D0207/D0308): rationale and consequences guard count renumbered 5 to 4 at 6583e08 - editorial, the agreed substance unchanged. Their standing words, verbatim: 'issues raised are automatically accepted. they can be customizedly changed post-fact.'"; }
}
