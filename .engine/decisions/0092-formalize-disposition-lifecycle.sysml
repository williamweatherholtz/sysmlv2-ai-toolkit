// =====================================================================
// D0092 — formalize-disposition-lifecycle: a human's disposition of a >= Medium
// finding (ACT / ACCEPT-RISK / DISMISS) becomes a FIRST-CLASS recorded judgment —
// a method=confirmation verification carrying a typed `disposition : DispositionKind`,
// #Dispositions-linked to the finding Issue — instead of prose in the issue
// description. Reuses the assurance substrate (D0079/D0080 economy): one mechanism
// (verification + TestResult + suspect + #edge), so dispositions inherit provenance,
// the write path, and STALENESS for free. The single human-judgment write path is
// `apply-review` (extended; D0086). Schema/core was unfrozen for ONE change (the
// DispositionKind enum + an optional Test.disposition attribute) and re-frozen after.
// Accepted 2026-06-22 by wweatherholtz (acceptance dialogue: "Accept as proposed" —
// schema-unfreeze sign-off + the disposition-as-confirmation-verification design).
// =====================================================================
package Decision0092 {
    private import EngineElement::*;
    private import EngineWork::*;
    private import EngineVerification::*;
    private import EngineRelationships::*;

    // D0070: this Decision changes the element-critique DISPOSITION process (prospective; existing
    // prose dispositions grandfathered, backfilled with recorded basis). Schema touch is bounded.
    #ProspectiveChange part d0092 : Decision {
        :>> id = "92a3b4c5-1d6e-4f70-a829-516273849592";
        :>> title = "D0092: formalize the finding-disposition lifecycle (typed ACT/ACCEPT-RISK/DISMISS verdict + one write path + computed view)";
        :>> createdAt = "2026-06-22";
        :>> createdBy = "wweatherholtz";
        :>> status = DecisionStatus::accepted;
        :>> context = "The human-disposition gate (>= Medium findings -> ACT / ACCEPT-RISK / DISMISS, D0079/D0080) was DOCTRINE-IN-PROSE with AD-HOC recording: the vocabulary lived only in decision text + the element-critique ecDisposition step; the three verdicts mapped to three different mechanisms (ACT -> #Resolves action; ACCEPT-RISK -> a confirmation TestResult; DISMISS -> a mooting Decision); and in practice the disposition was written as PROSE in the Issue description ('ACT disposition (human, date): ...'). There was no typed DispositionKind, no single write path, and no computed 'undispositioned' signal — `assured` inferred it via the finding_blockers PROXY (open >= Medium with no resolver), never reading a recorded verdict. For a near-complete engine whose most important recurring human act is JUDGING a finding, that is the weak UX/data surface. The human flagged it directly ('is ACT/ACCEPT-RISK/DISMISS formalized? best UX for when the engine is completed') and the sibling smell on issue039 ('straying into prose & bespoke data — could there be strong processes?'). The engine already has the right pattern for the SIBLING case: apply-review (D0086) formalizes REVIEW dispositions (accept/finding + rationale) as linked judgments via a write path.";
        :>> decision = "Make a finding disposition a FIRST-CLASS recorded judgment, reusing the assurance substrate (D0079/D0080 economy — one mechanism, not a parallel subsystem). SCHEMA (schema/core, human-accepted, re-frozen after): add `enum def DispositionKind { act; acceptRisk; dismiss; }`; add optional `attribute disposition : DispositionKind[0..1]` to `verification def Test`. MODEL: a disposition is a `method=confirmation` verification of the finding (the human's word IS the evidence, D0016) carrying `disposition`; rationale in procedureText; provenance (judgedBy/judgedAt/judgedAgainst) in its TestResult; linked to the finding Issue by a `#Dispositions` marker edge (schema-free). WRITE PATH: `apply-review` (D0086) is extended to accept act/acceptRisk/dismiss verdicts targeting a finding Issue (alongside accept/finding for elements) — ONE human-judgment round-trip. COMPUTED: 'dispositioned' = the finding carries a non-suspect #Dispositions confirmation; `assured` reads this typed verdict (retiring the finding_blockers proxy); issue resolution extends so ACCEPT-RISK/DISMISS CLOSE the obligation while ACT still requires its #Resolves resolver done. STALENESS: a disposition goes suspect when its finding changes after the disposition commit -> re-disposition (this IMPLEMENTS D0080's 'reopen accept-risk dispositions whose basis changed', previously prose). Backfill the recent prose dispositions (issue035..040) as typed records with recorded basis (migration discipline, D0067; never fabricated). issue039/issue040 then ride on this lifecycle (issue039 shrinks to 'an ACT'd process-defect's resolver is a guard' on a now-typed lifecycle, not a bespoke marker subsystem).";
        :>> rationale = "ALTERNATIVES: (A CHOSEN) disposition = a method=confirmation verification + typed DispositionKind + #Dispositions edge, write via apply-review — reuses TestResult provenance, the write API, suspect-staleness, and the human gate; minimal schema (1 enum + 1 optional attr, additive so every existing Test still parses); ONE judgment tool. (B) reuse with NO schema change — encode the verdict in confirmation procedureText by convention — REJECTED: untyped, unqueryable, re-introduces the prose smell this fixes. (C) a standalone Disposition part def + its own store/state — REJECTED: duplicates the verification substrate (the D0079 alt-B anti-pattern). (D) a new dedicated `sysmlv2 disposition` command — REJECTED in favor of extending apply-review (one human-judgment mental model + tool, D0086). CRITERIA: typed-not-prose x reuse-one-mechanism x additive-not-breaking x single-write-path(UX) x compute-don't-store(staleness falls out) x frozen-schema-minimal. The schema/core freeze (CLAUDE.md 2.5) was honored: ONE bounded human-accepted change, re-frozen after — mirroring the D0080 acceptance dialogue.";
        :>> consequences = "Milestone (chained): d0092Schema (DispositionKind enum + Test.disposition attr; kernel-validated; re-freeze) -> dispositionWritePath (extend apply-review to write a #Dispositions confirmation; a computed disposition/undispositioned view; retrofit `assured` + open-issues resolution to read the typed verdict) -> dispositionBackfill (issue035..040 prose -> typed records, recorded basis). Downstream: issue039 (correctionGuardCoverage) reframed onto the typed lifecycle; issue040 (sittingModel, #Covers edge) unaffected. CLAUDE.md 3c (confirmation/disposition) + the element-critique skill/process + usage.md updated by doc-sync as each step lands. schema/core RE-FROZEN after d0092Schema — any further change needs new sign-off. ROLLOUT: [2026-06-22] m1 dispositionSchema landed (21a3c5f); m2 dispositionWritePath landed — apply-review writes act/acceptRisk/dismiss as #Dispositions confirmations, `sysmlv2 dispositions` computes dispositioned-vs-not, `assured`+open-issues read the typed verdict (finding_blockers proxy retired), and the element-critique process/skill + CLAUDE.md + usage.md were doc-synced (this commit co-records the process-def change per the D0070 keystone).";
    }

    verification d0092Accept : Test { :>> id = "92a3b4c5-1d6e-4f70-b829-516273849592"; :>> method = VerificationMethod::confirmation; :>> procedureText = "wweatherholtz attests acceptance of d0092 (formalize the finding-disposition lifecycle: a disposition is a method=confirmation verification carrying a typed DispositionKind, #Dispositions-linked to the finding; apply-review is the write path; computed undispositioned view retires the finding_blockers proxy; staleness falls out of suspect; schema/core unfrozen for the DispositionKind enum + optional Test.disposition attr and re-frozen after) by selecting 'Accept as proposed' in the D0092 acceptance + schema-unfreeze dialogue on 2026-06-22."; }
    part d0092AcceptR1 : TestResult { :>> id = "92a3b4c5-1d6e-4f70-c829-516273849592"; :>> outcome = VerdictKind::pass; :>> judgedAgainst = "3126545"; :>> judgedAt = "2026-06-22"; :>> judgedBy = "wweatherholtz"; }
    part d0092AcceptR2 : TestResult { :>> id = "26e3ef6a-c10d-4881-9c62-fe811661c5f6"; :>> outcome = VerdictKind::pass; :>> judgedAgainst = "eb0adcf"; :>> judgedAt = "2026-09-04"; :>> judgedBy = "wweatherholtz"; :>> createdBy = "claudeOpus5"; :>> notes = "REBOUND (D0308): AUTO-RE-BOUND under standing consent (D0207/D0308): consequences gained a ROLLOUT note at 21a3c5f - editorial, the agreed substance unchanged. Their standing words, verbatim: 'issues raised are automatically accepted. they can be customizedly changed post-fact.'"; }
}
