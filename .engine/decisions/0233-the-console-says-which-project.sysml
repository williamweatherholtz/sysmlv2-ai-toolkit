// D0233 (status: the `status` field below is the truth) — whichProject: the console names the project it serves, in the browser tab, and can switch between them
// Recorded via `keel record decision` (D0105 RMWX axis; issue054). Acceptance is a separate explicit
// human gate (method=confirmation, D0106): flip status + add the d0233Accept event on sign-off.
package Decision0233 {
    private import EngineElement::*;
    private import EngineWork::*;
    private import EngineVerification::*;
    private import EngineRelationships::*;

    // #ProspectiveChange (D0070) - this Decision governs a process/schema change; the co-committed
    // change rides the process-change guard's hard lock.
    #ProspectiveChange part d0233 : Decision {
        :>> id = "e8c89914-52d8-4254-a779-1e4f95db25f8";
        :>> title = "whichProject: the console names the project it serves, in the browser tab, and can switch between them";
        :>> createdAt = "2026-08-25";
        :>> createdBy = "claudeFable5";
        :>> status = DecisionStatus::accepted;
        :>> context = "Reported while using it: keel serve does not indicate what project it is serving, and the author suggested that serving several local projects from one server - tabs - might be the better feature. Investigated before interpreting, and the finding changes the answer: the SERVER SIDE OF THAT FEATURE ALREADY EXISTS. /api/projects discovers every sibling keel project and names the active one - its own doc comment says it is the half of N-C4 that stops a supervisor wondering which project they are looking at - and POST /api/project switches, refusing a non-project rather than falling back. NOTHING RENDERED EITHER. So a capability shipped with no surface, which is the accepted-Decision-with-artifact- unbuilt class. Three concrete gaps: the startup banner printed the port and every endpoint and never the ROOT; the page title was the constant 'Keel console'; the header was the constant 'Keel . console'. The title one is the important one and answers the tabs question directly, because a browser TAB shows the page title - two consoles were indistinguishable in the tab bar for exactly that reason.";
        :>> decision = "The console names its project in three places. The startup banner prints the root before anything else. The page TITLE is '<project> . keel', substituted server-side so the tab is right on first paint and right even if the page's JavaScript never runs. The header carries a project badge whose tooltip is the full root, beside a switcher populated from /api/projects that POSTs to /api/project and reloads, hidden when only one project is reachable. A display_path helper strips the Windows verbatim prefix at every display site - the third place that needed it, so it is a function rather than a habit.";
        :>> rationale = "The author's instinct that one server for several projects is the better feature is RIGHT, and cheaper than they thought, because the hard part was already built - what was missing was the surface. It is also better for a reason beyond convenience: the console WRITES. Two identically-titled consoles means a Decision accepted into the wrong project, an attested fact in the wrong tree, and no way to notice. Labelling two servers would fix the confusion; one console with an unmistakable active project fixes the hazard, because the destination is visible at the moment of writing. Server-side substitution rather than a fetch is deliberate: a title that arrives after JavaScript runs is wrong exactly when the page is slow or broken, which is when a supervisor is most likely to be looking at the wrong tab.";
        :>> consequences = "Nine reachable keel projects were discovered on this machine, so the switcher is immediately useful and a select is the right shape for that number rather than tabs. A switch RELOADS instead of repainting, because a stale view beside a switched root is the confusion this exists to remove; a refused switch reports the reason and names the project still being served. STATED LIMIT: this is still ONE active project at a time, not several rendered side by side - the author's 'tabs' in the literal sense. That is now a UI question rather than a plumbing one, and it is deliberately not built here because a select over nine projects is a smaller surface than nine live panes and answers the reported pain. Verified against a running server rather than by reading: the banner names the root, the title reads 'sysmlv2-ai-toolkit . keel', a POST switch flips it to 'Penumbra . keel', C:/Windows is REFUSED with the active project unchanged, and switching back restores it. Resolves issue268.";
    }

    // acceptance event (D0121 review-queue sign-off; D0066/D0106 — human-judged, not fabricated)
    verification d0233Accept : Test { :>> id = "4774eb8e-c6e0-44a9-a452-5061d24dee71"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0233AcceptR1 : TestResult { :>> id = "5030eee1-b616-4c81-a46c-32e0ef5132fd"; :>> outcome = VerdictKind::pass; :>> judgedAgainst = "f81ffbe"; :>> judgedAt = "2026-08-25"; :>> judgedBy = "wweatherholtz"; }
}
