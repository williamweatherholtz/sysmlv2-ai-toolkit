// D0430 (status: the `status` field below is the truth) — idIsAUuid: an id written from today, or added in the working tree, is an RFC 4122 v4 UUID - the shape the write API emits - and guard id-is-a-uuid fails a typed one while counting the history once
// Recorded via `keel record decision` (D0105 RMWX axis; issue054). Acceptance is a separate explicit
// human gate (method=confirmation, D0106): flip status + add the d0430Accept event on sign-off.
package Decision0430 {
    private import EngineElement::*;
    private import EngineWork::*;
    private import EngineVerification::*;
    private import EngineRelationships::*;

    // #ProspectiveChange (D0070) - this Decision governs a process/schema change; the co-committed
    // change rides the process-change guard's hard lock.
    #ProspectiveChange part d0430 : Decision {
        :>> id = "1ab29ad4-26a6-4ad9-8065-634682c1654e";
        :>> title = "idIsAUuid: an id written from today, or added in the working tree, is an RFC 4122 v4 UUID - the shape the write API emits - and guard id-is-a-uuid fails a typed one while counting the history once";
        :>> createdAt = "2026-09-10";
        :>> createdBy = "claudeOpus5";
        :>> status = DecisionStatus::accepted;
        :>> context = "Section 1.3 says identity is an immutable UUID and control-map.sysml says every id is a well-formed v4 UUID enforced by guard identity-well-formed. The guard enforces 8-4-4-4-12 of [0-9a-z] and nothing more (guards.rs identity_well_formed), so on 2026-09-10 a verifier subagent hand-wrote six TestResults with ids such as eh5h6i7g-8f9e-0j1h-2i3d-4e5f6g7h8i9d, typed around the write API, and validate and every guard accepted them (issue454, in-field, High). The write API's gen_uuid emits v4 and every one of the 216 ids dated 2026-09-10 in the tree is v4, so the v4 shape is the fingerprint that separates an API-written record from a typed one. A block-aware census of the tree on 2026-09-10 (idscan655) found 5,515 hex-shaped ids that fail the version or variant nibble and 88 that are not hex, all dated before today or undated - 402 of the undated ones in .tracking, mostly backlog DoD Tests that carry no createdAt. An id is immutable, so none of those can be corrected, and a validate that refused them would be red over an honest tree (D0098).";
        :>> decision = "NOT A FORK: this makes an existing claim true and changes no severity of any existing control. A new forward guard id-is-a-uuid FAILS any item whose recorded date (judgedAt, createdAt, saidAt or acceptedAt) is on or after 2026-09-10 and whose id is not an RFC 4122 v4 UUID - 8-4-4-4-12 lowercase hex, version nibble 4, variant nibble in 89ab - and FAILS any id of that shape on a line ADDED in the working tree relative to HEAD, whatever its date or lack of one, because an id that did not exist at HEAD is new no matter what it says about itself. Every other id that fails the shape - dated before the cutoff, or undated at HEAD - is counted in one HISTORY line by class, hex-but-not-v4 apart from not-hex, and never enumerated (D0261). keel validate does not change: the cutoff and the diff are the guard's to read, and the 402 undated non-v4 ids already in .tracking are history, not a defect to refuse.";
        :>> rationale = "A date ratchet alone has the hole guard 36's first version had: a record that omits its date, or backdates it, walks through. Guard 38 answered that with an explicit grandfather list of 15, which cannot absorb a sixteenth; this class has 5,603 members and a list would be the migration nobody asked for. The working-tree diff closes the hole where it matters - the fabrication issue454 saw was staged, not committed, and a pre-commit guard reading the diff catches it before it becomes history - while the date clause covers what was committed after today on a clone whose diff is empty. Counting the history by class keeps the number honest: the 5,515 hex-not-v4 ids are v5s and sequence-shaped ids that were never typed by hand, and the 88 not-hex ones are the mnemonic suffixes and the earlier typed ones; conflating them would hide the class this guard exists for. validate stays as it is because a gate that fails an honest tree teaches bypass (D0132/issue081), which is a worse outcome than a typed id.";
        :>> consequences = "guards.rs gains id_is_a_uuid and a view function that classes every id from the model; GUARD_NAMES grows by one and keel version reports the count - doc-guard-count keeps the number out of prose; guards.md gains the row; control-map.sysml gains gIdIsAUuid anchored to ehz6 beside gIdentityWellFormed, whose statement claimed v4 before anything checked it - that record belongs to another actor and is left as written, with this constraint stating what is now enforced. A record written around the API from today on fails the commit gate on its id alone; a record written through the API is unaffected. STATED RESIDUAL: a typed id that happens to satisfy the v4 nibbles passes - the check is a fingerprint, not a proof of authorship; the ledger of API writes (D0424) is the proof, and this guard is the cheap first filter. Removal: delete the guard, its row and gIdIsAUuid; nothing else depends on them.";
    }

    // acceptance event (D0121 review-queue sign-off; D0066/D0106 — human-judged, not fabricated)
    verification d0430Accept : Test { :>> id = "ee56fd9a-00d7-499d-bbec-416fba54f715"; :>> method = VerificationMethod::confirmation; :>> procedureText = "Selected on the decision brief copy-out (fifteenth publish), pasted into chat 2026-09-11: the set of 33 HELD process-change ratifications accepted with one word, this record being one member (D0406 named it in the table). No note added. - their words, verbatim: “Accept the set: each of the 33 rules named in the table is recorded accepted on its own, quoting these words (recommended)” WARN: read-back - the quoted words do not name d0430 (D0201 B); recorded as given (D0423)."; }
    part d0430AcceptR1 : TestResult { :>> id = "e9b021a9-c049-4466-9dbd-20c444684c67"; :>> outcome = VerdictKind::pass; :>> judgedAgainst = "3e6c518"; :>> judgedAt = "2026-09-11"; :>> judgedBy = "wweatherholtz"; :>> createdBy = "claudeOpus5"; }
}
