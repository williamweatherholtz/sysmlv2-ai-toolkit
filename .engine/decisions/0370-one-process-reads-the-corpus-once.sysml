// D0370 (status: the `status` field below is the truth) — oneCorpusPerProcess: a keel process opens each corpus file once and shares one model, validated by the file's own (len, mtime) on every read
// Recorded via `keel record decision` (D0105 RMWX axis; issue054). Acceptance is a separate explicit
// human gate (method=confirmation, D0106): flip status + add the d0370Accept event on sign-off.
package Decision0370 {
    private import EngineElement::*;
    private import EngineWork::*;
    private import EngineVerification::*;
    private import EngineRelationships::*;

    // #ProspectiveChange (D0070) - this Decision governs a process/schema change; the co-committed
    // change rides the process-change guard's hard lock.
    #ProspectiveChange part d0370 : Decision {
        :>> id = "cdf9bea4-3602-4886-8bd1-7d53b9168ad3";
        :>> title = "oneCorpusPerProcess: a keel process opens each corpus file once and shares one model, validated by the file's own (len, mtime) on every read";
        :>> createdAt = "2026-09-07";
        :>> createdBy = "claudeOpus5";
        :>> status = DecisionStatus::accepted;
        :>> context = "D0367 ranked the corpus-reopen and clone terms of issue409 third. After the guards ran in parallel (D0368) and the commit facts were cached (D0369), `keel guard` on this host still opened every `.sysml` file some 25,000 times - each of forty guards walked `.tracking`, `.engine` and `.knowledge` and read the corpus for itself, and every `Model::build` cache hit CLONED the whole item graph. On a Defender host the open is the cost: real-time scanning runs on the open, a metadata query does not. Measured on this tree, shell timer, same binary shape: `keel guard` 7176-8293 ms before, 4587-6523 ms after; `KEEL_PERF=1` reads `1951 file open(s) (23410 from corpus)` and `21 tree walk(s) (116 from memo)` after against 25,361 opens and 39 walks before; parse 1294 ms to 559 ms; stdout identical modulo the timing lines (66 PASS, 0 FAIL both sides). `keel orient .` 1847-2106 ms to 1554-1645 ms, stdout byte-identical. Sprint 598's retro named the class this design answers: a memo that was correct only because its callers happened to be serial.";
        :>> decision = "A new module `corpus` is the one read path for the corpus. `corpus::read_to_string(path)` stats the file on EVERY call and serves the cached text only when its (len, mtime) equal what was read and the mtime is at least two seconds old - git's racy rule, so a file rewritten inside one mtime tick is re-read rather than trusted; a missing file is the same error `std::fs::read_to_string` gives, never a stale hit. `collect_sysml` serves its remembered walk only while every directory it entered still carries the mtime it had, and never remembers a directory that did not exist. `Model::build` returns `Arc<Model>` so a cache hit shares the graph instead of copying it. Every read site in `guards.rs` and the model's own reads go through the corpus. The change DETECTOR - `fingerprint::compute` - walks with `collect_sysml_uncached`: the thing that detects change does not read a memo. Because `guards.rs` is under the keystone lock (D0209 clause 2) this is a #ProspectiveChange and waits for the human's word. NOT A FORK: this is the mechanism D0367 ranked third with its number, and a read-path swap changes no guard's logic - the corpus returns the bytes the file holds or the error the filesystem gives.";
        :>> rationale = "A cache is honest when its validity is a fact the cached thing carries, not a discipline its callers keep. The file's (len, mtime) is that fact for content, a directory's mtime is that fact for its entries, and the racy window names the one case where the fact is too coarse to trust and pays one open for it. The alternative that was refused is an invalidation the callers would have to remember - a `clear()` after every write - which is exactly the serial-callers assumption sprint 598 found and named. The change detector stays on the uncached walk for the same reason the cache exists: two mechanisms that both answer 'has anything changed' from the same memo can agree while both being wrong. Counting the opens unconditionally rather than behind `KEEL_PERF` is what lets the DoD's test read a receipt instead of a skipped assertion.";
        :>> consequences = "`keel guard` runs in about two-thirds of its wall time and `keel orient` gains a quarter; the remaining cost of `keel guard` on this host is `git x44 in 6.4-9.1 s` under parallel contention - the residual dcGateAnswersFromItsReceipt and dcGitReadsStayInProcess judge. The 61 reads in `guards.rs` that go through the corpus are unchanged in what they receive. Files read once per process outside `guards.rs` and the model (write paths, status, serve) stay on `std::fs` - a single read gains nothing from a cache. Sprint 600 records the numbers.";
    }

    // acceptance event (D0121 review-queue sign-off; D0066/D0106 — human-judged, not fabricated)
    verification d0370Accept : Test { :>> id = "860e7cd0-ef12-4307-83e6-cc144e2307b5"; :>> method = VerificationMethod::confirmation; :>> procedureText = "their words, 2026-09-08, the copy-for-Claude text of the published brief with their selections marked: '[x] Ratify: one read per process / [ ] Reverse it, read from disk each time / [ ] Discuss (answers: d0370)'"; }
    part d0370AcceptR1 : TestResult { :>> id = "b72e1786-1896-4723-b20a-e667d8c5504d"; :>> outcome = VerdictKind::pass; :>> judgedAgainst = "a08f2a1"; :>> judgedAt = "2026-09-08"; :>> judgedBy = "wweatherholtz"; :>> createdBy = "claudeOpus5"; }
}
