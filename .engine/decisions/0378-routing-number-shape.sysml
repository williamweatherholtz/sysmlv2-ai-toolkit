// D0378 (status: the `status` field below is the truth) — routingNumber: what the project buys from the skill-routing probe - a repeated sweep with variance, a stratified subset sampled repeatedly, or a diagnostic rig with no standing number
// Recorded via `keel record decision` (D0105 RMWX axis; issue054). Acceptance is a separate explicit
// human gate (method=confirmation, D0106): flip status + add the d0378Accept event on sign-off.
package Decision0378 {
    private import EngineElement::*;
    private import EngineWork::*;
    private import EngineVerification::*;
    private import EngineRelationships::*;

    // RESEARCH: Measured on this host and recorded in issue392 (2026-09-07): one probe run costs $0.47-0.59 and 25-70 s sequentially, 31 s per run at four-way parallelism; .engine/tools/routing_prompts.toml holds 47 prompts, one per deployed process, so one sample per skill is about $25 and three samples about $70 and an hour. Two of the four cases run twice on identical prompts changed verdict (release WRONG then ROUTED; doc-sync ROUTED then none). No routing threshold is declared anywhere (grep of .engine/contracts for routing: one controlNote, no trigger), so the number is an indicator under D0088 and D0363 classes its runs as samples, not measurements.
    part d0378 : Decision {
        :>> id = "87c8ad60-b3a4-41f2-bf16-0d6e4cc220cc";
        :>> title = "routingNumber: what the project buys from the skill-routing probe - a repeated sweep with variance, a stratified subset sampled repeatedly, or a diagnostic rig with no standing number";
        :>> createdAt = "2026-09-08";
        :>> createdBy = "claudeOpus5";
        :>> status = DecisionStatus::accepted;
        :>> context = "The routing probe (.engine/tools/routing_probe.py) runs a real model against one realistic request per process and reads the transcript for which skill was invoked. It works, and it showed that a single run is not a measurement: two of four verdicts flipped between identical runs minutes apart, with model sampling the only explanation left. A one-sample-per-skill sweep would have printed a coverage figure that looked authoritative, moved five or ten points on a re-run, and invited rewriting descriptions that were never broken. The rig can support a repeated sweep, a repeated subset, or one-off diagnosis; what it must not do is publish a one-sample number as if it were stable. Which of the three the project pays for is a spend decision, and the money is the human's. The resolver dcRoutingNumberIsStable waits on this answer; it is first on the frontier.";
        :>> decision = "OPTION A (repeated sweep): every run of the routing measure is three samples of all 47 prompts, reported as a routed rate with per-case sample count and disagreement beside it, never a bare percentage; declared as a Measure with determinism stochastic and its sample size and spend recorded next to the value. COST: about $70 and an hour per refresh, so it is refreshed on a schedule of weeks and reads stale between; two hours of work to add the sampling loop, the disagreement column and the Measure item. OPTION B (stratified subset): the same three-sample rule over a fixed subset - the twelve processes the frontier and the briefs invoke most, plus four rotated each run - so a refresh is about $18 and fifteen minutes; the published number covers the subset and says so, and a skill outside it is never scored. COST: the same two hours of work plus a declared subset that must be kept honest as skills come and go; a number that is not about the whole set and will be quoted as if it were. OPTION C (diagnostic rig, no standing number): the rig is kept for one-off diagnosis - when a skill is suspected of not routing, run three samples of that one prompt before and after any rewrite, and record those runs as evidence on the item that motivated them; dcSkillsRouteBehaviourally's criterion is amended to say no standing coverage number is published and why. COST: no whole-set view, ever, so a skill nobody suspects is never tested; half an hour to amend the criterion and add the --samples flag. OPTION D (as it stands): nothing is run and nothing is amended. COST: a High issue stays open at the head of the frontier with a resolver that cannot move, and the rig's one-sample sweep remains the only thing anyone can run.";
        :>> rationale = "WHY NOT DECIDE THIS AUTONOMOUSLY: every option except D spends the human's money on a recurring basis, and the amount and cadence are theirs to set. WHAT I RECOMMEND, AND WHAT WOULD CHANGE IT: OPTION C. No defensible threshold for share-of-skills-that-route exists, which is what made this an indicator rather than a requirement (D0088); a stochastic rate that costs $70 to refresh will be refreshed rarely, and a rarely refreshed indicator with no threshold is read once and then ignored, which is what happened to the turn-boundary count (D0359). What the rig has actually been useful for is the question it was built to answer about one skill at a time: does THIS description route, before and after THIS rewrite. C keeps that and refuses the number that would mislead. It flips to A if the project ever wants to compare its skill set across releases - then the whole-set rate is the point and its cost is worth paying on a release cadence - and to B if a cheaper standing signal is wanted and the subset is declared with the same care as the prompts. The stated residual under C: an unsuspected skill that does not route stays unfound until something goes wrong.";
        :>> consequences = "On A: routing_probe.py gains --samples with a default of three and a disagreement column; a Measure item with determinism stochastic, sample size and spend is declared and the indicator reads from it; a refresh schedule is declared and removable. On B: the same, plus a declared subset in routing_prompts.toml with its rotation rule, and a published number that names its coverage. On C: --samples is added, dcSkillsRouteBehaviourally's criterion is amended to withdraw the standing number, and the process for a suspected skill is three samples before and after, recorded on the motivating item. On D: issue392 and dcRoutingNumberIsStable stand as they are. In every case the resolver's own DoD holds: a re-run moves any published number by less than the amount that would change an action, or no number is published; and no skill is reported as not routing on a single sample.";
    }

    // acceptance event (D0121 review-queue sign-off; D0066/D0106 — human-judged, not fabricated)
    verification d0378Accept : Test { :>> id = "851c6689-4b86-4e78-ad31-46d93fa244e3"; :>> method = VerificationMethod::confirmation; :>> procedureText = "recorded from chat - their words, verbatim: “[x] C: diagnostic rig only, no standing number (recommended) (answers: d0378)”"; }
    part d0378AcceptR1 : TestResult { :>> id = "49742ac9-887e-42f1-bca7-ad34d6fc9379"; :>> outcome = VerdictKind::pass; :>> judgedAgainst = "748746a"; :>> judgedAt = "2026-09-08"; :>> judgedBy = "wweatherholtz"; :>> createdBy = "claudeOpus5"; }
}
