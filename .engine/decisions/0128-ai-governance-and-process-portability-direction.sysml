// D0128 (status: the `status` field below is the truth) — Direction: in-loop AI governance + modular process portability + dogfooded release (CLI+MCP)
// Recorded via `keel record decision` (D0105 RMWX axis; issue054). Acceptance is a separate explicit
// human gate (method=confirmation, D0106): flip status + add the d0128Accept event on sign-off.
package Decision0128 {
    private import EngineElement::*;
    private import EngineWork::*;
    private import EngineVerification::*;
    private import EngineRelationships::*;

    part d0128 : Decision {
        :>> id = "a47b6014-3c4b-4efb-886e-ceaa06af0dfd";
        :>> title = "Direction: in-loop AI governance + modular process portability + dogfooded release (CLI+MCP)";
        :>> createdAt = "2026-07-27";
        :>> createdBy = "wweatherholtz";
        :>> status = DecisionStatus::accepted;
        :>> context = "A 2026-07-27 design conversation shaped three linked directions that were discussed but never recorded (the exact unrecorded-design-in-chat risk). (1) AI GOVERNANCE: CLAUDE.md is weak governance (soft context, drifts); agents keep being told to stop writing prose / working outside processes; guards feel reactive because they run at COMMIT. (2) PROCESS PORTABILITY: ships the ENTIRE engine process set monolithically — all-or-nothing, no selection; there is NO import/export/activate/palette in code or model. The want: projects leverage GOOD processes a la carte across projects (agile, STPA, requirements mgmt, semver-CI release, employee reviews, ...). (3) RELEASE: keel pushes every commit but has no release discipline — one stale GitHub release (v0.1.0, ~a month old), the Deploy workflow is DEFINED but never run (a dogfooding gap). The MCP idea was floated as the governance mechanism.";
        :>> decision = "Adopt three directions, with a critical correction on the MCP framing. GOVERNANCE (nAiGovernanceInLoop): strengthen via IN-LOOP GATES (block at the action/turn boundary with corrective feedback — a Stop-hook prototype exists, .engine/tools/stop_gate.py, running keel validate+guard) + AFFORDANCE/CHANNELING (typed write paths; narrative into a Decision's rationale, not shadow prose) + a concise per-project workflow spec. Separate DISCOVERY (agent doesn't know the process/tools -> a self-describing CLI+MCP surface helps) from COMPLIANCE (agent freelances -> only gates+affordances help). MCP is a SURFACE for discovery/ergonomics, NOT an enforcement layer — do not let it masquerade as governance. There is no deterministic 'prevention' for an LLM; the lever is moving the existing gates earlier (in-loop) + shaping affordances, with an over-governance-thrash guard (block clear violations, warn the rest). PORTABILITY (nProcessPortability): evolve processes into modular, importable/activatable units (definition + deploying skill + DECLARED rules/guards + metadata), backed by the D0105/D0107 declarative-rules migration (so activate/disable toggles enforcement, not just skills); a curated palette + BYO + AI-assisted selection + opt-in popularity. RELEASE (nReleaseDiscipline): operationalise the Deploy workflow — semver reconciled across crate/API/engine, git tag, CI-built + published artifact, a recorded Release item; cadence per-milestone. Sequence: prove the in-loop gate (measure), then modular-process unit + activation manifest, then catalog/import-export, then MCP surface, then onboarding, then popularity metrics; release process can proceed in parallel.";
        :>> rationale = "Recording persists the reasoning of a multi-turn design conversation before it is lost to chat history (recording-is-part-of-the-task). The MCP correction matters: building MCP expecting it to fix compliance would be a category error — the compliance win is surface-agnostic (in-loop gates). Modular portability is the natural evolution of n06ProcessAsData (process-as-data) + the D0059 process-has-deploying-skill foundation, and the declarative-rules work (D0105/D0107) is the enabler that makes activate/disable real. The release gap is an honest dogfooding failure (the engine defines Deploy but never ran it). This is a large, multi-sprint platform direction; recording it as ONE governing Decision + three Needs lets it be sequenced + sliced rather than built at once (the scope risk).";
        :>> consequences = "Records Needs nAiGovernanceInLoop / nProcessPortability / nReleaseDiscipline (business.sysml). Downstream (to be sprinted, chartered to this Decision): productionise the in-loop Stop-gate (+ Tier-1/2 later); design the modular-process unit + per-project activation manifest (leaning on declared rules); import/export/activate/disable + a catalog; the CLI+MCP discovery surface; AI-assisted onboarding; opt-in popularity metrics; and the release/deploy process (semver + CI release job + Release item). Architect Sure becomes the human lens over all of it (palette browser, activation, release view). This Decision is PROPOSED; acceptance is a separate explicit human gate (D0106).";
    }

    // acceptance event (D0121 review-queue sign-off; D0066/D0106 — human-judged, not fabricated)
    verification d0128Accept : Test { :>> id = "c810327b-ef86-42e1-b24a-06a64897d5cd"; :>> method = VerificationMethod::confirmation; :>> procedureText = "william weatherholtz"; }
    part d0128AcceptR1 : TestResult { :>> id = "7fb7526c-c55f-4398-9c2b-314d3a962972"; :>> outcome = VerdictKind::pass; :>> judgedAgainst = "196dec4"; :>> judgedAt = "2026-08-13"; :>> judgedBy = "wweatherholtz"; }
}
