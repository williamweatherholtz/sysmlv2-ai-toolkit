// D0285 (status: the `status` field below is the truth) — An STPA control-structure diagram holds five conventions by construction - authority descending, control down and feedback up, labels that say what passes, right angles with nothing overlapping, semicircles at crossings - as a process and a tool, never a per-session judgment
// Recorded via `keel record decision` (D0105 RMWX axis; issue054). Acceptance is a separate explicit
// human gate (method=confirmation, D0106): flip status + add the d0285Accept event on sign-off.
package Decision0285 {
    private import EngineElement::*;
    private import EngineWork::*;
    private import EngineVerification::*;
    private import EngineRelationships::*;

    // #ProspectiveChange (D0070) - this Decision governs a process/schema change; the co-committed
    // change rides the process-change guard's hard lock.
    #ProspectiveChange part d0285 : Decision {
        :>> id = "fcb17559-6e3f-469f-8ef0-03ace5ef144c";
        :>> title = "An STPA control-structure diagram holds five conventions by construction - authority descending, control down and feedback up, labels that say what passes, right angles with nothing overlapping, semicircles at crossings - as a process and a tool, never a per-session judgment";
        :>> createdAt = "2026-09-02";
        :>> createdBy = "claudeOpus5";
        :>> status = DecisionStatus::accepted;
        :>> context = "keel show control-structure (D0284) computes the structure; drawing it was left to whoever drew it. The first render was an auto-laid graph with no authority axis and edges labelled by count; the human said the diagram needs to be better and set the axis, the directions and the rule that every edge is labelled with what passes (st067). The second used curves; the human said linear (st068). The third used straight diagonals and the human said 90-degree lines, minimal overlap, semicircles where lines cross, no lines overlapping (st069). The fourth held all five and the human said save this as the STPA graphing process (st070). Four renders, three corrections, one instruction: the conventions are recurring and D0040 says a recurring task without a skill leaks its knowledge into chat where it cannot be enforced.";
        :>> decision = "A process, stpa-diagram, with steps sd0Compute through sd6Verify, and a tool, .engine/tools/stpa_diagram.py, that takes the JSON of keel show control-structure and renders an SVG in which the five properties hold by construction: (1) authority is the vertical axis, highest at the top, processes along the bottom, controllers in the gaps between process columns so no line passes through a box; (2) control actions are solid, leave an issuer's bottom-left and enter a process's top-left; feedback is dashed, leaves a process's top-right and enters a receiver's bottom-right; (3) every edge is vertical / horizontal / vertical with its own horizontal channel and its own trunk and drop slot, so no two segments are collinear; (4) every edge is labelled with what passes along it, the label sitting on its channel at the first position no other edge's vertical runs behind, with a leader when the channel is shorter than the label; (5) every vertical that crosses another edge's horizontal hops it with a semicircle, and the legend says so. The one remaining judgment is sd6Verify: look at the render at full size and zoomed before delivering, because a label can still hide a line or float past a short channel, which are the two defects the review found. The tool is the sanctioned interim; dcStpaDiagramInTheBinary charters the port into the binary under D0221 with the five properties as unit tests.";
        :>> rationale = "WHY BY CONSTRUCTION AND NOT BY CHECKLIST: a checklist is read by the person drawing, and the person drawing was the one who got it wrong three times. In the tool, a diagonal cannot be produced because the router emits three orthogonal segments; a shared line cannot be produced because channels and slots are allocated uniquely; an unlabelled edge cannot be produced because the label is the edge's own record rendered; a junction cannot be produced because the crossing code draws an arc. That converts four of the five conventions from instructions into properties, and leaves one - readability of the placement - to a review step that names exactly what to look for. WHY THE LABEL IS THE POINT: the human's words were that labelling the edges is critical; a control structure whose edges say a count says nothing about what authority moves, and the UCA analysis that follows (dcStpaProcessForKeel) is per control action per data item, so an edge label that does not name the data has already lost the analysis. WHY THE TOOL IS PYTHON FOR NOW: the reviewed render exists and is right, and a port to Rust that reproduced it byte for byte would have delayed saving the conventions by a day for no reader; D0221 is honoured by chartering the port with the interim named as such, the same shape conformance_lane.py has held since D0132. WHY A PROCESS-CHANGE MARKER: .engine/processes and .engine/skills are keystone-locked (D0209 clause 2) and this Decision is what authorises the two new files.";
        :>> consequences = "Every future control-structure diagram - this project's or a downstream project's - is drawn by the tool from computed JSON, and a reader can rely on the five properties without being told them. The safety viewpoint's page carries the reviewed diagram. dcStpaDiagramInTheBinary sits on the frontier for the port; when it lands the tool is deleted in the same commit and the process text names the command. What this Decision does NOT do: it does not change the structure or its computation (D0284), and it does not begin the UCA analysis - it makes its input legible. REMOVAL PATH (D0163): delete the process, skill and tool together; the page falls back to the JSON tables, which remain the contract.";
    }

    // acceptance event (D0121 review-queue sign-off; D0066/D0106 — human-judged, not fabricated)
    verification d0285Accept : Test { :>> id = "767fee4d-dbd3-43d2-b4a5-db9f4eeaa486"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0285AcceptR1 : TestResult { :>> id = "e5985d37-f6d4-4c16-89af-9081457be47c"; :>> outcome = VerdictKind::pass; :>> judgedAgainst = "a3d7e8f"; :>> judgedAt = "2026-09-02"; :>> judgedBy = "wweatherholtz"; }
}
