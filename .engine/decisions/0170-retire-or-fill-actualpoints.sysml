// D0170 — PROPOSED. `Story.actualPoints` is declared on 370 items and set on none. Frozen schema
// (invariant 5), so retiring it needs explicit human sign-off. #ProspectiveChange (D0070).
package Decision0170 {
    private import EngineElement::*;
    private import EngineWork::*;
    private import EngineVerification::*;
    private import EngineRelationships::*;

    #ProspectiveChange part d0170 : Decision {
        :>> id = "6a25c9f1-3b74-4e08-8d51-27ba60ce4f38";
        :>> title = "D0170: retire `Story.actualPoints`, or fill it — a field declared on 370 items and set on none";
        :>> createdAt = "2026-08-20";
        :>> createdBy = "claudeOpus5";
        :>> status = DecisionStatus::accepted;
        :>> context = "FOUND IN THE NINTH HARDENING PASS, and it is the sibling of a defect I resolved three sprints earlier without noticing this one. `schema/core` declares 88 attributes; five are never set anywhere in the model. Two are accounted for: `actualHours` was demoted to an indicator by issue175, and `safetyLevel` belongs to the optional safety schema downstream projects use. `impact` and `reasonForChange` sit on `ChangeRequest`, which has exactly THREE instances - two unset optional fields on a type used three times is a small fact, and I nearly wrote it up as `368 sprints recorded no reason for any change`, which would have been badly wrong. WHAT SURVIVES IS `actualPoints`. It is declared on `Story`, which has 370 instances. `estimatedPoints` is set on all of them; `actualPoints` is set on NONE, and no Rust code reads it. So the schema asks every sprint to record what the work actually cost, and no sprint ever has - the identical defect to `actualHours` at 1%, on the field right beside it, in a schema I have been editing all session.";
        :>> decision = "PROPOSED, and the choice is genuinely open rather than rhetorical. OPTION A - RETIRE IT: remove `actualPoints` from `schema/core`, per the doc-removal rule that removal means gone rather than a note saying it used to exist. The argument for retiring: `estimatedPoints` plus the sprint's own gates already say what was planned and whether it landed, and a points-actual is a velocity artifact for a team forecasting sprint capacity, which is not what a solo-plus-AI project does (D0010). OPTION B - FILL IT: the sprint closeOut path sets it, computed as the points the work turned out to be worth in hindsight. The argument for filling: estimate-versus-actual is the only feedback the estimate ever gets, and D0038's estimation model exists to be calibrated. I LEAN TO RETIRE, for one reason that is about honesty rather than convenience: an AI writing `actualPoints` in the same breath as `estimatedPoints`, minutes apart, with no independent measurement between them, is not producing feedback - it is producing a number that will agree with the estimate because the same judgment made both. `actualHours` at least had a clock behind it in principle. This does not.";
        :>> rationale = "WHY THIS NEEDS A SIGNATURE AND CANNOT BE SELF-CLEARED: `schema/core` is frozen under invariant 5, and this is the whole point of that invariant - a field is cheap to add and expensive to remove, because anything downstream may read it. It also cannot be filled retroactively: 370 sprints are closed, their actuals were never measured, and inventing them would be exactly the fabrication guard 36 exists to catch. WHY I AM RECORDING IT AS A FINDING AT ALL, given it is Low severity: a schema field that nothing writes and nothing reads teaches a reader that the schema is aspirational, and the next reader cannot tell which of the other 83 attributes are real. That is the same erosion as a metric red for 354 sprints (issue175) - the damage is to the reader's trust in every OTHER number, not to this one.";
        :>> consequences = "IF RETIRED: one attribute leaves `schema/core`, `validate_schema.py` must pass, and the doc surface must be swept for mentions - the removal itself is a two-line change and the ceremony around it is the cost. `estimatedPoints` is unaffected, and no view or guard reads `actualPoints` today, so nothing breaks. IF FILLED: the closeOut path gains a write, and the number's independence problem stated in the decision remains unaddressed - which would be a worse outcome than either retiring it or leaving it visibly empty. IF NEITHER, which is the status quo: issue186 stays OPEN. That is deliberate. Closing it as `documented` would be the move this whole hardening series has been finding and rejecting - D0169 documented a limitation and shipped a false green one sprint later, which is what issue183 was. A finding I cannot clear stays uncleared. REMOVAL PATH, per D0163: this Decision needs none - if rejected, nothing was applied.";
    }

    #Resolves dependency from d0170 to issue186;

    // acceptance event (D0121 review-queue sign-off; D0066/D0106 — human-judged, not fabricated)
    verification d0170Accept : Test { :>> id = "14c72681-48d4-4294-a2ba-f0088e485e32"; :>> method = VerificationMethod::confirmation; :>> procedureText = "Their words, verbatim: 'accept all. proceed'. Said in response to the queue of six proposed Decisions presented for signature - D0167, D0168, D0169, D0170, D0171, D0172 - so 'all' is that queue and this acceptance covers d0170 as one of the six. For D0170 the acceptance includes the Decision's stated lean, retire."; }
    part d0170AcceptR1 : TestResult { :>> id = "df74b140-2d9a-4fbf-8768-5e5a392a5415"; :>> outcome = VerdictKind::pass; :>> judgedAgainst = "3abc583"; :>> judgedAt = "2026-08-20"; :>> judgedBy = "wweatherholtz"; }
}
