// D0147 — ACCEPTED (wweatherholtz, 2026-08-15): a `Claim` item type, so a contributor's intent to
// work an item is an authored fact. FROZEN CORE (§1.5) — sign-off is the d0147Accept event below.
// #ProspectiveChange (D0070): nothing existing changes meaning; this adds a type.
package Decision0147 {
    private import EngineElement::*;
    private import EngineWork::*;
    private import EngineVerification::*;
    private import EngineRelationships::*;

    #ProspectiveChange part d0147 : Decision {
        :>> id = "8f4b1e57-3a92-4d60-b7c4-e05a2836f19b";
        :>> title = "D0147: a `Claim` item type for concurrent work selection (frozen core)";
        :>> createdAt = "2026-08-15";
        :>> createdBy = "claudeOpus5";
        :>> status = DecisionStatus::accepted;
        :>> context = "FOUND by the consumer check while scoping dcWorkClaim (D0144), before writing any code. The ready frontier is ONE global list with no owner and no claim, so several contributors — nearly all AI, on separate machines, working asynchronously — rationally select the same top-ranked item, and the duplication surfaces only at integration. The distributed-collaboration process already specifies the fix in detail and names its own data: 'Record the claim as an authored fact (claiming actor, item, time, and the commit claimed against) and land it IMMEDIATELY so it is visible remotely before work begins.' It also states the mechanism plainly — 'the only things authored are irreducible facts, including the claim'. THE SCHEMA HAS NO SUCH TYPE. Nothing in `schema/core` can hold a claim, so the process's central artifact is unrepresentable. This is the SECOND consumer check in two sprints to find a declared process step whose data the schema cannot hold (issue110 was the first, for actor ROLE), which is itself the finding worth acting on: process definitions and schema were authored at different times against each other's intentions and were never reconciled.";
        :>> decision = "ACCEPTED under §1.5: add to `schema/core/work.sysml` a `part def Claim :> Element` carrying `claimedItem : String` (the item name), `claimedBy : String` (an actor id, matching how all other provenance is carried today), `claimedAt : Timestamp`, and `claimedAgainst : String` (the commit the claim was made against). NO `status`, NO `expiresAt`, NO `released` flag: liveness is COMPUTED — a claim is live if it is the newest claim on its item and its age against git-derived time is under the expiry window, and stale otherwise. Authoring a status field would be the exact defect §1.6 forbids, a stored verdict that can disagree with the facts it summarises. Mutual exclusion needs no lock server and no field: the remote accepts exactly one of two concurrent claims because a git ref update is a compare-and-swap, and a rejected push IS the exclusion working rather than an error to handle.";
        :>> rationale = "A claim is IRREDUCIBLE — it cannot be regenerated from other authored facts plus git, because it records an intention that exists nowhere else — so by §1.1's test it is authored data and not a view. ALTERNATIVES: (i) a typed EDGE, `#Claims dependency from <actor> to <item>` — REJECTED, edges carry no attributes and a claim needs time and commit, which is precisely what makes it a fact rather than a relationship; (ii) declare `Claim` in `.tracking` as project-local rather than in the engine — REJECTED, the claim mechanism belongs to the distributed-collaboration PROCESS, which ships downstream via `keel init`, so a project-local type would leave every downstream project to reinvent it and would put an engine mechanism outside the engine, inverting D0093 in the opposite direction from issue106; (iii) reuse `Story.owner` — REJECTED, ownership is a durable assignment and a claim is a short-lived, expiring, race-resolved intent; conflating them would make an expired claim look like an abandoned assignment. WHY IT IS PROPOSED AND NOT APPLIED: frozen core needs explicit human sign-off on the specific change, and an AI actor cannot supply it. dcWorkClaim is therefore HELD rather than executed, and the frontier moves past it to dcLandLoop, which needs no schema change — pausing on the gated item rather than on the whole frontier (D0052).";
        :>> consequences = "If ACCEPTED: one new type in frozen core, plus the claim write path, actor-filtered `whats-next`, and computed stale-claim expiry that dcWorkClaim's own verification already specifies. If REJECTED: `.engine/processes/distributed-collaboration.sysml` step `dcClaim` must be amended, because a process step whose central artifact cannot be recorded is cited as if enforced while being unsatisfiable — the same conclusion issue110 reached about actor role, and the reason both are recorded as issues rather than left as design notes. Tracked as issue111.";
    }

    // acceptance event (D0121 review-queue sign-off; D0066/D0106 — human-judged, not fabricated)
    verification d0147Accept : Test { :>> id = "1630e068-9648-4a59-805d-6b89b23c333e"; :>> method = VerificationMethod::confirmation; :>> procedureText = "wweatherholtz, 2026-08-15, verbatim: 'accepted on all three. expand to suit the new improved schema'. Given in direct reply to the sprint-298 report, which presented D0146 (Actor.role), D0147 (a Claim type) and D0148 (ship the EngineCodeAudit module) together as one finding - process definitions demanding data the schema cannot hold - each with its alternatives and with what must happen on rejection. The human accepted all three and directed the follow-on work."; }
    part d0147AcceptR1 : TestResult { :>> id = "3f491bae-b756-491d-a4ca-f41d0ef5e74a"; :>> outcome = VerdictKind::pass; :>> judgedAgainst = "46f0cca"; :>> judgedAt = "2026-08-15"; :>> judgedBy = "wweatherholtz"; }
    part d0147AcceptR2 : TestResult { :>> id = "a91ccb21-c922-429d-be18-85f3df4a5fa2"; :>> outcome = VerdictKind::pass; :>> judgedAgainst = "eb0adcf"; :>> judgedAt = "2026-09-04"; :>> judgedBy = "wweatherholtz"; :>> createdBy = "claudeOpus5"; :>> notes = "REBOUND (D0308): AUTO-RE-BOUND under standing consent (D0207/D0308): decision wording PROPOSED to ACCEPTED at a6b7123 - editorial, the agreed substance unchanged. Their standing words, verbatim: 'issues raised are automatically accepted. they can be customizedly changed post-fact.'"; }
}
