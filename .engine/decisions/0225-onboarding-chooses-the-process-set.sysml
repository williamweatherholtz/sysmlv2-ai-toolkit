// D0225 (status: the `status` field below is the truth) — projectOnboarding: a project chooses its process set by being asked about its work, and each process declares the situation it applies to
// Recorded via `keel record decision` (D0105 RMWX axis; issue054). Acceptance is a separate explicit
// human gate (method=confirmation, D0106): flip status + add the d0225Accept event on sign-off.
package Decision0225 {
    private import EngineElement::*;
    private import EngineWork::*;
    private import EngineVerification::*;
    private import EngineRelationships::*;

    // #ProspectiveChange (D0070) - this Decision governs a process/schema change; the co-committed
    // change rides the process-change guard's hard lock.
    #ProspectiveChange part d0225 : Decision {
        :>> id = "c50a6d02-9b8b-4a7a-a612-55e4c35ea8b7";
        :>> title = "projectOnboarding: a project chooses its process set by being asked about its work, and each process declares the situation it applies to";
        :>> createdAt = "2026-08-24";
        :>> createdBy = "claudeFable5";
        :>> status = DecisionStatus::accepted;
        :>> context = "Adopting keel onto a second repository exposed a gap the self-build could never feel. `keel init` lays down a working project with every process active and never asks the author what they are building, so an author facing 25 processes has two bad options: keep all of them and meet friction they never chose - D0054 names adoption friction as the dominant failure mode, above bad architecture - or switch off the ones whose names they do not recognise, which is the worst available selection rule, because the least familiar names are doing the least obvious work. The author asked for this directly and set it as a precondition on the migration: an onboarding process when processes have not been defined, that works out what technical needs or workflows they want or researches best practices, and picks a good set. They enumerated the range it has to serve - hardware, software, both, business processes, safety-related, art, video games, construction plans, whatever - and 'whatever' is part of the requirement, not a throwaway.";
        :>> decision = "A `project-onboarding` process and skill, plus `keel onboard` as its computed view, plus one declared fact per process: an `// APPLIES-WHEN:` line stating the SITUATION in which a project needs that process. Onboarding elicits what is being built and what must not go wrong (deploying business-elicitation, so answers are recorded verbatim as Statements first), matches those facts against each declared condition, RESEARCHES the domain's practice where no process covers it, presents a recommendation as an argument with per-process reasoning the author can strike lines from, and charters the result as a Decision named by `charteredBy` in activation.toml. Guard 50, `process-applicability`, requires every declared Process to carry a condition. `keel onboard` is a VIEW and never a gate.";
        :>> rationale = "Three constraints decided the shape. FIRST, D0216 forbids offering a menu, because a chosen option is evidence about the menu rather than about the chooser's work - but picking a process set from a catalogue IS a menu. The resolution is that onboarding never asks which processes you want; it asks about the work and then argues for a set, which is a claim the author can refute rather than a list they can pick from. SECOND, the conditions are SITUATIONS, never domain labels, and that is what lets 'whatever' be in scope: a closed domain table cannot serve a domain nobody listed, but 'an element being wrong is expensive' is equally true of a bridge drawing, a dosing algorithm and a contract, so element-critique reaches a domain the table never named. THIRD, the condition lives BESIDE its process rather than in a central table, because a central table cannot travel with one unit - the defect that made 23 of 24 units land red on adoption (issue253/D0222), and the mistake this engine has now made twice. The guard exists because a process that cannot say when it applies is invisible to the match: the chartered set omits it silently, indistinguishably from a decision to omit it, which is the honest-state class D0098 permits gating even though completeness is not.";
        :>> consequences = "Adding a process now costs one more declared fact, and the guard will refuse the commit without it - deliberate, since the alternative is a process nobody can be advised to adopt. `keel onboard` reports NOT CHARTERED for every project that has not run onboarding, including this one until D0226; that is a report and not a violation, because a project that never declared an activation file runs everything by default and has violated nothing (D0138/D0164). The research step is the weakest link and is written as such: an AI asked about an unfamiliar domain's practice can fabricate a standard, so the skill says to record what was found WITH ITS SOURCE, never to attribute a practice to a body that did not publish it, and to say plainly when research was unavailable - an unresearched gap recorded as a gap is honest, and a fabricated best practice is the worst possible output of an onboarding conversation, because the author cannot tell it was invented. Verified: 25 processes declare a condition and the guard passes 25 scanned; a process file without one FAILS it; `keel onboard` reports the set with each condition and the charter state; `process audit` reports project-onboarding TRAVELS WHOLE at 3 files. Resolves issue257.";
    }

    // acceptance event (D0121 review-queue sign-off; D0066/D0106 — human-judged, not fabricated)
    verification d0225Accept : Test { :>> id = "5f5470cd-221f-4748-91de-65606347411d"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/23."; }
    part d0225AcceptR1 : TestResult { :>> id = "b7519cc4-a744-4b6e-ae3e-6e87443949a6"; :>> outcome = VerdictKind::pass; :>> judgedAgainst = "64f2dea"; :>> judgedAt = "2026-08-25"; :>> judgedBy = "wweatherholtz"; }
}
