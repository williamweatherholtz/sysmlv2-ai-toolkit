// D0298 (status: the `status` field below is the truth) — Every declared control carries its arming evidence - a probe, a named present test, or a stated reason - and keel show controls counts them apart instead of folding proof into 'not machine-checkable'
// Recorded via `keel record decision` (D0105 RMWX axis; issue054). Acceptance is a separate explicit
// human gate (method=confirmation, D0106): flip status + add the d0298Accept event on sign-off.
package Decision0298 {
    private import EngineElement::*;
    private import EngineWork::*;
    private import EngineVerification::*;
    private import EngineRelationships::*;

    // #SafetyChange (D0070) - this Decision governs a process/schema change; the co-committed
    // change rides the process-change guard's hard lock.
    #SafetyChange part d0298 : Decision {
        :>> id = "603edb3d-e799-40b0-b15a-c631d1804c8a";
        :>> title = "Every declared control carries its arming evidence - a probe, a named present test, or a stated reason - and keel show controls counts them apart instead of folding proof into 'not machine-checkable'";
        :>> createdAt = "2026-09-04";
        :>> createdBy = "claudeOpus5";
        :>> status = DecisionStatus::accepted;
        :>> context = "issue303 and D0253: arming may be proven by TEST where a read-only view cannot establish it, and one control was proven that way; sprint 486 proved a second, a later sprint four more. When this sprint started, five of the fifteen declared controls had NO entry in control-arming.toml at all - ctlAdoptionCheck (whose both-direction test had existed for several sprints), ctlAuditAdherence, ctlOverrideObligation, ctlPostEditGate, ctlTurnBoundaryGate - and the view listed them UNDECLARED, which is the D0254 third failure class in reverse: a proven control read as a gap. And the view could not tell a control proven by a named test from one resting on a paragraph of reasoning: both rendered 'not-machine-checkable', so the evidence count the DoD asked for did not exist as a number anywhere.";
        :>> decision = "Four probes in keel-cli/tests/remaining_controls_actually_fire.rs, each proving the control ALLOWS on a clean case before asserting it REFUSES on a dirty one: the edit gate (a scaffolded project passes a clean edit silently and blocks an unparseable one); the turn gate (a fresh scaffold ends its turn, the same tree with one broken file cannot); the override (denied, then opened for ONE path once - a second path stays closed - the write announced, an obligation left under .tracking/obligations/, the next write denied again); the adherence audit (an unchanged range passes, an unsigned blocking-to-warning downgrade fails naming the rule, the same downgrade with a co-committed #SafetyChange Decision passes). control-arming.toml gains the five entries; ctlAdoptionCheck names the test it already had. The controls view reads provenBy: a control with a named test that EXISTS in the tree renders PROVEN-BY-TEST, one naming a missing file renders PROOF-MISSING (a claim, not evidence), and the view carries armingEvidence - armedByProbe, provenByTest, reasonOnly, proofMissing, notArmed, undeclared - so the honest count is a number the reader gets, not a paragraph they infer. Read back on this tree: 1 armed by probe, 11 proven by test, 3 reason-only (branch protection, audit-history in CI, the release gate job - infrastructure this binary cannot observe, each with its reason), 0 missing, 0 undeclared.";
        :>> rationale = "WHY BOTH DIRECTIONS IN EVERY PROBE: a control that refuses everything is stuck, not armed, and a test that asserts only the refusal passes on a stuck control. WHY THE VIEW CHECKS THE FILE EXISTS: provenBy is prose in a TOML file until something reads it; a test that was deleted or renamed leaves the entry standing and the evidence gone, and the view is the one place that can notice. WHY THE THREE REASON-ONLY CONTROLS STAY REASON-ONLY: their arming lives on GitHub and in CI run records the binary cannot read; the DoD named this a legitimate outcome when stated, and it is stated per control. WHY ctlAdoptionCheck WAS THE FIRST TO FIX: it had been proven for sprints and reported as undeclared - the cheapest, most embarrassing kind of gap, and exactly what a count would have surfaced.";
        :>> consequences = "dcProveTheRemainingControls is delivered; issue303 resolves. Arming states: ARMED, PROVEN-BY-TEST, PROOF-MISSING (new), not-machine-checkable, NOT-ARMED, PROBE-MISSING, UNDECLARED. A future control declared without evidence reads undeclared: 1 in the count, which is the point. The four probes join hook_and_push_controls_actually_fire.rs and adoption_check_can_fail.rs as the arming suite; a control added to the map without a probe or a reason will be the next reader's first line.";
    }

    // acceptance event (D0121 review-queue sign-off; D0066/D0106 — human-judged, not fabricated)
    verification d0298Accept : Test { :>> id = "4d3caa21-ecd4-4a5d-b699-b2df24471b35"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0298AcceptR1 : TestResult { :>> id = "704522ab-6ef2-435c-a856-f1e06a0a2b13"; :>> outcome = VerdictKind::pass; :>> judgedAgainst = "d3338c3"; :>> judgedAt = "2026-09-04"; :>> judgedBy = "wweatherholtz"; }
}
