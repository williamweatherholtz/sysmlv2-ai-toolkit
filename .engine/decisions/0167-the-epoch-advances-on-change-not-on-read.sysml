// D0167 — PROPOSED. The fingerprint epoch advances when a change is OBSERVED or a WRITE happens, never
// on a read. This narrows a correctness condition the human attached to authorising the memo at all, so
// it is recorded for sign-off rather than treated as an optimisation. #ProspectiveChange (D0070).
package Decision0167 {
    private import EngineElement::*;
    private import EngineWork::*;
    private import EngineVerification::*;
    private import EngineRelationships::*;

    #ProspectiveChange part d0167 : Decision {
        :>> id = "1a6f24c8-9b03-4e51-8d7a-63be05147f92";
        :>> title = "D0167: in `keel serve` the fingerprint epoch advances on an observed change or a write, never on a read — and the resulting out-of-band staleness window is bounded and stated";
        :>> createdAt = "2026-08-20";
        :>> createdBy = "claudeOpus5";
        :>> status = DecisionStatus::accepted;
        :>> context = "THEIR INSTRUCTION SCOPED THIS: 'the performance i want is all targeted to the keel serve - the interactive surface. i dont doubt the cli can be slow. regardless, deploy performance improvements'. MEASURED AT THE HTTP BOUNDARY, which is where they experience it, a six-request arrival burst cost 1.05-1.17s WARM across five samples - and per-request instrumentation showed the whole of it was the cache KEY, not the cache miss: `/api/surfaces -> 200 (181ms) [fp 180ms/604 stat, parse 0ms, build x0, git x0]`. A cache HIT re-statted 604 files to establish that nothing had changed. Six requests in one page load, 3624 stats, to answer a question no request between them had changed the answer to. THE INSTRUMENTATION GAP THAT HID THIS: `perf::report` prints at process EXIT, and a server does not exit, so the interactive surface was the one thing KEEL_PERF could never observe. Every performance number in this session was therefore a CLI number - which is exactly the surface they said they did not care about. TWO SEPARATE WASTES WERE ALSO FOUND AND FIXED WITHOUT NEEDING THIS DECISION: /api/obligations computed four views into a private local to read one number out of each, and the console then fetched three of those same four - so `orient` was computed TWICE per arrival; and every open TAB ran its own 604-stat poll every 1.5s, so watching cost N times the same answer.";
        :>> decision = "PROPOSED: the epoch is advanced by an OBSERVED CHANGE or a WRITE, never by a read. Concretely - (a) ONE watcher task per server, spawned at startup and independent of any connection, computes the fingerprint every 1.5s and on a DIFFERENCE bumps the epoch, warms the arrival views, and publishes to a `tokio::sync::watch` channel; (b) SSE connections SUBSCRIBE to that channel instead of each polling, so watch cost is constant in the number of tabs; (c) a non-GET request bumps the epoch BOTH BEFORE and AFTER it runs - before so the handler reads fresh, after so the next read sees the write; (d) a GET bumps nothing and reads the memo. ALSO, and independent of the epoch question: one shared view store reachable without an `AppState` handle, so the expensive internal callers write into the same cache the endpoints read; and the store is keyed by the VIEW's name rather than the ROUTE's, since /api/dispositions and /api/computed/dispositions served identical JSON under two keys and expired it twice. WHY THIS IS A DECISION AND NOT A COMMIT: `fingerprint.rs` records a condition the human attached to authorising the memo, quoted in its own module doc - 'max cache is just fine, if theres a good mechanism to piece-wise update the cache when changes are detected' - which the module implemented as 'keyed by an EXPLICIT EPOCH, never by elapsed time. Nothing expires on a timer and nothing is guessed.' A TTL was the obvious fix and was REJECTED for contradicting that condition outright. This proposal honours the letter - nothing expires on elapsed time, an observation is not a clock - but it does change WHO advances the epoch, and that is theirs to accept.";
        :>> rationale = "WHY AN OBSERVATION IS NOT A TIMER, which is the whole argument: a TTL says 'assume unchanged for 250ms'. This says 'the tree was READ and found identical' - a fact about the tree, established by the same computation the request would have done, just once for all readers instead of once per reader. The memo is still keyed by an explicit epoch and still invalidated by evidence rather than by a clock. WHY THE WATCHER MUST NOT LIVE IN THE SSE CONNECTION, which was my first shape and is wrong: with no browser attached nothing would advance the epoch, and the next arrival would be served a pre-edit answer indefinitely. That is a correctness bug, not a slow path, and it is the reason the watcher is spawned at startup. WHY A WRITE BUMPS TWICE: bumping only BEFORE leaves the handler memoizing the PRE-write fingerprint under the new epoch, so the next read answers from the cache of a tree that no longer exists until the watcher catches up. The human accepts a Decision and the count does not move - which is precisely the 'when I click accept it doesnt look like anything changes' report that started this whole line of work, and I would have reintroduced it. WHY THE WARMING IS ON THE SAME EVENT: the moment the server learns the model changed is the one moment it KNOWS a recompute is coming, because the page is about to be told to refetch. Warming there turns the first interaction after every commit from a blocking recompute into a hit - and in this session the model changed on every commit, dozens of times an hour.";
        :>> consequences = "MEASURED, same tree, same session, HTTP boundary: the warm six-request arrival burst goes from 1.05-1.17s across five samples to 0.02s, five consecutive samples, roughly 3ms per request; the cold burst from 3.91s to 3.11s; and watch cost from 604 stats per 1.5s PER TAB to 604 stats per 1.5s regardless of tabs. THE COST, STATED RATHER THAN BURIED: an edit made OUTSIDE the server - my file writes, a git operation, their editor - is seen up to 1.5s late, and during that window a read is answered `computed` from the pre-edit value. VERIFIED END TO END rather than argued: a real file edit produced `computed` at t+1s, `stale` at t+2-3s once the watcher observed it, and fresh `computed` from t+4s once the warmer landed; the file was restored and `git diff` is empty. WHY THAT WINDOW IS ACCEPTABLE AND WHERE IT IS NOT: the change-detection interval already governed when a page could learn of an out-of-band edit, because nothing tells the page to refetch sooner - so the blindness is relocated, not created. A write THROUGH the server has no window at all. WHAT WOULD MAKE IT UNACCEPTABLE: a consumer that reads /api/* as an authority immediately after an out-of-band write and cannot tolerate 1.5s - the CLI is unaffected, since a one-shot process is one epoch by construction, but a scripted read-after-write against a running server would need to poll for the `stale` label rather than trust the first answer. If they want that closed, the fix is a filesystem watch rather than a poll, and it is a separate proposal. REMOVAL PATH, per D0163: restore the unconditional `new_epoch()` in the request middleware and delete `spawn_watcher` plus the `changes` channel; SSE goes back to per-connection polling. The shared store and the view-name keying are independent of this and stay. The test `the_epoch_is_advanced_by_writes_and_observations_not_by_reads` is what would have to be deleted deliberately, which is the point of it - it FAILS on an unconditional bump, verified by making that exact regression and watching it fail. IF REJECTED: the interactive surface keeps a ~180ms floor on every request that is entirely cache-key cost, and the six-request page load keeps paying it six times.";
    }

    // acceptance event (D0121 review-queue sign-off; D0066/D0106 — human-judged, not fabricated)
    verification d0167Accept : Test { :>> id = "e1550515-3d1e-443e-a44e-9ce7119c3ea0"; :>> method = VerificationMethod::confirmation; :>> procedureText = "Their words, verbatim: 'accept all. proceed'. Said in response to the queue of six proposed Decisions presented for signature - D0167, D0168, D0169, D0170, D0171, D0172 - so 'all' is that queue and this acceptance covers d0167 as one of the six. For D0170 the acceptance includes the Decision's stated lean, retire."; }
    part d0167AcceptR1 : TestResult { :>> id = "4cf59d37-9bfd-4d8f-a411-5a7305599ccf"; :>> outcome = VerdictKind::pass; :>> judgedAgainst = "3abc583"; :>> judgedAt = "2026-08-20"; :>> judgedBy = "wweatherholtz"; }
}
