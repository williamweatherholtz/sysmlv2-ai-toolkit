// D0289 (status: the `status` field below is the truth) — keel accept honours the recording delegation the policy already declares: in an agent session the human's quoted words are the channel, an unquoted note is refused, and a withdrawn delegation restores the old refusal
// Recorded via `keel record decision` (D0105 RMWX axis; issue054). Acceptance is a separate explicit
// human gate (method=confirmation, D0106): flip status + add the d0289Accept event on sign-off.
package Decision0289 {
    private import EngineElement::*;
    private import EngineWork::*;
    private import EngineVerification::*;
    private import EngineRelationships::*;

    part d0289 : Decision {
        :>> id = "664200fd-f140-4bf4-bebf-61f650b3b100";
        :>> title = "keel accept honours the recording delegation the policy already declares: in an agent session the human's quoted words are the channel, an unquoted note is refused, and a withdrawn delegation restores the old refusal";
        :>> createdAt = "2026-09-03";
        :>> createdBy = "claudeOpus5";
        :>> status = DecisionStatus::accepted;
        :>> context = "The human (st074): an exception for quoted user text to be authoritative; they know an AI could misquote them and accept that limit; the workflow is awful if every acceptance means going to a terminal; the exception stands until a better non-local authoritative channel that is not GitHub issues exists. The tree shows the exception was ALREADY GRANTED: attestation-policy.toml has carried decisionAcceptance.delegatedRecording = d0192 since 2026-08-22 (their words then: 'option A is fine. this hasn't been a real issue to date.'), and delegatedAcceptanceSubstanceRule demands that a delegated acceptance record quote the human (a single-quoted span of at least ten characters) or cite a deck, console or GitHub gesture. What made the workflow awful was one layer added after: cmd_accept's channel check (D0178/P1.3) refused every agent-marked, non-TTY session outright, regardless of the policy. A command refusing what the declared policy permits is the D0105 dual-truth defect on the write path.";
        :>> decision = "cmd_accept's channel layer reads the declared policy. In an agent-marked session with no interactive terminal: if attestation-policy.toml declares a recording delegation for decisionAcceptance AND the --note quotes the human's words by the same predicate the substance rule applies afterwards, the acceptance is recorded and the message cites the delegation; if the delegation is declared but the note carries no quote, the command refuses and says QUOTE, so no record is written that the gate would then refuse; if no delegation is declared, the command refuses exactly as before. The judge is always the Person named by --by (the write layer's refuse_ai_judgment is untouched); the agent is the recorder. The doc surface says so where it used to imply a terminal was needed.";
        :>> rationale = "WHY THIS IS AN ALIGNMENT AND NOT A NEW WEAKENING: the authority to record on quoted words was granted in D0192 and its limit was stated there in the same words the human used today - a fabricated quote defeats the check; the protections are the human reading their own record and the audit trail. Nothing in the trust boundary moves; the command stops contradicting the contract it was supposed to serve. WHY CHECK THE QUOTE BEFORE WRITING: the substance rule would refuse an unquoted record at the gate, after the file was written and the turn spent; refusing at the command with the exact shape required is D0054 friction removed in the right direction. WHY THE HUMAN'S TIME BOUND IS RECORDED AND NOT ENCODED: 'until a better non-local authoritative channel exists' is a revisit condition on the delegation, which lives in the policy file with its own TO WITHDRAW line; encoding an expiry here would put the same rule in two places. WHAT THIS DOES NOT PERMIT: paraphrase. The predicate wants a quoted span; the response contract wants it verbatim; an acceptance I record on words the human did not say is the fabrication D0192 names, and no control reads chat to catch it - so this is the one place where the rule rests on my discipline, and the record says so.";
        :>> consequences = "The human accepts in chat and the agent records it, quoting them; the pending forks on this project can be accepted with a sentence each. Three integration tests hold the three arms (recorded with quote; refused without; refused when withdrawn). The revisit condition is the human's: a non-local authoritative channel other than GitHub issues, when one exists, supersedes this by withdrawing the delegation line. REMOVAL PATH (D0163): delete delegatedRecording from decisionAcceptance in attestation-policy.toml - one line, no rebuild - and the command refuses agent sessions as it did.";
    }

    // acceptance event (D0121 review-queue sign-off; D0066/D0106 — human-judged, not fabricated)
    verification d0289Accept : Test { :>> id = "341e119c-abf0-41f9-947c-c95361e59ebe"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0289AcceptR1 : TestResult { :>> id = "36d7a819-5050-47d2-b3e8-046236567748"; :>> outcome = VerdictKind::pass; :>> judgedAgainst = "03d25b0"; :>> judgedAt = "2026-09-03"; :>> judgedBy = "wweatherholtz"; }

    // QUOTE RECEIPT (D0198 shape) - the human's own word on this Decision and on what it supersedes, given
    // 2026-09-03 after the auto-acceptance above; recorded verbatim, judged by the recorder as a record of words.
    verification d0289AcceptAttest1 : Test { :>> id = "e99886ab-821e-4ea9-82e6-97e42e907ffc"; :>> method = VerificationMethod::confirmation; :>> procedureText = "wweatherholtz, 2026-09-03, in chat, verbatim: 'D0289 supersedes layer 3 of D0178: from an agent session, my words quoted verbatim in the acceptance note are the channel, under the D0192 delegation, until a better non-local channel exists' (st075). This receipt makes the acceptance above THEIRS rather than standing consent's, and scopes the supersession: layer 3 of D0178 only - layers 1 and 2 stand."; }
    part d0289AcceptAttest1R1 : TestResult { :>> id = "c99ef04b-8fc3-48a7-bbf4-ffc58b4010ba"; :>> outcome = VerdictKind::pass; :>> judgedAgainst = "f72aef4"; :>> judgedAt = "2026-09-03"; :>> judgedBy = "claudeOpus5"; }

    // What this Decision changes and where it came from - edges the auto-accepted text did not carry.
    #SupersedeClause dependency from d0289 to d0178;
    dependency from d0289 to d0192;
    #DerivedFrom dependency from d0289 to us076;
}
