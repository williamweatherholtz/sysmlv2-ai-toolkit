// D0224 (status: the `status` field below is the truth) — proseGoesThroughAFile: the write path refuses captured tool output in a governance record, and `record decision --from FILE` makes the safe road the easy one
// Recorded via `keel record decision` (D0105 RMWX axis; issue054). Acceptance is a separate explicit
// human gate (method=confirmation, D0106): flip status + add the d0224Accept event on sign-off.
package Decision0224 {
    private import EngineElement::*;
    private import EngineWork::*;
    private import EngineVerification::*;
    private import EngineRelationships::*;

    // #ProspectiveChange (D0070) - this Decision governs a process/schema change; the co-committed
    // change rides the process-change guard's hard lock.
    #ProspectiveChange part d0224 : Decision {
        :>> id = "be7301a1-6ce5-4b4a-89dc-b41fdd2a2f1b";
        :>> title = "proseGoesThroughAFile: the write path refuses captured tool output in a governance record, and `record decision --from FILE` makes the safe road the easy one";
        :>> createdAt = "2026-08-24";
        :>> createdBy = "claudeFable5";
        :>> status = DecisionStatus::accepted;
        :>> context = "Recording D0223, a BACKTICK inside a double-quoted shell argument was command substitution. The decision text NAMED a keel command; sh ran it and substituted roughly 2000 characters of hardening JSON into the `decision` field of a governance record. The part that matters is how it was caught: incidentally, because the injected JSON happened to carry a unicode escape the SysML parser rejects. Tool output without one would have parsed clean and landed, and the committed record would then assert something no human and no AI ever wrote. That is the same class as a fabricated attestation and worse than a typo, because a typo is visible and this is not. Shell escaping had already gone wrong six times this session; every previous instance broke a BUILD, where the failure announces itself. This one silently corrupted a RECORD.";
        :>> decision = "Two halves, because a lesson is not a control (D0047). REFUSE: `record_decision` and `record_issue` reject any prose field carrying captured tool output, detected as a run of three or more quoted-key-then-colon pairs - the shape of JSON and of a Python dict repr, which is what a tool prints and what authored prose does not produce. The refusal names the mechanism, so the author learns the backtick rule at the moment it bites them. SUPPORT: `keel record decision --from FILE` takes the prose from a draft file - `key: value` headers and `--- key` sections whose bodies are verbatim - so quotes, backticks and dollar signs are literal and no shell layer exists to run anything. Explicit flags still override, and the file is deliberately not TOML or JSON: a format that makes the author escape quotes would reintroduce exactly the problem the file removes. A SECOND shape is refused for the same reason: a console transcript, detected as four or more strong guard markers, calibrated against the whole corpus where no authored field carries more than one and the landed instance carried dozens.";
        :>> rationale = "The engine's whole claim is that a recorded fact states what someone actually said or did. A write path that will accept a tool's own output as a human-or-AI-authored rationale breaks that claim quietly, and quiet is the dangerous part - every other defect this session announced itself with a red gate. Detection is deliberately NARROW because a detector that fires on real prose is worse than none: it teaches the author to route around the write path, which is where every other check lives. The bar was set by running it over the entire existing corpus - every context, decision, rationale and consequences field of 223 Decisions, 800-plus fields quoting guard names, field syntax and human speech - and requiring zero flags, with the population asserted non-empty so the check cannot pass vacuously the way two others did this session. The second half is D0054: friction is the top risk, so the fix cannot be a rule the author must remember under pressure. Passing five paragraphs as shell arguments was the friction; a file removes the interpreter rather than asking for vigilance.";
        :>> consequences = "An author whose prose genuinely needs three quoted-key-colon pairs - quoting a JSON fragment inside a rationale, say - will be refused and must use `--from`, which accepts it verbatim; that is the intended trade and the escape hatch is in the message. The detector is a heuristic and will miss tool output that is not JSON-shaped, so it narrows the hole rather than closing it; the durable protection is `--from`, and the refusal exists to teach it. Verified: the injected D0223 text is refused by name with the excerpt quoted; a clean decision naming guards in quotes still records; the whole existing corpus flags zero; 265 lib tests pass. DISCOVERED AFTER RECORDING, and it changes the standing of this control: the injection had ALREADY landed. D0214's context held 13,136 characters of console transcript, substituted mid-sentence where a backticked command name stood, recorded and auto-accepted and pushed without detection - it carried no invalid escape and no key-colon pairs, so neither the parser nor the first shape would have caught it. The dump is excised and the sentence restored, the acceptance receipt untouched because what was agreed did not change; the transcript shape now refuses that instance by construction, and it is a test case rather than a hypothesis. Resolves issue255 and issue256.";
    }

    // acceptance event (D0121 review-queue sign-off; D0066/D0106 — human-judged, not fabricated)
    verification d0224Accept : Test { :>> id = "e255a553-098b-4c6f-b015-1c26a0d78613"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/22."; }
    part d0224AcceptR1 : TestResult { :>> id = "90266537-5c70-44bc-b3f7-5346cd6a73a9"; :>> outcome = VerdictKind::pass; :>> judgedAgainst = "9cb157a"; :>> judgedAt = "2026-08-24"; :>> judgedBy = "wweatherholtz"; }
}
