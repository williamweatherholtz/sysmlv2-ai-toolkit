// D0144 — Check the CONSUMER before building the PRODUCER. A gated Definition-of-Ready step, added
// after three instances in one pass.
// #ProspectiveChange (D0070): work chartered under the prior DoR stays valid.
package Decision0144 {
    private import EngineElement::*;
    private import EngineWork::*;
    private import EngineVerification::*;
    private import EngineRelationships::*;

    #ProspectiveChange part d0144 : Decision {
        :>> id = "3e58a0c7-9412-4d7b-86ef-b45103f7c9d2";
        :>> title = "D0144: consumer-before-producer is a Definition-of-Ready gate";
        :>> createdAt = "2026-08-14";
        :>> createdBy = "claudeOpus5";
        :>> status = DecisionStatus::accepted;
        :>> context = "THREE INSTANCES IN ONE PASS, each the same shape: something was BUILT and the thing that had to read it turned out to be unable to. (1) Sprint 270 emitted `flow` edges into the Model, then discovered `Model::build` does not ingest `.engine/workflows`, so the emission is correct and unexercised (issue104). (2) Sprint 277 retyped `Process`/`ProcessStep` in the schema before the parser could read `action def X :> Y`, taking check-engine to 132 diagnostics. (3) Sprint 278 scoped a 6132-value provenance migration to `ref Actor` before checking that the reference TARGET lives in `ProjectActors` — a per-project package `.engine` may not import without inverting the D0093 engine/instance boundary (issue106). Each check was one grep. Each discovery came after the design was recorded, and in the third case after the human had been told the work was merely 'excluded pending review' rather than 'proposed on a shape that does not hold'. The human named the rule directly on reading the third: 'consumer before building producer seems wise'. D0047 requires a recurring defect to become a control rather than a reminder, and three instances is past that threshold.";
        :>> decision = "(A) The Definition of Ready gains a step, `dorConsumer`, ordered after `dorDeps` and before `dorSized`: if the item PRODUCES anything another component must read — an edge, an attribute, a file, an emitted artifact, a new construct — NAME that consumer and confirm it can read the thing as specified, before building. (B) The step explicitly includes checking the DIRECTION of any dependency the change would create, because the third instance failed on layering rather than on capability: a producer in `.engine` may not depend on `.tracking`. (C) Where a computed proxy exists it is named in the step so the check is cheap: `keel guard parser-coverage` answers 'does the parser read this construct', and the dead-schema rule in rules.sysml answers 'does anything instantiate this type'. (D) It applies at TRIAGE as well as execution — the third instance was recorded as a work item with a shape that could never hold, so the check belongs where the item is written, not only where it is built.";
        :>> rationale = "This is a PROCESS control rather than an automated one, and the distinction matters against D0047's rule that manual vigilance is not a control. A DoR step is not vigilance: it is a gated step whose passing is recorded and whose ordering the `ceremony` guard enforces, so skipping it is visible in the same way skipping any other gate is. What CANNOT be automated is the check itself, because the consumer differs per change — a parser for one, a Model directory list for another, a package-import direction for a third — and no exact predicate covers that set. Writing a heuristic guard over refine-gate prose would fire on ambiguity and train its reader to ignore it, which is the issue081 dynamic this project has already paid for once. So the honest design is: a gate that forces the question, plus the two computed proxies that DO exist for the specific classes where one is possible, both named in the step so the cheap check is the obvious one. ALTERNATIVES: (i) leave it as a recorded lesson in three retros — REJECTED, that is exactly the documented-preference state D0139(B) and rules.sysml both demonstrate does not hold; (ii) a guard requiring the refine gate's text to mention a consumer — REJECTED as a prose heuristic, per the above; (iii) extend `parser-coverage` into a general producer-consumer check — REJECTED, it is not generalisable: 'is there a reader' has no uniform computable form across edges, files, imports and constructs; (iv) CHOSEN.";
        :>> consequences = "`.engine/processes/definition-of-ready.sysml` gains `dorConsumer` and one succession rewire. Marked #ProspectiveChange (D0070): items chartered under the prior DoR stay valid, since the step adds a question rather than changing what any existing check means. Doc-sync rides the same commit: the stale `query.py` citation in that file, plus the remaining ones in agile-workflow, definition-of-done and the test-verify skill, are retired to the `keel` commands that exist — `query.py` was retired at D0074 and the earlier sweep (D0142) corrected only `schema/core`, which is itself a small instance of not checking every consumer of a change.";
    }

    verification d0144Accept : Test { :>> id = "a7e2b593-0c41-4f8d-b7a6-e3915d0286cf"; :>> title = "Human acceptance of d0144"; :>> createdAt = "2026-08-14"; :>> createdBy = "claudeOpus5"; :>> method = VerificationMethod::confirmation; :>> procedureText = "wweatherholtz, 2026-08-14, verbatim: 'continue to implement improvements. consumer before building producer seems wise.' Given in direct reply to the sprint-278 report, which stated the pattern as three instances across sprints 270, 277 and 278 and said plainly that it 'belongs in how findings get triaged, not just how they are executed'. The human named the rule and endorsed it; this Decision records the control that follows and the reason it is a gated process step rather than an automated guard."; }
    part d0144AcceptR1 : TestResult { :>> id = "f0b48c17-6d3a-4e29-95c0-8a271be6df34"; :>> outcome = VerdictKind::pass; :>> judgedAgainst = "a7b39f8"; :>> judgedAt = "2026-08-14"; :>> judgedBy = "wweatherholtz"; }
}
