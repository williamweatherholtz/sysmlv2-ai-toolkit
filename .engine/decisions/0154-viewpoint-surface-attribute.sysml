// D0154 — ACCEPTED (wweatherholtz, 2026-08-16): add `surface` to the Viewpoint type so grouping is a
// declared per-viewpoint fact. FROZEN CORE (§1.5) — sign-off is the d0154Accept event below.
// #ProspectiveChange (D0070): adds an optional attribute; nothing existing changes meaning.
package Decision0154 {
    private import EngineElement::*;
    private import EngineWork::*;
    private import EngineVerification::*;
    private import EngineRelationships::*;

    #ProspectiveChange part d0154 : Decision {
        :>> id = "c9f4e207-6a83-4d51-b0e8-27ad4915f36c";
        :>> title = "D0154: Viewpoint carries `surface` — the grouping the console derives navigation from";
        :>> createdAt = "2026-08-16";
        :>> createdBy = "claudeOpus5";
        :>> status = DecisionStatus::accepted;
        :>> context = "FOUND BY THE CONSUMER CHECK (dorConsumer, D0144) while starting to build srConsoleNavigationDerived, and it stopped the build. MEASURED: the registry declares 28 Viewpoints, so navigation generated one-per-viewpoint yields 28 top-level entries — worse than the 12 hardcoded tabs the redesign exists to remove, and a direct violation of srConsoleArrivalBounded, which requires that adding a viewpoint NOT increase the top-level count. The obvious fallback fails too: grouping by the existing `audience` attribute yields 20 distinct groups across 28 viewpoints, because `audience` is free prose — 'maintainer / reviewer / auditor' and 'maintainer / auditor / reviewer' name the same three people and count as two. Nothing in the model declares which surface a viewpoint belongs to, so the requirement could not be built as specified.";
        :>> decision = "ACCEPTED: add `attribute surface : String[0..1]` to `part def Viewpoint` in schema/core/computed.sysml. A viewpoint declares which top-level surface it appears on; the console derives its navigation from the distinct set of declared surfaces, so the top-level count is a function of declared GROUPING rather than of viewpoint count. Optional, so every existing viewpoint remains valid and an undeclared one is reported rather than defaulted onto a surface it never claimed.";
        :>> rationale = "WHY AN ATTRIBUTE AND NOT A CONTRACT FILE, which was the first instinct because it needs no frozen-core sign-off: `critique-policy.toml` and `attestation-policy.toml` are precedent for DECLARED POLICY — rules that apply per TYPE or per CLASS. Which surface a viewpoint appears on is PER-ELEMENT DATA about that viewpoint. Putting per-element facts in a side file is the dual truth §2.1 forbids: a reader of the registry could not see where a viewpoint appears, and the two could disagree with nothing to detect it. The Viewpoint type already carries concern, audience, sources and renderer — four per-element facts about how a lens is presented — and `surface` is the fifth of exactly that kind. WHY NOT REUSE `audience`: it is free text, inconsistently ordered, and it conflates two different questions — who a lens is FOR versus where it APPEARS. The human also deferred audience-based filtering entirely on 2026-08-16, so building grouping on it would have coupled a live requirement to a deferred one. WHY OPTIONAL: 28 viewpoints predate this attribute and all remain valid; forward-only, per issue068, and an absent surface must surface as an explicit gap rather than a silent default.";
        :>> consequences = "One optional attribute in frozen core; every existing viewpoint stays valid and `keel init` ships the field to every downstream project. The 28 declared viewpoints need `surface` populated before the console can group them, and any left unpopulated must be REPORTED by the surface rather than hidden — an undeclared grouping is exactly the kind of absence srConsoleViewStatusExplicit says must be visible. Unblocks srConsoleNavigationDerived and srConsoleArrivalBounded, which were stalled on it.";
    }

    // acceptance event (D0121 review-queue sign-off; D0066/D0106 — human-judged, not fabricated)
    verification d0154Accept : Test { :>> id = "5d17b8ac-04e9-4b72-9c36-8fa1e0d2537b"; :>> method = VerificationMethod::confirmation; :>> procedureText = "wweatherholtz, 2026-08-16, verbatim: 'd0148 accepted. go A'. Given in direct reply to a message that stopped the build, reported the measurement (28 viewpoints; grouping by audience yields 20 groups because audience is free prose), rejected the contract-file alternative as per-element data outside the model, and offered exactly two options — A: add `surface` to Viewpoint, frozen core, needing sign-off; B: ship derived navigation now and accept a temporarily worse console. The human chose A. Their reference to 'd0148' is to the PRECEDENT cited in that message — D0148 being the earlier frozen-core addition made when the model could not hold what a requirement needed — and not to D0148 itself, which was accepted on 2026-08-15 for the EngineCodeAudit module and is unaffected."; }
    part d0154AcceptR1 : TestResult { :>> id = "e0c63f95-7b21-4a08-85d4-3169bce7a24f"; :>> outcome = VerdictKind::pass; :>> judgedAgainst = "fce84b3"; :>> judgedAt = "2026-08-16"; :>> judgedBy = "wweatherholtz"; }
}
