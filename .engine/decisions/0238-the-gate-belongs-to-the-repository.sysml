// D0238 (status: the `status` field below is the truth) — the commit gate belongs to the repository and is workspace-scoped unconditionally
// Recorded via `keel record decision` (D0105 RMWX axis; issue054). Acceptance is a separate explicit
// human gate (method=confirmation, D0106): flip status + add the d0238Accept event on sign-off.
package Decision0238 {
    private import EngineElement::*;
    private import EngineWork::*;
    private import EngineVerification::*;
    private import EngineRelationships::*;

    // #SafetyChange (D0070) - this Decision governs a process/schema change; the co-committed
    // change rides the process-change guard's hard lock.
    #SafetyChange part d0238 : Decision {
        :>> id = "d26e1669-788b-4306-9208-b42fc5b78de0";
        :>> title = "the commit gate belongs to the repository and is workspace-scoped unconditionally";
        :>> createdAt = "2026-08-27";
        :>> createdBy = "claudeOpus5";
        :>> status = DecisionStatus::accepted;
        :>> context = "D0234 introduced the workspace — one git repository holding several keel projects. An adversarial panel then found the arrangement was not fit to use, and two of its Criticals are about the gate itself. Both were reproduced before being fixed. issue275: discovery was a depth-3 walk that RETURNED at the first project on a branch, so a project nested inside another, or deeper than three, was invisible to every workspace-scoped mechanism and rode out UNGATED. `keel init` refused neither position, so the 'a project does not nest inside another' comment described a convention rather than the code. issue278: a freshly created workspace was completely ungated. init wrote a hook per PROJECT and armed core.hooksPath only when the target itself held a git directory, so `git init` followed by two `keel init`s left no repo-root hook and no hooksPath — verified, the subsequent commit ran with zero pre-commit lines. The scaffolded hook body did carry a workspace branch, but it decided 'am I at a workspace root' by testing `[ ! -d .engine ]`, which is wrong for the commonest layout — a repo whose root is itself a project with peers beside it — where .engine exists and every peer rode out ungated. And the refusal message added in the same change advised `keel hook pre-commit`, which is not a hook event: at a workspace root it prints nothing and exits 0, so anyone who wired it in installed a gate that passes while checking nothing.";
        :>> decision = "The gate belongs to the REPOSITORY, and it is workspace-scoped unconditionally. 1. Discovery asks git (`git ls-files -c -o --exclude-standard`) instead of walking directories, and takes the prefix before any `.engine/` or `.tracking/` component as a project root. Found at any depth, nested included. The filesystem walk survives only as the fallback for a directory that is not a git repository. 2. `keel init` REFUSES a target inside an existing project. Projects in a workspace are peers, not tenants. When the host project is the repository root — where there is no 'beside' — the refusal says so and names the two remedies. 3. The pre-commit hook is written at the git repository ROOT and `core.hooksPath` is armed there, at init time. An existing hook is never overwritten: in a workspace that file is shared, and D0108 says a non-owner may add but never overwrite in place. 4. The hook body is one call — `keel gate --workspace .` — with no branch. It gates every project the commit touches and is identical to the old single-project path when the repo holds one project. 5. `workspace::canon` is the single normaliser for path comparison, and the advice string names a command that gates.";
        :>> rationale = "ALTERNATIVES for discovery: (A) raise the depth bound — rejected: it trades one guessed number for another and still cannot see a nested project, which is the layout the panel actually reproduced. (B) declare the project list in a repo-root manifest — rejected: a second place to keep the list true, which is the dual-truth D0018 forbids, and it goes stale exactly when a project is added. (C) ask git — CHOSEN. CRITERIA: can it be wrong about a project that exists; what does it cost per command; and does its answer match the set a push can carry. (C) wins on the third criterion decisively: git enumerates precisely what a commit can carry, so a project git does not know about is out of scope BY DEFINITION rather than by accident. It also costs one process instead of a recursive stat storm and inherits .gitignore for free. Making the hook body unconditional removes the misdiscrimination rather than correcting it. A test that asks 'am I a workspace root' has to be right about a question `keel gate --workspace` already answers correctly, so having two answers was the defect; there is now one. Arming core.hooksPath at init rather than printing it as a step: the step a newcomer is most likely to skip is the one that turns the gate on, and the printed step was worse than skippable — it read `git init && git config core.hooksPath .githooks` after a `cd` into the project, so followed literally from inside a workspace peer it created a NESTED repository and took that project out of the repository whose hook and push cover it.";
        :>> consequences = "A two-project workspace created only with documented commands is gated: verified end to end, where a clean commit gated both projects and a broken file in the second BLOCKED the commit with exit 1. The same reproduction exited 0 with the gate printing clean before this. A repo whose root is already a project can no longer gain a peer. That is a real narrowing and it is deliberate: a workspace is projects in subdirectories with none at the root, which is the layout the request behind D0234 described. The refusal names the two ways out rather than leaving the author to discover the cliff. Single-project repos are unaffected in behaviour, and this is a measurement rather than an assertion: the nine keel repositories on this machine each report exactly one project, and the full test suite passes. An earlier claim that a comparable change was 'byte-identical for a single-project repo' was an over-claim the panel refuted, so it is not repeated here — the scaffolded hook body DID change for new projects, and init now arms hooksPath where it previously only printed the step. Still open from the same panel and NOT addressed here: issue276 (the repo-root enforcement surface belongs to no project, so the keystone lock covers it with no guard), issue277 (audit-adherence derives its signature from repo-root-relative pathspecs and is blind one directory down), and issue279-284. The gate now RUNS across a workspace; whether it can be weakened without a signature is a separate question, and it is the next one.";
    }

    // acceptance event (D0121 review-queue sign-off; D0066/D0106 — human-judged, not fabricated)
    verification d0238Accept : Test { :>> id = "2879a0cb-6aed-4acd-a04e-b4b212bbe093"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0238AcceptR1 : TestResult { :>> id = "c202547e-05d9-4a52-9ff4-cd2620420479"; :>> outcome = VerdictKind::pass; :>> judgedAgainst = "09e4e87"; :>> judgedAt = "2026-08-27"; :>> judgedBy = "wweatherholtz"; }
}
