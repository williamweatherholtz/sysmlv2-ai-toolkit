// D0169 — PROPOSED. The critique process's own questions become COMPUTED lenses, and two of its
// findings are answered by DECLARED CONTRACTS rather than by frozen-schema changes.
// #ProspectiveChange (D0070).
package Decision0169 {
    private import EngineElement::*;
    private import EngineWork::*;
    private import EngineVerification::*;
    private import EngineRelationships::*;

    #ProspectiveChange part d0169 : Decision {
        :>> id = "3b81f5c0-7a24-4e69-9d08-42ce16bd7a53";
        :>> title = "D0169: `keel hardening` — the critique process measures itself, process enforceability and decision promises are DECLARED, and one metric is demoted to an indicator";
        :>> createdAt = "2026-08-20";
        :>> createdBy = "claudeOpus5";
        :>> status = DecisionStatus::accepted;
        :>> context = "THE HUMAN ASKED FOR A HARDENING PASS on the grounds that keel is not doing what it says and half-baked implementations are loose in the model. Six findings were recorded (issue171-176) and this Decision governs their resolution. THE FINDING THAT MATTERS MOST WAS ABOUT THE AUDIT ITSELF: D0046's critique process asks a stable, recurring set of questions, and every pass re-derived them as throwaway python. In the pass that produced these findings FOUR probes were wrong before they were right - a regex matching `: Process` also matched `: ProcessStep` (131 reported, 24 exist); help extraction reported `keel orient` and `keel assured` as nonexistent minutes after both had been run; a second attempt reported 0 of 72 documented; and a registry probe reported 0 registered skills against 35 real declarations, which would have been a phantom-drift finding of exactly the kind CR-10 already fixed once in 2026-06. EACH WRONG NUMBER WAS ONE EDIT FROM BECOMING A RECORDED FINDING, and a recorded finding directs the next session. D0040 says a recurring task without a skill leaks process knowledge into conversation history; this leaked worse - it leaked WRONG ANSWERS toward the model.";
        :>> decision = "PROPOSED, in four parts. (A) `keel hardening` - three computed lenses replacing the probes: HELP COVERAGE (which dispatched subcommands the catalogue names), PROCESS ENFORCEMENT (which processes assert a guard), DECISION FOLLOW-THROUGH (which accepted Decisions promised an artifact that does not exist). All three read SOURCE rather than running the binary, because a view that shells out to itself to report on itself cannot be trusted. (B) HELP IS A CATALOGUE PLUS A TEST. 35 of 75 subcommands were dispatched and never described, because help was a wall of `eprintln!` beside a hand-maintained `match` - two truths drifting in one direction only. `const CATALOGUE` is now the single table `print_usage` iterates, and `every_dispatched_subcommand_is_documented` fails the build on an arm with no line. NOT full derivation - clap would be that - and the gap is stated rather than hidden: a table plus a test makes the drift impossible to LAND rather than impossible to write. (C) TWO CONTRACTS INSTEAD OF TWO SCHEMA CHANGES. `.engine/contracts/process-enforcement.toml` records, per process, whether its constraint is machine-checkable AND WHY NOT - because `asserts no guard` printed identically for a genuine judgment (a definition of done) and for a real missing guard (D0108's ownership rule), so 68% of the catalogue looked like debt when much of it is not. `.engine/contracts/decision-artifacts.toml` records what an accepted Decision promised to EXIST. Neither needs `schema/core`, which is frozen (invariant 5), and neither is a property OF the item - both are claims about the tree, checked against the tree. (D) TWO NUMBERS THAT COULD NOT INFORM ARE SPLIT OR DEMOTED. `rootedness` splits `decision_chartered` into `decision_rooted` (the chartering Decision cites a Statement, UserStory or Need) and `decision_ungrounded` (it rests only on my judgment); the sum is retained so no reader breaks. And `actualHours` becomes an INDICATOR: it sat at 4 of 358 for the project's entire history, and no defensible threshold exists, because a human will not type hours and an AI has no clock it can honestly attest to.";
        :>> rationale = "WHY THE INSTRUMENT IS THE HIGHEST-LEVERAGE ITEM AND NOT THE MOST OBVIOUS ONE: the other five findings are each one defect. This one is the reason the next five would also be re-derived, and re-derived wrongly. It also proved itself twice DURING construction - the help lens first looked for `fn usage(`, which does not exist, and reported 0 of 75; then it read `print_usage`'s body, which was right until part (B) moved the lines into a const, at which point it reported 1 of 75. Both times the number was ABSURD rather than plausible, which is the whole argument for a lens over a probe: a mis-aimed lens fails loudly, a mis-written regex fails credibly. WHY THREE BUCKETS FOR ENFORCEMENT rather than a guard per process: a guard cannot be conjured for a judgment, and gating the ratio would make the cheapest fix a guard that checks nothing - textbook Goodhart, and invariant 7 already says a boundary nobody can defend stays an indicator. The three buckets make the UNDECLARED set the honest gap, and an `admittedGap` - the contract itself saying a guard could exist - is worse than silence, because someone looked and agreed. Four processes are in that state and I did not paper over them. WHY `decision_ungrounded` IS THE NUMBER I EXPECT TO BE ARGUED WITH: 294 of 360 delivery Stories are chartered by a Decision resting only on my own judgment, against 12 decision-rooted and 53 need-rooted. D0064 permits decision-driven engine evolution, so none of the 294 is a violation - and that is exactly why one bucket could not inform. A metric that cannot fail cannot direct anything.";
        :>> consequences = "MEASURED, before and after, same tree: help coverage 40 of 75 (53%) to 75 of 75 (100%); process enforcement 11 of 24 enforced with 13 indistinguishable unknowns, now 11 enforced + 9 declared-unenforceable + 4 undeclared, 83% accounted; decision promises 0 declared, now 4 declared with 1 unbuilt - D0161's `.knowledge/`, left visible on purpose, since this lens exists to surface it rather than to make it disappear. The charter split resolves 306 into 12 + 294. CONTROLS ADDED: `every_dispatched_subcommand_is_documented` (verified BOTH WAYS - a dispatch arm with no catalogue line was added deliberately and the test named it), plus three unit tests pinning the lens behaviours that were wrong by hand - a ProcessStep is not a Process, `check-engine` does not satisfy `check`, an arm BODY literal is not a command. WHAT THIS DOES NOT DO: `keel hardening` reads `main.rs` from the repo, so it answers about the SOURCE TREE and not about an installed binary - correct for an audit, useless as a runtime self-check, and stated so nobody mistakes one for the other. The two contracts are AUTHORED, so they can be wrong: I entered two false promises while writing one (`hook.rs`, which lives in `main.rs`, and `activation.toml`, absent by design) and the lens reported two false gaps until I corrected them. That is the cost of a declared contract and it is the right cost - silence would have been worse. REMOVAL PATH, per D0163: delete `hardening.rs`, its module registration, its dispatch arm and its catalogue line; delete the two contract files (the lens then reports `declared = 0` and says so); revert the `CATALOGUE` const to inline `eprintln!` calls and delete the coverage test; drop `decision_rooted`/`decision_ungrounded` from `rootedness`, whose sum is already carried; and drop `actualHours_pct` plus `estimationFeedbackIndicator`. Nothing else reads any of it. IF REJECTED: the audit keeps re-deriving its own questions by hand, and the next pass gets a different set of wrong numbers.";
    }

    // acceptance event (D0121 review-queue sign-off; D0066/D0106 — human-judged, not fabricated)
    verification d0169Accept : Test { :>> id = "0abcaabe-d9f1-42de-a0e8-7f8019e6eb42"; :>> method = VerificationMethod::confirmation; :>> procedureText = "Their words, verbatim: 'accept all. proceed'. Said in response to the queue of six proposed Decisions presented for signature - D0167, D0168, D0169, D0170, D0171, D0172 - so 'all' is that queue and this acceptance covers d0169 as one of the six. For D0170 the acceptance includes the Decision's stated lean, retire."; }
    part d0169AcceptR1 : TestResult { :>> id = "2141ffbc-8c56-4ddb-979e-ed879136d9bc"; :>> outcome = VerdictKind::pass; :>> judgedAgainst = "3abc583"; :>> judgedAt = "2026-08-20"; :>> judgedBy = "wweatherholtz"; }
}
