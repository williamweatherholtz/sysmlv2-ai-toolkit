// D0446 (status: the `status` field below is the truth) — A skill's declared budget names the check that holds it, in the row, or says unheld
// Recorded via `keel record decision` (D0105 RMWX axis; issue054). Acceptance is a separate explicit
// human gate (method=confirmation, D0106): flip status + add the d0446Accept event on sign-off.
package Decision0446 {
    private import EngineElement::*;
    private import EngineWork::*;
    private import EngineVerification::*;
    private import EngineRelationships::*;

    // #ProspectiveChange (D0070) - this Decision governs a process/schema change; the co-committed
    // change rides the process-change guard's hard lock.
    #ProspectiveChange part d0446 : Decision {
        :>> id = "a5339c7b-77c4-453c-ab05-0681236322a7";
        :>> title = "A skill's declared budget names the check that holds it, in the row, or says unheld";
        :>> createdAt = "2026-09-11";
        :>> createdBy = "claudeOpus5";
        :>> status = DecisionStatus::accepted;
        :>> context = "Skills under .engine/skills/*/SKILL.md declare numeric budgets in contract tables (asi-templates section 2.1: word caps per brief section). Three decision briefs were published over those caps while the prose beneath the table said a checker held them; the human's verdict on the third ('the decision brief is still far too verbose.', st109) arrived before any check did - a declared rule with no reader, the issue397 shape again (retro of sprint 607, issue413). D0047 says a reminder is not a control. Before this change the section 2.1 table had nine rows, seven with a number, and none named what measured it: `python scripts/check_templates.py --budgets` read 7 violation(s) on the live tree (Title, The ask, Why now, The decision rule, Why this wins, What would change my mind, Provenance strip). This Decision is a process change because .engine/skills/asi-templates/SKILL.md is a locked process definition (D0070) and the change adds a column the skill's readers must fill; no guard, hook or CI workflow is added or altered.";
        :>> decision = "Every table in a deployed skill (.engine/skills/*/SKILL.md) whose header names a Budget column carries, in each row whose budget has a number, the check that measures it - a `check_templates.py --<flag>` the script dispatches, a guard listed in .engine/docs/guards.md, or a pytest path that exists - or the literal word `unheld`. `python scripts/check_templates.py --budgets` walks the skill set and refuses a numeric row that names neither, naming the skill, the section, the row and the number; a named check that does not exist is refused the same way. The check carries its D0388 pair as `--probe` (fixtures fixed before the live tree was read) and both the pair and the live census run under `--self-test`, which CI already runs on every push. The asi-templates 2.1 table gains a `Held by` column: Title, The ask, Per-ask exhibits and Provenance strip name `check_templates.py --brief`; Why now, The decision rule, Why this wins and What would change my mind name `tests/exec_summary`; Courses says `unheld`.";
        :>> rationale = "A section-level mention ('the remaining rows are measured by the exec-summary suite') cannot say which row it holds, and that is exactly the shape that failed: the sentence was true of nothing in the table above it while three pages went out. Per-row naming makes the claim checkable and the census readable - the list of what is held, by what, and what is honestly unheld is the answer, not a verdict line. Placing the check in check_templates.py rather than a new guard adds no enforcement surface: the CI script-probe step (D0394) already runs `--self-test`, so the live census is judged by a run that exists. `unheld` is accepted because an honest declaration of no reader is a fact the table can carry; silence is a hope.";
        :>> consequences = "- A skill author who adds a numeric budget to a Budget table must name its check in the row or write `unheld`; CI refuses the push otherwise. - The census is the deliverable: `--budgets` prints every Budget-table row with its status (held -> check, unheld, no number, FAIL). - Finding surfaced for a separate Issue: the four rows naming `tests/exec_summary` (Why now 60, The decision rule 40, Why this wins 90, What would change my mind 30) are held only in the sense the DoD and the skill assert - the suite's word caps live in check_templates.BUDGETS (driver 20, why 32, flip 20, conf 16) and run over the exec-summary template family, not over a brief page, and no anchor in the brief markup carries those four sections. The named check exists and runs; whether it measures THESE numbers on THIS surface is the next question, and per-row naming is what made it askable. - Out of scope, by the DoD's own boundary: a budget stated in prose rather than a Budget table (sprint-planning: 'prefer <= 5 pts per sprint') is not scanned.";
    }
    #DerivedFrom dependency from d0446 to st116;

    // acceptance event (D0121 review-queue sign-off; D0066/D0106 — human-judged, not fabricated)
    verification d0446Accept : Test { :>> id = "380645af-b513-4160-85b4-70793960cb41"; :>> method = VerificationMethod::confirmation; :>> procedureText = "Selected on the decision brief copy-out (fifteenth publish), pasted into chat 2026-09-11: the set of 33 HELD process-change ratifications accepted with one word, this record being one member (D0406 named it in the table). No note added. - their words, verbatim: “Accept the set: each of the 33 rules named in the table is recorded accepted on its own, quoting these words (recommended)” WARN: read-back - the quoted words do not name d0446 (D0201 B); recorded as given (D0423)."; }
    part d0446AcceptR1 : TestResult { :>> id = "8846f384-fb42-4ebb-8ff6-3534a53885c6"; :>> outcome = VerdictKind::pass; :>> judgedAgainst = "3e6c518"; :>> judgedAt = "2026-09-11"; :>> judgedBy = "wweatherholtz"; :>> createdBy = "claudeOpus5"; }
}
