// D0260 (status: the `status` field below is the truth) — Guard 55, sprint-closure: a sprint the work has moved on from may not carry an unstamped task
// Recorded via `keel record decision` (D0105 RMWX axis; issue054). Acceptance is a separate explicit
// human gate (method=confirmation, D0106): flip status + add the d0260Accept event on sign-off.
package Decision0260 {
    private import EngineElement::*;
    private import EngineWork::*;
    private import EngineVerification::*;
    private import EngineRelationships::*;

    // #SafetyChange (D0070) - this Decision governs a process/schema change; the co-committed
    // change rides the process-change guard's hard lock.
    #SafetyChange part d0260 : Decision {
        :>> id = "ed921a8c-03c8-47dc-b724-c978ef528e3b";
        :>> title = "Guard 55, sprint-closure: a sprint the work has moved on from may not carry an unstamped task";
        :>> createdAt = "2026-08-30";
        :>> createdBy = "claudeOpus5";
        :>> status = DecisionStatus::accepted;
        :>> context = "The human asked why finished work is being confused for open work, and whether the cause was the unenforceable check we dropped or verifiable-work-flagged-as-unverified. The measured answer is narrower than the question assumed, and one half of it is my own reporting error. MEASURED: 496 sprint files, 495 tasks scanned. ONE miss ever - sprint 483, whose story was finished and verified on 2026-08-28 with its TestResult never appended, so the ready frontier served finished work as open for three weeks. Every other sprint stamps every task. Not a pattern; a single miss. THE SECOND 'INSTANCE' WAS NOT ONE. I reported dcRenameIsAChange (the Critical) as the same shape. It is the opposite: the guard-side code fix had landed at ddba1cd, but the DoD's required two-direction VERIFY had never been run and NO test covered the rename class (confirmed - keystone_sees_renames.rs is the first). Proof is part of done here and the DoD said so explicitly. The frontier was RIGHT to hold it open, and I framed a correct flag as a bookkeeping artifact. NEITHER HYPOTHESIS HOLDS. The dropped check was a DoD-WORDING gate ('resolves in part'), removed because it false-positived on backlog.sysml prose; it never touched stamping. And unverifiable work is not being flagged - the inverse happened, which is the more dangerous direction.";
        :>> decision = "Guard 55, sprint-closure: for every delivery file except the highest-numbered one, each task declared in its action def must have a TestResult whose name starts with the task name. Violation names both the task and its sprint. The HIGHEST-numbered sprint is exempt - an in-progress sprint has unstamped tasks by definition, and gating it would make the guard a lockout. Opening sprint N+1 is the objective, self-declared event that says N is no longer in progress. Armed by four probes (sprint_closure_actually_bites.rs): the refuse case reproduces sprint 483; the allow case pins the in-progress exemption; a third proves appending the result CLEARS the violation; a fourth asserts the live tree scans >400 tasks clean, so a mis-scoped guard cannot pass by seeing nothing. The sprint 495 retro is corrected in place to say all of the above, since a successor reading 'the same shape' would draw the wrong lesson.";
        :>> rationale = "WHY A CONTROL FOR A 1-IN-496 EVENT. Because it is a RATCHET, not a new burden: the rule is already observed 496 times out of 496, so the guard starts at zero violations and costs no one anything. It converts a perfect de-facto convention into an enforced one. That is the cheapest kind of control to justify and the easiest to keep - the opposite of a rule imposed on a population that is not already complying. WHY THE EXEMPTION IS THE LOAD-BEARING PART. Without it this guard blocks every commit during an open sprint - it would be issue272 exactly: a control that prevents an illegitimate state by forbidding a legitimate one, which trains bypasses. The exemption is objective (a file number), not a judgment call, and the refuse/allow probe pair pins both sides so a future edit cannot quietly widen or narrow it. WHY NOT A HEAVIER PROCESS. The human asked for 'a strong process'. The measurement says the discipline is already near-perfect and the single miss has a mechanical cause with a mechanical fix. A ceremony added on top of a 495/496 record would be process for its own sake - and D0258's priority-assessment step, one day old, already caught this instance by obliging a read of the frontier's head. Control plus existing step, no new ceremony. WHAT THIS DOES NOT FIX. A task stamped with a result that is WRONG - a pass appended for work not actually done - is untouched by this guard and belongs to the attestation surface (D0232), not here. Naming that boundary so nobody reads this guard as proof of honest evidence.";
        :>> consequences = "55 guards. keel guard sprint-closure runs in the standard set and the commit tier. Zero violations at adoption. The frontier's 'ready' now means what it says for closed sprints: an unstamped task cannot survive the opening of the next sprint. The sprint 495 retro finding is corrected rather than left standing. This Decision rides the keystone lock as a #SafetyChange (guards.rs).";
    }

    // acceptance event (D0121 review-queue sign-off; D0066/D0106 — human-judged, not fabricated)
    verification d0260Accept : Test { :>> id = "c768dd98-1dec-40b0-82a8-6662667fd064"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0260AcceptR1 : TestResult { :>> id = "96bc2cb3-3bb6-46ad-a663-34f989b530bc"; :>> outcome = VerdictKind::pass; :>> judgedAgainst = "761e2e2"; :>> judgedAt = "2026-08-30"; :>> judgedBy = "wweatherholtz"; }
}
