// D0247 (status: the `status` field below is the truth) — STPA is a process keel deploys, not a Need and not a core function
// Recorded via `keel record decision` (D0105 RMWX axis; issue054). Acceptance is a separate explicit
// human gate (method=confirmation, D0106): flip status + add the d0247Accept event on sign-off.
package Decision0247 {
    private import EngineElement::*;
    private import EngineWork::*;
    private import EngineVerification::*;
    private import EngineRelationships::*;

    // #ProspectiveChange (D0070) - this Decision governs a process/schema change; the co-committed
    // change rides the process-change guard's hard lock.
    #ProspectiveChange part d0247 : Decision {
        :>> id = "1e2a6069-8b61-41f9-aabd-a11a0d96aec0";
        :>> title = "STPA is a process keel deploys, not a Need and not a core function";
        :>> createdAt = "2026-08-28";
        :>> createdBy = "claudeOpus5";
        :>> status = DecisionStatus::accepted;
        :>> context = "The bottom-up needs pass reported a capability that looked like an unrooted gap: .engine/schema/safety/stpa.sysml declares 15 STPA types, an stpa process and skill exist, `keel arch stpa-inputs` and `keel controls` compute over them, and a safetyEngineerPersona is authored - while no Need in the corpus mentions safety or hazard analysis at all. A keyword scan returned three hits for safety across all 64 Need statements and every one was a viewer FILTERING EXAMPLE, not a capability. Instantiation is thin in the same way: 4 Loss, 9 Hazard and 1 Controller exist, all of them in .tracking/architecture/engine-safety.sysml describing the ENGINE's own hazards. Eleven of the fifteen declared types - LossScenario, UnsafeControlAction, SafetyRequirement, SystemSafetyConstraint, ControlAction, Sensor, Actuator, Feedback, ProcessModel, ControllerConstraint and UcaType - have never been instantiated. The pass presented this as an either/or: safety analysis is a real product capability and needs a Need, or it is speculative scaffolding and needs a superseding Decision, and being neither is the state the engine's own scope rule exists to prevent. The human answered with a third reading, recorded verbatim as st023 and translated as us030: 'STPA is really a process. It's not a need explicitly - some confusion early on while we were building and I didn't have processes defined very strongly. One that I expect to use regularly, but not a core function in the way sysmlv2 representations are.'";
        :>> decision = "STPA is classified as a PROCESS that keel deploys, and is neither a Need nor a core engine function. Three consequences follow and are adopted together. CLAUSE A. No Need is authored for STPA, and none is owed. The absence of a safety Need is not a gap in the Need set and must not be reported or closed as one. The bottom-up pass's finding is answered by classification, not by authoring. CLAUSE B. No superseding Decision retires the safety schema either. The human expects to use STPA regularly, so the capability stays, its process stays deployable, and its 11 uninstantiated types are unused rather than dead - the ordinary state of a process nobody has run yet on this project, not evidence of abandonment. CLAUSE C. The engine's own hazard model in .tracking/architecture/engine-safety.sysml is untouched by this. Those 4 Losses and 9 Hazards are instance data about keel, authored under the control-map work, and they are not the STPA process's own scope. The cause the human named - processes were not strongly defined when the safety schema was authored - is recorded as fact, because it explains why a process arrived shaped as a schema and predicts that other early artifacts may carry the same confusion.";
        :>> rationale = "WHY CLASSIFICATION RATHER THAN A NEED. A Need is a stakeholder outcome that requirements satisfy and tests verify. 'The engine can run STPA' is not an outcome anyone needs from keel; it is a method a project may choose to apply to its own deliverable. Authoring it as a Need would put a method in the outcome tier, and every requirement derived under it would be describing the method rather than anything a stakeholder wanted. WHY NOT SUPERSEDE IT INSTEAD. Superseding is how this engine expresses a scope CUT, and nothing here is being cut. Using a superseding Decision to mean 'this stays but is not a Need' would corrupt the one mechanism the model has for saying work was dropped - the D0126 error, where a Decision credited work against a Need that had already been retired. WHY THIS MATTERS BEYOND STPA. The needs pass treated 'a capability with no Need' as uniformly a defect, and this case shows the classification is three-valued rather than two: a capability may be unrooted, deliberately cut, or a PROCESS whose availability is the point and whose use is a project's choice. The latent-need derivation process, authored separately, must carry this distinction or it will manufacture Needs for every process in the catalogue - which would be the same error at scale. COST OF NOT DECIDING. The safety schema keeps reading as either an unrooted capability or abandoned scaffolding to every future pass, and each pass re-derives the same ambiguity from scratch. This is the second time in one session that a bottom-up finding turned out to need a classification rather than an artifact.";
        :>> consequences = "The safety schema, the stpa process and skill, `keel arch stpa-inputs` and `keel controls` all stay exactly as they are. No file changes. Coverage and rootedness views are unaffected: STPA never appeared in them, which is precisely why the ambiguity was invisible until a bottom-up pass looked at the code rather than the model. The latent-need derivation process gains a required exclusion rule from clause C of the rationale - a deployable process is not a latent Need - and that rule is part of its definition rather than a caveat in its skill. DELIBERATELY LEFT OPEN, and not decided here: whether .engine/schema/safety/ should travel INSIDE the stpa process unit rather than sitting beside the frozen core schema. Clause B implies it - a process unit carries its definition, skill, rules and guards, and a schema its process alone uses is arguably unit content - but moving a schema package is a migration with its own blast radius, and folding it into a classification Decision would smuggle a structural change through on a naming verdict. It is recorded as an open question, not an implication.";
    }

    // acceptance event (D0121 review-queue sign-off; D0066/D0106 — human-judged, not fabricated)
    verification d0247Accept : Test { :>> id = "6da10676-a56a-49e3-a68a-1d142bc78686"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0247AcceptR1 : TestResult { :>> id = "34e57b10-4f40-4763-9418-214b499a8b64"; :>> outcome = VerdictKind::pass; :>> judgedAgainst = "2695768"; :>> judgedAt = "2026-08-29"; :>> judgedBy = "wweatherholtz"; }
}
