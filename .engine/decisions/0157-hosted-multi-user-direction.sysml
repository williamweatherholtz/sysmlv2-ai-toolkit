// D0157 — ACCEPTED (wweatherholtz, 2026-08-17) as a DIRECTION ONLY. Records an intent that causes no
// action (§1.4), derives no requirement, and blocks nothing. It exists so the intent is discoverable
// without taxing every burndown computation until it is real.
// #ProspectiveChange (D0070): records a direction; changes no process definition and no schema.
package Decision0157 {
    private import EngineElement::*;
    private import EngineWork::*;
    private import EngineVerification::*;
    private import EngineRelationships::*;

    #ProspectiveChange part d0157 : Decision {
        :>> id = "c4e07b95-2a61-4f38-8d72-b1509fe6a3c8";
        :>> title = "D0157: hosted multi-user keel with a process marketplace — intended direction, NOT current scope, no requirement derived";
        :>> createdAt = "2026-08-17";
        :>> createdBy = "claudeOpus5";
        :>> status = DecisionStatus::accepted;
        :>> context = "Raised by wweatherholtz on 2026-08-17 while resolving issue132: 'what happens if the service is opened up beyond a local instance? in that case, we'll want multi users with different projects and the ability to have a process marketplace of best practices to implement. I think that direction is more future facing even if the need for genuinely multi user is weak atm.' TWO OF THE THREE PARTS ARE ALREADY REAL, which is why this Decision records less than it first appeared to need. MULTI-PROJECT shipped in sprint 317: the console discovers sibling keel projects, rebinds between them, and reports whether the engine and deliverable models coincide. THE EXCHANGE PRIMITIVES OF A MARKETPLACE shipped in sprint 297: nProcessPortability and srPortCatalogExchange give list / search / export / import / activate / disable over a process UNIT that carries its definition, its deploying skill and the names of the rules and guards a receiving project must activate. What is genuinely absent is HOSTING and DISCOVERY-AT-SCALE — a place to publish to and browse — plus authenticated multi-user access to a running service. keel is ALSO already multi-contributor at the model layer (D0108/D0129: one bound actor per machine, per-actor claim files, merge-only integration, contention recorded for human adjudication); it is the serve console that is local-only and unauthenticated.";
        :>> decision = "RECORDED AS A DIRECTION, WITH NO ACTION AND NO REQUIREMENT. The intent: if keel's service is opened beyond a local instance, it should support authenticated multi-user access, several projects per user, and a hosted catalogue where good processes can be published and adopted. NOTHING is derived from this: no Need, no SystemRequirement, no backlog action. A Need is the wrong home for it and that is the substance of this Decision, not a formality — Needs drive decomposition, so a broad Need whose demand the human himself calls 'weak atm' either sits undecomposed (dropping need_decomposed_pct off 100% and keeping it there) or gets decomposed into auth requirements for a local-only application. THE SECOND OUTCOME IS EXACTLY ISSUE132: N-8's defect was never that it was wrong, but that it was written WIDER THAN THE DEMAND, and a reader three months later decomposed the wide half.";
        :>> rationale = "WHY A DECISION IS THE RIGHT HOME: §1.4 makes a decision that causes no action first-class — 'we intend X, not now' is a fact worth recording, and recording it costs nothing because no computation keys on a Decision's future-ness. Being future-facing in the Decision layer is free; being future-facing in the Need layer is a standing tax on every burndown answer until the future arrives. WHAT WOULD TRIGGER PROMOTION, and this is the record's weakest part, said plainly rather than dressed up: a real second user who cannot work through git, or a real request to publish a process to someone outside a clone. NO DATE IS RECORDED because none was given, and 'not now' ages badly without a trigger — if the hosted service is expected within a release or two, this Decision should be superseded by one that says so, because a direction with no trigger is indistinguishable from a direction nobody will act on. WHY NOT BUILD THE HOSTING NOW: it is the one part with no primitives in place, it sends data outward, and process_cmd.rs already declined the adjacent feature ('opt-in popularity') on the same grounds — that sending usage data outward is a decision for a human and not a detail of a command.";
        :>> consequences = "Nothing changes today, which is the point. A future contributor asking 'was multi-user considered?' finds this instead of silence or a speculative Need. If the direction is taken up, the work starts from Needs authored THEN against demand that exists THEN — and D0115's single-user framing must be revisited at the same time, which issue137 records independently because that phrase is already inconsistent with shipped behaviour. If the direction is abandoned, this Decision is superseded and no requirement, test or backlog item has to be unwound, because none was ever created.";
    }

    // acceptance event (D0121 review-queue sign-off; D0066/D0106 — human-judged, not fabricated)
    verification d0157Accept : Test { :>> id = "9a3c6e40-5d18-4b72-a06f-c47e9b2d1503"; :>> method = VerificationMethod::confirmation; :>> procedureText = "wweatherholtz, 2026-08-17, verbatim: 'yes implement as indicated' — in direct reply to a message whose second named record was 'Record a Decision for the hosted/multi-user/marketplace direction: what it is, why not now, what would trigger it, and explicitly that no requirement is derived from it yet.' The DIRECTION recorded here is quoted from their own words in the message before that one, and the same message contained my argument against making it a Need, which they did not contest. This attests the decision to RECORD the direction without deriving work from it. It is not an attestation that the hosted service will be built, nor that any date applies — no trigger date was given, and the Decision says so."; }
    part d0157AcceptR1 : TestResult { :>> id = "5f81b3d6-4c09-4e27-b8a5-13d70fe4c982"; :>> outcome = VerdictKind::pass; :>> judgedAgainst = "7493b12"; :>> judgedAt = "2026-08-17"; :>> judgedBy = "wweatherholtz"; }

    // ── The trigger this Decision said it lacked. ADDED rather than folded into the text above, because
    // that text carries an attestation and rewriting it would leave the attestation naming words the
    // human never saw (the same reason N-8 was superseded instead of edited, D0156).
    verification d0157Defer : Test {
        :>> id = "7e14ba62-8c05-4d93-a6f1-20fb85c37e49";
        :>> title = "D0157 deferred indefinitely — the trigger is the human reraising it";
        :>> createdAt = "2026-08-17";
        :>> createdBy = "claudeOpus5";
        :>> method = VerificationMethod::confirmation;
        :>> procedureText = "wweatherholtz, 2026-08-17, verbatim: 'defer the hosted service for now. If we get close to needing it, I'll reraise. Otherwise, keep pursuing.' This CLOSES the weakness D0157's own rationale named: it recorded a direction with no trigger, and said plainly that a direction with no trigger is indistinguishable from one nobody will act on. The trigger is now explicit and it is a PERSON rather than a date — the owner of the intent reraises it. That is a stronger trigger than a date for an intent whose demand they described as 'weak atm': a date would come due while the demand had not, and the honest answer at that point would be to defer again. NO WORK IS SCHEDULED BY THIS and none may be derived from it: the deferral is not a plan to build later, it is a decision not to build now, held open by the one person who can tell when that changes."; }
    part d0157DeferR1 : TestResult { :>> id = "b0d7c391-5a28-4e64-8f19-c3e40a7b1d52"; :>> outcome = VerdictKind::pass; :>> judgedAgainst = "PENDING"; :>> judgedAt = "2026-08-17"; :>> judgedBy = "wweatherholtz"; }
}
