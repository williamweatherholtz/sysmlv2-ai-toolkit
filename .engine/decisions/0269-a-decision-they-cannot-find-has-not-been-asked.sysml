// D0269 (status: the `status` field below is the truth) — Decision surfacing: pending judgments lead the response with a durable link, and are carried until answered
// Recorded via `keel record decision` (D0105 RMWX axis; issue054). Acceptance is a separate explicit
// human gate (method=confirmation, D0106): flip status + add the d0269Accept event on sign-off.
package Decision0269 {
    private import EngineElement::*;
    private import EngineWork::*;
    private import EngineVerification::*;
    private import EngineRelationships::*;

    // #ProspectiveChange (D0070) - this Decision governs a process/schema change; the co-committed
    // change rides the process-change guard's hard lock.
    #ProspectiveChange part d0269 : Decision {
        :>> id = "6430b08a-3897-4295-8461-cfe5465754da";
        :>> title = "Decision surfacing: pending judgments lead the response with a durable link, and are carried until answered";
        :>> createdAt = "2026-08-31";
        :>> createdBy = "claudeOpus5";
        :>> status = DecisionStatus::accepted;
        :>> context = "The human, verbatim: 'create a new process - if there are decisions for me to make, always give me a link to the executive summary artifact. Don't bury it under past messages.' THE FAILURE IS MINE AND IT REPEATED. Across this session I reported open decisions accurately and at the END of long turns: the Needs awaiting acceptance, the build order, the CI mechanism, the trust refinement. Each report was true. Each sat under several thousand words of work, and one of them I had already been asked about once - the human had to say 'I'm not seeing an executive summary' before I produced the page at all. The distinction that matters: I was not withholding anything. I was placing it where it could not be acted on. A decision the human cannot find has not been asked, whatever the transcript shows - and 'it was in my message' is the same defence as 'the warning was in the log', which this project has already rejected twice this week (D0258 for the priority-inversion warnings, D0261 for the 61 undischargeable ones).";
        :>> decision = "The decisionSurfacing process, four steps, cadence continuous. DETECT - something is pending when the work cannot honestly continue without their judgment, or continued under an assumption they never confirmed. Explicitly NOT pending: anything I decided and can defend, or a question I can answer by reading the model. Manufacturing decisions to have something to surface is worse than burying one, because it teaches them the page is noise. RENDER - one exec-summary tab per decision, each with its stake, steelmanned options, honest costs, my recommendation and what would change it. The browser suite runs; its word budgets have rejected my drafts three times and the page is better for it. LEAD - the URL goes in the FIRST lines of the response, with a one-line name per pending item. The report of the work follows the link and never precedes it. CARRY - re-surface every turn while anything is pending. A decision leaves the page only when answered or when I STATE that I am withdrawing it.";
        :>> rationale = "WHY AN ARTIFACT AND NOT A FILE CARD. They asked for a link, and a link is materially different: it survives the scroll, reopens from the gallery, and does not depend on finding the message that carried it. Republishing the same file path updates it in place, so there is one address rather than a trail of them - a decision page that forks into several links is buried again, differently. WHY 'CARRY' IS A STEP AND NOT A COURTESY. An unanswered decision that quietly stops being mentioned has been decided by default, by me, invisibly. That is the same failure as the priority-inversion warnings nobody read, arriving through the conversation instead of through a guard - and silence is not consent. WHY THIS CANNOT BE GUARD-ENFORCED, said plainly. No control can read my conversational output; this is the D0151 clause, which binds what I SAY and has no mechanism behind it. What makes it enforceable at all is that the human sees the top of every message: if the link is missing while something is pending, the violation is visible in the first line rather than hidden in the last.";
        :>> consequences = "The catalogue gains decisionSurfacing and its deploying skill, both transferable as a unit. The four decisions currently open are published at a durable URL and lead this response. They stay there, re-linked each turn, until answered or withdrawn. NOT CHANGED: what counts as a decision worth their time. D0204 still holds - sitting review is an optional pull-audit, never a debt owed by them - and this process must not become a channel for manufacturing obligations. It surfaces what is genuinely waiting; it does not generate things to wait on.";
    }

    // acceptance event (D0121 review-queue sign-off; D0066/D0106 — human-judged, not fabricated)
    verification d0269Accept : Test { :>> id = "2c883b31-c708-4269-8f70-d7484284dc50"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0269AcceptR1 : TestResult { :>> id = "ac92a1ca-ee89-401d-ab99-9760e2c455b2"; :>> outcome = VerdictKind::pass; :>> judgedAgainst = "1b13eb0"; :>> judgedAt = "2026-09-01"; :>> judgedBy = "wweatherholtz"; }
}
