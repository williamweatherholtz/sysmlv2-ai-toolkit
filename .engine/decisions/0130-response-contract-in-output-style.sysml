// D0130 (status: the `status` field below is the truth) — The AI's response contract lives in a SYSTEM-PROMPT output
// style, and honest-state gating moves to the turn boundary via a Stop hook. CLAUDE.md stops being
// the sole home of the contract, because it is the weakest layer that can hold it.
// Acceptance is a separate explicit human gate (D0106): flip status + add the d0130Accept event.
// Marked #ProspectiveChange (D0070): work chartered under the prior process stays valid.
package Decision0130 {
    private import EngineElement::*;
    private import EngineWork::*;
    private import EngineVerification::*;
    private import EngineRelationships::*;

    #ProspectiveChange part d0130 : Decision {
        :>> id = "3f21c8ad-9e0b-4c77-8a52-71d6b4e0c913";
        :>> title = "D0130: the response contract is a system-prompt output style; honest-state gating moves to the turn boundary (Stop hook)";
        :>> createdAt = "2026-08-13";
        :>> createdBy = "claudeOpus5";
        :>> status = DecisionStatus::accepted;
        :>> context = "The human asked (2026-08-13) whether the AI's output format can be defined LOCALLY so it is consistent, noting they understood such a direction to be STRONGER than CLAUDE.md. It is, and the distinction is load-bearing. Verified against the harness settings schema and the local configuration: (1) an OUTPUT STYLE (`.claude/output-styles/<name>.md`, selected by the `outputStyle` settings key) modifies the SYSTEM PROMPT; (2) HOOKS in settings.json are executed by the HARNESS, so a `Stop` hook can refuse to let a turn end and feed the violation back — the only layer here that ENFORCES rather than instructs; (3) CLAUDE.md is injected as ordinary user-turn context, the weakest layer that can hold a rule; (4) AI memory is weaker still, and is per-agent rather than project truth. Local state before this Decision: NO output style existed in either user or project scope; the UserPromptSubmit hooks were wired (the triage reminder); and the Stop-hook prototype named in D0128 (.engine/tools/stop_gate.py) existed UNTRACKED and UNWIRED. So the response contract — parse-first routing, no prose state, no fabricated attestation — lived only in CLAUDE.md, with nothing checking it. That is not hypothetical: sprint 247/248 recorded four process-adherence misses (issue082-085) in which the AI bypassed ALREADY-ACCEPTED decisions (D0052 priority ordering, D0047 corrections-become-guards, D0018 no-prose-shadow-truth) and narrated state in prose. Two defects were also found IN the prototype while productionising it: it hardcoded a Windows-only `keel.exe`, so it would have silently NO-OPPED on every other contributor's machine (the issue076 class, reproduced inside the governance control itself), and it decoded subprocess output with the platform default, so its corrective feedback reached the agent as mojibake.";
        :>> decision = "Adopt three layers with explicit roles. (A) The RESPONSE CONTRACT becomes an output style (`.claude/output-styles/keel.md`, `outputStyle: keel`), i.e. system-prompt level: parse-first `Parsed:` routing on EVERY response; never author state in prose (status/priority/next are computed — reorder the backlog and read the view back, D0052/D0018); verify rather than assert (file:line for code claims, read the computed answer back after a change, never trust a transform's self-report); never fabricate a `method=confirmation` attestation and never let provenance default; and correct at the root so a recurrable defect becomes a tracked Issue PLUS an automated control (D0047). (B) The output style is the CANONICAL home of the response contract; CLAUDE.md REFERENCES it and must not restate it, so the two cannot drift into dual truth (D0105, one source of truth). (C) IN-LOOP GATING: the Stop hook runs `keel validate` + `keel guard` at the TURN boundary and BLOCKS the turn from ending while the model is dishonest, feeding the violations back for correction — moving the existing honest-state gate earlier without changing what it means. It is loop-safe (a second consecutive red allows the stop with a loud warning rather than trapping the agent), it never blocks for a reason the agent cannot fix in-loop, and when the binary is absent it says so VISIBLY instead of no-opping. NOT adopted here: Tier-1 (PreToolUse deny) and Tier-2 (PostToolUse per-edit) hooks, which D0128 makes conditional on measurement — keelInLoopGates stays OPEN for them and was deliberately not marked delivered.";
        :>> rationale = "The lever is placement, not wording. Restating the contract more firmly in CLAUDE.md would have changed nothing, because the failure mode was not misunderstanding — it was that an instruction in the weakest layer competes with everything else in context, and nothing detected the bypass. This is D0128's own accepted conclusion ('there is no deterministic prevention for an LLM; the lever is moving the existing gates earlier (in-loop) + shaping affordances… + a concise per-project workflow spec') applied literally: the output style IS that spec, the Stop hook IS the in-loop gate. ALTERNATIVES: (i) strengthen CLAUDE.md wording — REJECTED, same layer, already demonstrated insufficient four times; (ii) put the contract ONLY in a hook reminder (like the existing triage reminder) — REJECTED as insufficient alone: a per-turn reminder is still instruction, and the existing one did not prevent issue084/085; it is complementary, not a substitute; (iii) an MCP surface as the governance mechanism — REJECTED, and D0128 already made this correction explicitly: MCP is a DISCOVERY/ergonomics surface, never an enforcement layer, and letting it masquerade as governance would be a category error; (iv) CHOSEN — system-prompt contract for the instruction plus a harness-executed Stop gate for the enforcement, with CLAUDE.md demoted to a reference so there is one canonical home. RISK ACCEPTED + FLAGGED: a custom output style modifies the default system prompt, so it can suppress default harness behaviours; it is therefore scoped to the response contract rather than attempting to redefine the agent, is committed at project scope so every contributor gets the same one (the consistency the human asked for), and is reverted by removing one settings key. COST: the Stop gate adds roughly 1-2s per turn end. CRITERIA: enforcement-over-instruction x one-canonical-home x reversibility x no-new-authority-layer.";
        :>> consequences = "Adds `.claude/output-styles/keel.md` and sets `outputStyle: keel` + a `Stop` hook in `.claude/settings.json` (project scope, committed, so the contract is identical for every contributor — including the distributed team of D0129). The prototype is productionised with two real fixes: cross-platform binary probing (it would otherwise have silently no-opped off Windows) and explicit UTF-8 decoding of subprocess output. CLAUDE.md is doc-synced to REFERENCE the output style rather than restate the contract, so §3's routing rules have one canonical home. keelInLoopGates remains OPEN — Tier-1/Tier-2 and the measurement D0128 asks for are NOT delivered, and the delivered slice is recorded as its own action rather than closing the broader item. TAKES EFFECT for the human only after the harness reloads settings (open `/hooks` once, or restart); the AI cannot verify a Stop hook fires within the turn that wires it. FOLLOW-ON (not in scope): shipping the output style as an engine artifact deployed by `keel init` so downstream projects inherit it — that belongs with keelProcessPortability, and authoring it in two places now would create the dual truth this Decision exists to remove. Acceptance state is NOT restated here — it is carried by `status` plus the d0130Accept event, which are its only home (decisionNoVerdictProseRule, D0105).";
    }

    // Acceptance event (D0066/D0106 — human-judged, never AI-fabricated). The attestation TEXT is the
    // evidence for a method=confirmation (D0016), so it records what was actually said and the context
    // that makes it an attestation to THIS Decision rather than a general instruction — the standard
    // issue083/dcAttestationSubstance exists to enforce, applied to itself.
    verification d0130Accept : Test { :>> id = "324f537c-de5e-4ef7-af4b-ea5d319f3124"; :>> title = "Human acceptance of d0130"; :>> createdAt = "2026-08-13"; :>> createdBy = "claudeOpus5"; :>> method = VerificationMethod::confirmation; :>> procedureText = "wweatherholtz attests acceptance of d0130 (response contract as a system-prompt output style; honest-state gating at the turn boundary via the Stop hook). Attested 2026-08-13 in session, with the words 'accepted proceed', given IMMEDIATELY AFTER requesting and reading the full authored text of d0130 ('give me text of d0130') — so the attestation is to this Decision's specific content, including its two flagged caveats: that a custom output style modifies the default system prompt and can suppress default harness behaviours, and that clause (B) is not yet fully realised because CLAUDE.md section 3 still restates part of the contract (tracked as issue086). An EARLIER 'agreed, proceed' on 2026-08-13 was deliberately NOT recorded as acceptance: in context it authorised proceeding with the next backlog item and was not an attestation to this Decision (D0016 — a confirmation is never inferred from a general instruction)."; }
    part d0130AcceptR1 : TestResult { :>> id = "38abf29e-410d-4247-a259-7214cf1b5fb1"; :>> outcome = VerdictKind::pass; :>> judgedAgainst = "fd7b9b2"; :>> judgedAt = "2026-08-13"; :>> judgedBy = "wweatherholtz"; }
    part d0130AcceptR2 : TestResult { :>> id = "c1c9e466-0823-4e8c-a004-e4177be5508b"; :>> outcome = VerdictKind::pass; :>> judgedAgainst = "eb0adcf"; :>> judgedAt = "2026-09-04"; :>> judgedBy = "wweatherholtz"; :>> createdBy = "claudeOpus5"; :>> notes = "REBOUND (D0308): AUTO-RE-BOUND under standing consent (D0207/D0308): consequences acceptance-state sentence replaced at 7740eb0 (D0105 dual-truth removal) - editorial, the agreed substance unchanged. Their standing words, verbatim: 'issues raised are automatically accepted. they can be customizedly changed post-fact.'"; }
}
