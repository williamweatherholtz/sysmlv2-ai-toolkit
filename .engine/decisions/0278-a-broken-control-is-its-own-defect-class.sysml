// D0278 (status: the `status` field below is the truth) — A defect in a control is its own class, and the control announces it beside its own verdict
// Recorded via `keel record decision` (D0105 RMWX axis; issue054). Acceptance is a separate explicit
// human gate (method=confirmation, D0106): flip status + add the d0278Accept event on sign-off.
package Decision0278 {
    private import EngineElement::*;
    private import EngineWork::*;
    private import EngineVerification::*;
    private import EngineRelationships::*;

    // #SafetyChange (D0070) - this Decision governs a process/schema change; the co-committed
    // change rides the process-change guard's hard lock.
    #SafetyChange part d0278 : Decision {
        :>> id = "3530d217-662e-4173-a9d0-6ca84c50fa8e";
        :>> title = "A defect in a control is its own class, and the control announces it beside its own verdict";
        :>> createdAt = "2026-09-01";
        :>> createdBy = "claudeOpus5";
        :>> status = DecisionStatus::accepted;
        :>> context = "The human's instruction, in their words: 'when you encounter a huge issue, like guards over/under reporting, they need to be fixed ASAP. make a process that hooks in to what we're doing to identify these kinds of issues, triage them, backlog them, whatever.' THE EVIDENCE THAT THE GAP IS REAL, counted rather than felt. On this one day I found three control defects - the `issues` guard passing a mis-triage, `decision-scaffolding` passing a half-built compound Decision, `ownership` over-reporting on actor attribution - and recorded ZERO of them as Issues. All three went into sprint-retro prose and a commit message, which is the one place D0018 says state must never live. They were true, they were written down, and they were unfindable, uncounted and unactioned. Noticing was never the problem.";
        :>> decision = "A projectMigration-style process, controlDefect, with six steps: notice, establish against the SOURCE, classify the direction, assess what it PASSED while broken, record-and-register in one act, then fix or carry deliberately. Two mechanisms make it more than a rule. FIRST, `.engine/contracts/control-defects.toml` is an authored registry keyed by control name, and `keel guard` prints each registered defect BESIDE that control's own verdict - so a green from a control known to under-report arrives already qualified, at the moment someone is reading it. SECOND, a new guard `control-defect-registry` fails when an entry names a control this binary does not have, carries a direction that is neither over nor under, or points at an Issue that is not OPEN.";
        :>> rationale = "WHY A CONTROL DEFECT IS NOT JUST A HIGH-SEVERITY BUG, and this is the whole argument: an ordinary defect affects what it touched, while a broken control INVALIDATES ITS OWN HISTORY. Every verdict it gave while broken is unverified and nobody knows which. That blast radius is retroactive and unbounded until somebody assesses it - a question no ordinary bug raises and no existing process asks. The human's ASAP follows from the retroactivity rather than from urgency-as-mood: every hour a broken control keeps running, it adds verdicts nobody can trust. WHY THE TWO DIRECTIONS ARE TRACKED SEPARATELY. Over-reporting is loud - somebody hits it - and its damage is to trust: an over-reporting gate is one people learn to route around, which is the D0214 unread-warning failure arriving through a different door. Under-reporting is SILENT; nothing surfaces it, and it is found only by accident or by auditing the control itself. So an under-reporting defect is floored at High regardless of how small the observed case looks, because its severity is not the case, it is the unknown population behind it. And an over-report found is a reason to go looking for the matching under-report, since one wrong predicate usually does both on different inputs. WHY THE ANNOUNCEMENT AND NOT A REPORT. A separate list of known-broken controls is a list nobody reads, which is the exact shape of every failure this codebase keeps rediscovering - VIEW_SUBCOMMANDS, the per-instance fixes of issue322/issue325/issue329, D0252's unbuilt clause. Printing the defect beside the verdict cannot be missed by anyone who reads the verdict, needs nobody to remember, and stops automatically when the entry is removed. REJECTED, a new #ControlDefect marker: markers live in schema/core, which is FROZEN and needs human sign-off, and a contract file carries the same fact with no schema change. REJECTED, gating on DETECTION: you find a control defect by being surprised at a verdict, and no gate can read surprise.";
        :>> consequences = "`keel guard` gains a defect line beside three controls today, and every future one the registry records. Guard count 56 to 57. THE HONEST LIMIT, stated in the process itself rather than left to be discovered: detection cannot be enforced - this is the same class as the response contract's verify-before-asserting clause (D0151), and the process makes the RESPONSE reliable, not the noticing. THE REGISTRY CAN ROT AND IS GUARDED AGAINST ROTTING: a typo'd control name would mean the note never prints, restoring the exact state the registry exists to end, and an entry outliving its Issue would keep qualifying verdicts that are now sound - which is how a true warning becomes noise. Both fail `control-defect-registry`. THREE DEFECTS ARE REGISTERED AND CARRIED, each with a written reason as the process requires: ownership needs a signed Decision because it is guard source; issues needs a choice between two fix shapes because the distinguishing signal is prose; decision-scaffolding needs a Decision to have addressable clauses. None is carried for want of time, which the process names as the one unacceptable reason. WHAT THIS DOES NOT DO: it does not re-check what the three passed while broken. Each invalidation statement says NOT RE-CHECKED and says why - for `issues`, 329 issues; for `decision-scaffolding`, a population that cannot even be enumerated because clauses are prose.";
    }

    // acceptance event (D0121 review-queue sign-off; D0066/D0106 — human-judged, not fabricated)
    verification d0278Accept : Test { :>> id = "15dfad7b-f080-4b9c-80a3-32279cfb2ea0"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0278AcceptR1 : TestResult { :>> id = "53c8d023-9d3c-4493-80bb-55130b4b2f57"; :>> outcome = VerdictKind::pass; :>> judgedAgainst = "a52d81b"; :>> judgedAt = "2026-09-01"; :>> judgedBy = "wweatherholtz"; }
}
