// D0209 (status: the `status` field below is the truth) — adhereNotInvert: strengthen deterministic acceptance and freeze the enforcement core, do not invert the topology
// Recorded via `keel record decision` (D0105 RMWX axis; issue054). Acceptance is a separate explicit
// human gate (method=confirmation, D0106): flip status + add the d0209Accept event on sign-off.
package Decision0209 {
    private import EngineElement::*;
    private import EngineWork::*;
    private import EngineVerification::*;
    private import EngineRelationships::*;

    // #ProspectiveChange (D0070) - this Decision governs a process/schema change; the co-committed
    // change rides the process-change guard's hard lock.
    #ProspectiveChange part d0209 : Decision {
        :>> id = "7be9e9a9-f262-49e5-b999-21641fc6a3ae";
        :>> title = "adhereNotInvert: strengthen deterministic acceptance and freeze the enforcement core, do not invert the topology";
        :>> createdAt = "2026-08-24";
        :>> createdBy = "claudeFable5";
        :>> status = DecisionStatus::accepted;
        :>> context = "The human asked whether to make a deterministic program (keel) the manager that spawns AI agents, to 'make AI fully adhere to process' - and authorized a five-lens panel (docs/reviews/manager-inversion-panel-2026-08-24.md). The panel converged unanimously. THREE FINDINGS: (1) the achievable win is deterministic ACCEPTANCE of indeterminate output, not deterministic behavior - and keel already implements it (computed state + audit-history re-derivation); (2) keel's Stop hook is ALREADY the deterministic turn-manager (~80 percent of the intent, zero rewrite); (3) the inversion does not escape the monitor-modifiable-by-monitored gap the control eval just found (issue236) - it re-hosts it one level up, because an agent-authored orchestrator is still agent-editable, and 'agents add their own processes' institutionalizes exactly that. The full inversion would also reimplement the Claude Code harness (turn loop, prompt assembly, tool mediation) that 440 sprints and every downstream library-consumer lean on.";
        :>> decision = "ADOPT the panel's convergent direction: do NOT invert the topology; strengthen deterministic acceptance and freeze the enforcement core, in this order. (1) BUILD a CI process-adherence audit that re-derives from the tree, on infra the agent cannot touch, that the PROCESS was followed - guard-set never shrank unsigned across the pushed range, every done item has a real passing gate at its own SHA, evidence resolves, ceremony complete (the sound floor; extends audit-history/K15 from state-honesty to process-adherence). (2) FREEZE the enforcement surface: generalize the rules-dir keystone fix so every path a guard reads its own definition from (guard source, hook config, CI workflow) needs a human-signed marked Decision. (3) PROCESS CURSOR + gate-on-transition: promote the already-declared ProcessStep state machine from a reference the AI reads into an executed one (keel advance refuses step N+1 until step N's verify-Tests pass) - the one genuine gap (D0098 deferred order-gating), bounded, no inversion. (4) PROACTIVE post-edit 'that change broke X' prevention (suspect-drift/broken-edge on edit). (5) An opt-in keel run <process> orchestrator is DEFERRED to last, adopted only for transitions where a landed-then-detected bad state is expensive to unwind, only alongside library mode, and only with its own code inside the signed keystone. NOT SOLD as making design QUALITY deterministic - Rice's theorem forbids that; the undecidable residue (is this the right work, a good design, a real verification) stays with the agent irreducibly.";
        :>> rationale = "Every lens reached the same place by a different route: the deterministic manager the human wants already exists as the turn-boundary gate, the achievable guarantee is soundness-over-accepted-state not behavior, and inverting the topology buys only prospective admission at the cost of enlarging the trusted computing base and re-opening the self-modification gap. The increments deliver ~90 percent of trustworthy autonomy at a fraction of the inversion's cost, and break the regress the inversion cannot (separation + signing + independent CI re-derivation). This is a DIRECTION, not a fork: the human may override any clause on the decision issue, and the inversion remains available as clause 5 if they later want prospective admission for a specific expensive-to-unwind transition.";
        :>> consequences = "Chartered as a build sequence: dcProcessAdherenceAudit (this sprint), dcFreezeEnforcementSurface, dcProcessCursor, dcProactivePostEdit; the opt-in orchestrator stays a deferred clause, not chartered. The panel dossier and a version-pinned knowledge record are committed. Overriding on the decision issue reopens the direction.";
    }

    // acceptance event (D0121 review-queue sign-off; D0066/D0106 — human-judged, not fabricated)
    verification d0209Accept : Test { :>> id = "0f781d42-7395-4125-811a-d389582a822c"; :>> method = VerificationMethod::confirmation; :>> procedureText = "AUTO-ACCEPTED under standing consent (D0207): a non-fork direction decision recording the manager-inversion panel's unanimous convergence. Not individually reviewed; override anytime on the decision issue. Standing words: 'issues raised are automatically accepted. they can be customizedly changed post-fact.'"; }
    part d0209AcceptR1 : TestResult { :>> id = "b5b9bec4-780c-4566-a232-bf2b2f3f7915"; :>> outcome = VerdictKind::pass; :>> judgedAgainst = "be3e4c1"; :>> judgedAt = "2026-08-24"; :>> judgedBy = "wweatherholtz"; }
}
