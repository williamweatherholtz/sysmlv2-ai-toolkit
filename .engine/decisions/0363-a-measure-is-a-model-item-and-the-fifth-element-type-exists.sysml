// D0363 (status: the `status` field below is the truth) — measuresAreModelItems: the safety schema gains the fifth STPA element type and the attributes that make a measure verifiable
// Recorded via `keel record decision` (D0105 RMWX axis; issue054). Acceptance is a separate explicit
// human gate (method=confirmation, D0106): flip status + add the d0363Accept event on sign-off.
package Decision0363 {
    private import EngineElement::*;
    private import EngineWork::*;
    private import EngineVerification::*;
    private import EngineRelationships::*;

    // #SafetyChange (D0070) - this Decision governs a process/schema change; the co-committed
    // change rides the process-change guard's hard lock.
    #SafetyChange part d0363 : Decision {
        :>> id = "1a15f2dc-5aac-484d-abf4-cee6492c7824";
        :>> title = "measuresAreModelItems: the safety schema gains the fifth STPA element type and the attributes that make a measure verifiable";
        :>> createdAt = "2026-09-07";
        :>> createdBy = "claudeOpus5";
        :>> status = DecisionStatus::accepted;
        :>> context = "Two gaps were open against the frozen safety schema, both found by reading sources rather than our summaries of them. FIRST: the STPA Handbook (Leveson and Thomas 2018, read at pages 22 to 26 on 2026-09-07) states on page 25 that a hierarchical control structure 'contains at least five types of elements: Controllers, Control Actions, Feedback, Other inputs to and outputs from components (neither control nor feedback), Controlled processes'. This schema had four of the five and our own SOP named four, so every run of the analysis produced four - and the missing class is where an input nobody controls belongs, which is exactly where scenario S-F9 lives: an instrument reads the working tree while the report cites a commit, and the citation is authored by the same process that read the dirty tree. SECOND: the owner's correction, verbatim, 'metadata saying assessed=no is the wrong route. we verify through verification_type=analysis with a matching verification case. we don't embed verification in metadata.' The stored flag was removed the same hour and assessment became a join against ProprietyFinding targets, but the mechanism they named could not be reached at all: `part def Sensor :> Element;` had no attributes, the twenty measures were declared in a contract file, a contract file holds no items, and a verify edge needs an endpoint that resolves. So a measure could be inventoried, guarded and computed into the control structure and still never be verified the way every other element is. The owner authorised the schema change on 2026-09-07: 'we can change schema. proceed'.";
        :>> decision = "The safety schema gains `OtherInputOutput` with a direction and an external party - the handbook's fifth element type, named for the source's own term - and `Sensor` gains the attributes that make a measure a verifiable item: its mechanism, what it measures, its determinism as a four-value enum, the form of its reading, and the feedback it produces. NOT A FORK: the alternative was to guard the string join and leave the measures outside the typed model permanently, which was weighed and priced on the decision brief as ask 4 and declined - it buys typo protection today and forecloses verification forever.";
        :>> rationale = "`determinism` is an enum rather than a string because its four values ARE the point: a run of a tree-deterministic measure is a measurement, a run of a stochastic one is a sample, and nothing on a number says which - which is how a routing probe whose verdicts flipped on two of four cases nearly published a coverage figure (issue392). Free text there would let a reader interpret what should be read. The fifth element type is added rather than approximated, because the alternatives were to record an other-input as feedback, which is false - nobody controls it and it reports on nothing - or to leave it unrecorded, which is what produced a model with no way to express the class its own scenarios needed. Both additions went in one review because both are additions to the same frozen schema and reviewing them together costs less than twice, which the brief stated as the recommended course.";
        :>> consequences = "The twenty measures move out of `.engine/contracts/instruments.toml` and into the model as twenty Feedback and twenty Sensor items, generated from the manifest rather than retyped, and the contract file is DELETED rather than kept as a second home for the same facts. Guard 65 now holds the tree against `Sensor.mechanism` in both directions and a deliberate exclusion is argued in the excluded file itself, where a reader of that file sees it. The computed control structure reads the model, so a sensor row carries its item name and a verification case can point at it - and a stale reference cannot survive, because an authored `sensedFrom` either resolves or `edge-endpoints` fails the tree. Migrate needs no exclusion any more: model items are .tracking data and were never shipped. WHAT THIS DOES NOT DO: it does not assess anything. All twenty measures still compute as UNASSESSED, which is the honest state, and the first propriety tranche is the work this unblocks rather than the work it does. Actuators remain zero and four controllers still have no process model (issue394).";
    }

    // acceptance event (D0121 review-queue sign-off; D0066/D0106 — human-judged, not fabricated)
    verification d0363Accept : Test { :>> id = "2bb0d357-2f70-4fa5-b6d3-04a92f995894"; :>> method = VerificationMethod::confirmation; :>> procedureText = "their words, 2026-09-08, the copy-for-Claude text of the published brief with their selections marked: '[x] Ratify the schema change / [ ] Reverse it / [ ] Discuss (answers: d0363)'"; }
    part d0363AcceptR1 : TestResult { :>> id = "160a44ef-f15f-4d1c-9dfc-e2f7486e7b49"; :>> outcome = VerdictKind::pass; :>> judgedAgainst = "a08f2a1"; :>> judgedAt = "2026-09-08"; :>> judgedBy = "wweatherholtz"; :>> createdBy = "claudeOpus5"; }
}
