// D0458 (status: the `status` field below is the truth) — verbCountClauseReadsTheMeasuredNumber: the visible verb count after the lens collapse and the five folds is 34 top-level verbs (35 dispatch arms) and 51 lenses behind keel show - D0273's under-25 consequence and D0399 option A's landing figure of roughly 20 are reversed to that number
// Recorded via `keel record decision` (D0105 RMWX axis; issue054). Acceptance is a separate explicit
// human gate (method=confirmation, D0106): flip status + add the d0458Accept event on sign-off.
package Decision0458 {
    private import EngineElement::*;
    private import EngineWork::*;
    private import EngineVerification::*;
    private import EngineRelationships::*;

    part d0458 : Decision {
        :>> id = "5f4bb3ff-20a6-4f12-a8b0-c8e6fb8ec10c";
        :>> title = "verbCountClauseReadsTheMeasuredNumber: the visible verb count after the lens collapse and the five folds is 34 top-level verbs (35 dispatch arms) and 51 lenses behind keel show - D0273's under-25 consequence and D0399 option A's landing figure of roughly 20 are reversed to that number";
        :>> createdAt = "2026-09-12";
        :>> createdBy = "claudeFable5";
        :>> status = DecisionStatus::accepted;
        :>> context = "D0273 (accepted) stated as a consequence that the lens collapse leaves the visible verb count under 25. issue338 recorded that the number was written without deriving it from the same Decision's own measurement (43 lenses of about 111 arms implied roughly 66). D0399 put the two honest resolutions to the human as a fork and they chose option A, fold the five remaining families, whose text said the folds land the count at roughly 20 and make D0273's clause true as written. The five folds are landed: D0446 rendering, D0447 orientation, D0451 authoring, D0452 gating, D0453 channel, sprints 678 to 683, each a D0067 transform with a byte-equality baseline, and every per-fold delta read back from the tree as stated. The count did not reach 20 or 25 because option A's own arithmetic never said it would: 70 verbs at 649b433, 38 names removed since and 2 added (github, judge-set), is 34 - the census fact cliFamilyCensus reads those numbers from cli_facts.rs at both trees (issue507). d0457 put the remaining choice to the human on 2026-09-12 with the counts - fold ten or more of the remaining names away, or amend the clause to the measured number - and they chose B in their own words on the brief copy-out: 'B: amend the clause to the measured number - 34 verbs, 51 lenses behind show - by two clause corrections, no code (recommended)'.";
        :>> decision = "The measured surface is the number the record states. At 25527cc the top-level surface is 34 verbs, declared as CliCommand facts in .engine/cli/commands.sysml and cli_facts.rs outside the lens family (governance 8, integration 8, distribution 6, gating 4, rendering 3, channel 2, authoring 1, orientation 1, knowledge 1), reached through 35 dispatch arms in keel-cli/src/main.rs (the 35th arm is the --version flag alias of version), with 51 lenses behind the one router keel show. This Decision carries two #SupersedeClause edges. To d0273 it reverses only the consequence 'the visible verb count falls from roughly 111 dispatch arms to under 25': the collapse took 111 arms to 70 verbs and 37 lenses, and the five folds that followed took it to 34 verbs and 51 lenses; every other clause of D0273 - one router, no alias window, byte-equality verification, the ICD authored against the post-collapse surface - stands. To d0399 it reverses only option A's landing figure 'lands the verb count at roughly 20 and makes D0273's clause true as written': option A's course, its five folds and their Decisions stand in force as chosen. No further fold is chartered by this Decision; the verbs that remain name distinct acts, and the governance verbs are the words the human's acceptance is bound to (D0192, D0289, D0312). The number lives here and in the read-back: keel show hardening helpCoverage.dispatched reads 35, the census fact cliFamilyCensus.topLevel reads 34, and the two agree with this text. NOT A FORK: the human chose the course on d0457; this Decision records the number that choice binds.";
        :>> rationale = "A criterion an accepted Decision states, that the work cannot meet and that was never derived, is worse than either honest course: it keeps the task that owns it undone forever and teaches that a Decision's number is decoration. The human weighed the two costs - the record's accuracy at no code, or a smaller typed surface at the cost of renaming the words their own acts are bound to - and chose the correction. Recording the measured number in a Decision that names both reversed clauses by edge (D0398: supersession is said once, by an edge that carries its scope) leaves D0273's and D0399's other clauses in force and makes the count a fact the tree can be read against, which is what the DoD of dcRemainingCliFamilies asks: hardening reads back the number the standing Decision states, and the two agree. NOT A PROCESS CHANGE: no workflow, gate, schema, guard or hook changes; two edges and one stated number.";
        :>> consequences = "dcRemainingCliFamilies closes on the read-back its DoD names: keel show hardening helpCoverage.dispatched 35 against the 35 this Decision states, cliFamilyCensus.topLevel 34 against the 34 stated. issue338 (D0273's under-25 miss) and issue507 (option A's landing figure) resolve by that closure. The priority-inversion rows that ranked dcRemainingCliFamilies above the High-class items go with it. keel --help lists 34 names rather than about 18; a newcomer reads them by family. Nothing in the five landed folds moves, and no sixth fold is opened; if the human later wants the typed surface smaller for its own sake, that is a new Decision with its own counts, not a revival of this clause. The brief builder that surfaced d0457 refuses to build once the queue no longer holds that fork, by its own check.";
    }
    #SupersedeClause dependency from d0458 to d0273;
    #SupersedeClause dependency from d0458 to d0399;
    // D0303 layering: the number the human's d0457 option B choice binds
    #DependsOn dependency from d0458 to d0457;

    // acceptance event (D0121 review-queue sign-off; D0066/D0106 — human-judged, not fabricated)
    verification d0458Accept : Test { :>> id = "47dac636-8107-4fb7-b519-05e95e75e3e2"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0458AcceptR1 : TestResult { :>> id = "50fc404f-d5d8-4bf2-bf5c-9655b35ae103"; :>> outcome = VerdictKind::pass; :>> judgedAgainst = "25527cc"; :>> judgedAt = "2026-09-12"; :>> judgedBy = "wweatherholtz"; :>> createdBy = "claudeFable5"; }
}
