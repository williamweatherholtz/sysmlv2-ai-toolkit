// D0439 (status: the `status` field below is the truth) — consentReadsTheTextNotOnlyTheMarker: a Decision whose own text names the marker vocabulary without a marker line is held proposed under standing consent, and guard consent-scope reads the recorded files with the same classifier
// Recorded via `keel record decision` (D0105 RMWX axis; issue054). Acceptance is a separate explicit
// human gate (method=confirmation, D0106): flip status + add the d0439Accept event on sign-off.
package Decision0439 {
    private import EngineElement::*;
    private import EngineWork::*;
    private import EngineVerification::*;
    private import EngineRelationships::*;

    // #ProspectiveChange (D0070) - this Decision governs a process/schema change; the co-committed
    // change rides the process-change guard's hard lock.
    #ProspectiveChange part d0439 : Decision {
        :>> id = "84d0bfc4-9972-425c-afcd-65edeb5686ff";
        :>> title = "consentReadsTheTextNotOnlyTheMarker: a Decision whose own text names the marker vocabulary without a marker line is held proposed under standing consent, and guard consent-scope reads the recorded files with the same classifier";
        :>> createdAt = "2026-09-10";
        :>> createdBy = "claudeOpus5";
        :>> status = DecisionStatus::accepted;
        :>> context = "D0337 scoped standing consent to the existing processes: a Decision carrying a process-change or safety-change marker stays proposed for the human. The write path applied that rule by reading the draft's marker line and nothing else. On 2026-09-10 D0432's consequences read 'Process-change (D0337): it changes what the D0425 verifier runs, so it waits for the human's word' - the author had classified it, in the record's own words, as outside the consent - and its draft had no marker line, so it auto-accepted with a confirmation result judged by the human for a process change the human never saw. The recording session caught it by reading the write path's output and re-recording; nothing in the engine would have (issue460). Measured against the 151 auto-accepted Decisions in the tree: 104 carry a marker part and predate D0337, and one unmarked text (d0367) names the vocabulary in passing.";
        :>> decision = "NOT A FORK: this closes the gap issue460 names with the rule D0337 already states. An unmarked draft whose context, decision, rationale or consequences name process-change, safety-change, ProspectiveChange or SafetyChange as a whole word (case-insensitive) is HELD proposed under standing consent exactly as a marked one is: the write path prints why it was not accepted and writes one hold line under the record's header, which acceptance removes with the header it annotated. The author's way out is the NOT A FORK pattern: 'NOT A PROCESS CHANGE: <why>' in a field clears a mention in passing; otherwise they add the marker line and re-record, or a human accepts with their quoted word. Guard 71 consent-scope reads every AUTO-ACCEPTED Decision under .engine/decisions/ with the same classifier (deck::marker_words) and fails one that carries a marker part dated on or after 2026-09-06 or names the vocabulary unmarked dated on or after 2026-09-10; the 104 and the one before those dates are counted history.";
        :>> rationale = "The consent's boundary is a judgment the author makes when they write the text, and the marker line is only how the write path was told about it; when the two disagree the text is the honest one, because it is what a reader sees. Reading the text costs a whole-word scan of four fields at record time and closes the class rather than the instance - D0425's own record went the same way as D0432 (issue346), so the shape has recurred. One classifier for the hold and the guard is what makes a hand-edited or hand-accepted file unable to pass what the write path would have held; two implementations would drift the way the marker line and the text drifted. The guard scans only automatic acceptances: a human's own acceptance is theirs to give whatever the text says, so this binds the agent's act alone (D0426). What would change it: a rate of held Decisions that were genuinely inside the consent - the NOT A PROCESS CHANGE escape exists for that, and the ledger will show how often it is needed.";
        :>> consequences = "keel record decision holds an unmarked draft whose text names the vocabulary when standing consent is declared, and prints an advisory when it is not. write::note_marker_hold writes the hold line and rewrite_proposed_header removes it at acceptance. Guard 71 consent-scope joins GUARD_NAMES with a constraint-def identity, a catalogue row and a control-map row bound to EHZ3 and EHZ7. The classifier lives in deck.rs beside the fork classifier it mirrors; four unit tests, one write-path test and four end-to-end runs against a scaffold are the D0388 pair. CLAUDE.md sec 4's standing-consent paragraph names the hold. Process-change (D0337): a guard is added to the enforcement surface, so this Decision waits for the human's word. issue460 resolves through dcMarkerTextWithoutMarkerHolds. What accepting binds: a Decision's prose can hold it outside the consent. What it forecloses: an unmarked text that classifies itself as a process change auto-accepting.";
    }

    // acceptance event (D0121 review-queue sign-off; D0066/D0106 — human-judged, not fabricated)
    verification d0439Accept : Test { :>> id = "4714f3ee-f65f-4df7-b865-526681175d93"; :>> method = VerificationMethod::confirmation; :>> procedureText = "Selected on the decision brief copy-out (fifteenth publish), pasted into chat 2026-09-11: the set of 33 HELD process-change ratifications accepted with one word, this record being one member (D0406 named it in the table). No note added. - their words, verbatim: “Accept the set: each of the 33 rules named in the table is recorded accepted on its own, quoting these words (recommended)” WARN: read-back - the quoted words do not name d0439 (D0201 B); recorded as given (D0423)."; }
    part d0439AcceptR1 : TestResult { :>> id = "236d0933-3c36-4d2b-a6b4-80fa0acfb336"; :>> outcome = VerdictKind::pass; :>> judgedAgainst = "3e6c518"; :>> judgedAt = "2026-09-11"; :>> judgedBy = "wweatherholtz"; :>> createdBy = "claudeOpus5"; }
}
