// D0325 (status: the `status` field below is the truth) — recallInheritsFromTheTopSeeds: a neighbour of one of the three best-scoring seeds inherits that seed's score, and a payload shows at most 13 rows
// Recorded via `keel record decision` (D0105 RMWX axis; issue054). Acceptance is a separate explicit
// human gate (method=confirmation, D0106): flip status + add the d0325Accept event on sign-off.
package Decision0325 {
    private import EngineElement::*;
    private import EngineWork::*;
    private import EngineVerification::*;
    private import EngineRelationships::*;

    part d0325 : Decision {
        :>> id = "e1036116-4cbc-4e68-b3db-8580ace2b530";
        :>> title = "recallInheritsFromTheTopSeeds: a neighbour of one of the three best-scoring seeds inherits that seed's score, and a payload shows at most 13 rows";
        :>> createdAt = "2026-09-05";
        :>> createdBy = "claudeOpus5";
        :>> status = DecisionStatus::accepted;
        :>> context = "issue367 / recallRanksLinkedRecordsAsWellAsGrepDoes: on the 50-case linked-record set the ranked recall payload showed the target 37 times where the grep-plus-one-hop control found it 48 times in a mean 13 unranked candidates. The diagnostic added to the bench this sprint (where the SOURCE record landed) showed every miss had the source at position 1 to 3: the ranker found the record the words named and failed to follow its edges, because a neighbour's lift was half the seed's score divided by the root of its degree, which 29 other seeds' own lexical scores outrank. The DoD required the mechanism to be chosen on the 50-case set and only then read against the eight hand-written questions, never fitted to them.";
        :>> decision = "In brief_from_seeds, the neighbours of the top INHERIT_SEEDS = 3 lexical seeds inherit that seed's score decayed by rank (INHERIT_DECAY = 0.7), taking the larger of that and the existing degree-normalised lift; and a payload shows at most PUSH_ROWS = 13 rows, stating the cap in its truncation line. Chosen on the 50-case set: top-1 44/50, top-2 48/50, top-3 49/50 (48/50 within 13 rows, median position 2, 38 of 48 in the top three), top-5 no better; decay 0.7 against 1.0 indistinguishable on hits; a dominance ratio (1.5 to 3) 39-40/50; a second hop off the general lift neutral at 0.5-1.0 and 45/50 at 2.0; a second hop along the chosen seeds 48/50 at 0.3-0.5 and 46/50 at 0.8 - so no two-hop variant is taken. Result: 48/50 in a mean 13 rows, parity with the control on both measures (McNemar on 47 discordant pairs against the rarest-word control, p < 0.001). The experiment knobs were removed; the constants carry the measurements.";
        :>> rationale = "Why inheritance and not a bigger lift: the failure was not the lift's size but its normalisation - a seed's neighbours were competing against other seeds' own words - and inheriting the seed's score is what the control does when it opens a hit and lists its links; three seeds because the source sat at 1-3 in every miss and top-5 added nothing. Why a row cap: the control's candidate set is 13 and a ranked payload that shows more than an unranked list has not earned its ranking; median position 2 says the cap costs little. What the hand set says, read afterwards and NOT fitted: 5 of 8, unchanged from before this change - the two d0129 questions and the d0176 question sit two hops from every lexical match, and every two-hop variant measured on the 50-case set either did nothing or cost hits there; the one variant that reached 7/8 on the hand set (a general second hop at factor 2.0) took the 50-case set to 45/50 and was rejected on that ground. The DoD's hand-set clause (7/8 or better) is therefore NOT met, and the DoD result records fail with these numbers rather than a pass with a story; the item stays on the frontier for a mechanism that reaches two hops without costing the linked-record set.";
        :>> consequences = "Recall payloads are shorter (13 rows) and lead with the source's linked records. recall_bench.py prints where the source landed for every case, so a lexical miss and a traversal miss are told apart on the next run; both harnesses pass KEEL_RECALL_* environment knobs through to the binary for future experiments (none are read today). recallRanksLinkedRecordsAsWellAsGrepDoes carries a FAIL result citing 48/50@13 and 5/8; issue367 stays open. NOT A FORK: this Decision chooses one course; the options it names are the measurements that rejected the others.";
    }

    // acceptance event (D0121 review-queue sign-off; D0066/D0106 — human-judged, not fabricated)
    verification d0325Accept : Test { :>> id = "32e264f6-d2a5-4062-819a-683021255ff5"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0325AcceptR1 : TestResult { :>> id = "ae603f1f-f4af-4e9c-9148-9f3ef14b7139"; :>> outcome = VerdictKind::pass; :>> judgedAgainst = "2478290"; :>> judgedAt = "2026-09-05"; :>> judgedBy = "wweatherholtz"; :>> createdBy = "claudeOpus5"; }
}
