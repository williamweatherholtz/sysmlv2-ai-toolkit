// D0360 (status: the `status` field below is the truth) — controlsAreProvenNotAsserted: a control is UNPROVEN until a test constructs its defect and shows the control reporting it
// Recorded via `keel record decision` (D0105 RMWX axis; issue054). Acceptance is a separate explicit
// human gate (method=confirmation, D0106): flip status + add the d0360Accept event on sign-off.
package Decision0360 {
    private import EngineElement::*;
    private import EngineWork::*;
    private import EngineVerification::*;
    private import EngineRelationships::*;

    // #SafetyChange (D0070) - this Decision governs a process/schema change; the co-committed
    // change rides the process-change guard's hard lock.
    #SafetyChange part d0360 : Decision {
        :>> id = "53de224c-0a88-4452-baa1-98d38e43b86d";
        :>> title = "controlsAreProvenNotAsserted: a control is UNPROVEN until a test constructs its defect and shows the control reporting it";
        :>> createdAt = "2026-09-06";
        :>> createdBy = "claudeOpus5";
        :>> status = DecisionStatus::accepted;
        :>> context = "This project computes two things about a control: whether it is DECLARED (a typed edge says it covers a failure condition, D0195) and whether it is ARMED (a probe says it can physically fire, D0217, added because `core.hooksPath` was once pointed at a null device while the controls view truthfully reported no uncovered hazard). Neither answers the only question that separates a control from a control-shaped thing: has anyone ever constructed the defect and watched this control report it. Today that evidence, where it exists at all, lives in commit messages. A census over test function bodies (`.engine/tools/guard_proof_census.py`, first run 2026-09-06) puts numbers on it: of 64 enforced guards, 16 are named in a test that asserts a failure, 21 are named only around passing assertions, and 27 are named in no test body at all. TWO INSTANCES FROM ONE DAY, both mine. Guard 64 gate-environment-parity was probed by hand - the token stripped out, the guard shown to fail, the guard restored - and the receipt for that probe is a sentence in a commit message, not a test; the guard sits in the 27. And the self-check written for issue389 to stop the facts script naming a version literal PASSED CLEANLY while scanning only the source above itself, which excluded the entire section it existed to police; it was caught by a deliberate probe, and nothing would have caught it otherwise. A clean pass on a clean tree is not evidence about what a control catches, and treating it as evidence is how a blind control earns credit.";
        :>> decision = "A control's proof state is computed and reported as a third state beside declared and armed: PROVEN when a test constructs an instance of the defect and asserts that this control reports it, UNPROVEN otherwise, with the count and the unproven list surfaced rather than a bare share. NOT A FORK: the alternative is to keep crediting controls on a clean pass, which is the state that produced both of today's instances, and no third shape exists - a control either has a demonstrated catch or it has an assertion that it would catch.";
        :>> rationale = "The propriety process already names mutation testing as the grounding of its `overfit` lens - a control must kill variants, not the specimen - so the standard is not new; what is missing is that nothing computes whether it was met, so meeting it depends on whoever wrote the control choosing to probe it and then remembering to leave the probe behind. That is manual vigilance, which this project has already ruled is not a control (D0047). Reporting the count rather than gating on it is deliberate and follows D0088: no defensible threshold for 'share of controls proven' exists, and gating on one would be answered by writing whatever test makes the number go up, which is the Goodhart failure the indicator rule exists to avoid. The unproven LIST is the actionable half - it names 27 specific guards a reader can go and probe - and the number's only job is to say whether that list is growing.";
        :>> consequences = "Every new control now owes a demonstrated catch, and the absence of one is visible instead of implicit. The 27 currently unproven guards are named rather than quietly grandfathered: they were correct-when-written and stay in force, but nothing claims they were shown to work. The census tool is textual and says so - a guard exercised by a fixture that never names it counts as unnamed, and a guard whose only test asserts a clean tree counts as named-but-unproven, which is the right way round for this question. The immediate obligation this creates on me is the test for guard 64 that should have accompanied it. WHAT THIS DOES NOT DO: it does not make a proven control correct - a test can construct the wrong defect, which is the `overfit` lens's question and stays a matter of judgment rather than counting.";
    }

    // acceptance event (D0121 review-queue sign-off; D0066/D0106 — human-judged, not fabricated)
    verification d0360Accept : Test { :>> id = "676d85a2-ad24-4f7c-a739-aca7851f3cb5"; :>> method = VerificationMethod::confirmation; :>> procedureText = "their words, 2026-09-08, the copy-for-Claude text of the published brief with their selections marked: '[x] Accept the rule / [ ] Report only, require nothing / [ ] Drop it / [ ] Discuss (answers: d0360)'"; }
    part d0360AcceptR1 : TestResult { :>> id = "dbae96bb-3a88-46dd-adbf-101a1557058a"; :>> outcome = VerdictKind::pass; :>> judgedAgainst = "a08f2a1"; :>> judgedAt = "2026-09-08"; :>> judgedBy = "wweatherholtz"; :>> createdBy = "claudeOpus5"; }
}
