// D0262 (status: the `status` field below is the truth) — The federation test platform: eight claims about a downstream keel project, each paired with the observation that would refute it
// Recorded via `keel record decision` (D0105 RMWX axis; issue054). Acceptance is a separate explicit
// human gate (method=confirmation, D0106): flip status + add the d0262Accept event on sign-off.
package Decision0262 {
    private import EngineElement::*;
    private import EngineWork::*;
    private import EngineVerification::*;
    private import EngineRelationships::*;

    // #ProspectiveChange (D0070) - this Decision governs a process/schema change; the co-committed
    // change rides the process-change guard's hard lock.
    #ProspectiveChange part d0262 : Decision {
        :>> id = "c5b34df0-344b-4156-8f80-d63707b55706";
        :>> title = "The federation test platform: eight claims about a downstream keel project, each paired with the observation that would refute it";
        :>> createdAt = "2026-08-30";
        :>> createdBy = "claudeOpus5";
        :>> status = DecisionStatus::accepted;
        :>> context = "The human asked whether a NEW keel project actually works in a federation - issues reaching keel, processes picked up, a locally-authored process reaching upstream, numbering reset, initialisation complete, and whether the instantiated project confuses keel's purpose with its own. They asked for a designed suite, a panel critique of the design, implementation, and a second panel with findings, with empirical evidence recorded at every step. RECONNAISSANCE FIRST, so the design rests on observation rather than memory. A real project was scaffolded and probed. Two of the seven questions already have answers, and they disagree with each other: - NUMBERING IS FINE: the first decision allocates d0001 alongside 261 ReferenceDecisionNNNN packages, validate clean, duplicate-identity 361 scanned 0 violations. D0139/issue291's disjoint-prefix fix holds. - INITIALISATION IS NOT: at a 150-character parent path, `git add -A` FAILS - `unable to index file .engine/reference/decisions/0137-a-release-is-verified-by-running-the-published-asset.sysml` at 249 characters, over the Windows MAX_PATH margin git refuses without core.longpaths. The same scaffold at C:/kt1 stages 484 files clean, which discriminates path length from a corrupt scaffold. A fresh project cannot make its FIRST COMMIT (issue313). - AND THE UPSTREAM ISSUE PATH DOES NOT EXIST AT ALL: keel's entire GitHub surface is the DECISION channel (outbound decisions, inbound approval gestures). There is no command by which a downstream project files an issue against keel, and none by which keel ingests one. The human's second instruction - add a process and skill to ingest GitHub issues - is the inbound half of that missing loop.";
        :>> decision = "EIGHT CLAIMS. Each is stated with the observation that REFUTES it and with the vacuity trap that would let it pass while testing nothing - because a federation suite is exactly the kind that passes on an empty tree. F1 A SCAFFOLDED PROJECT CAN MAKE ITS FIRST COMMIT. Refuted by: git add failing at a realistic path depth. Vacuity trap: testing only at a short path, which is the condition under which it already works. F2 NUMBERING RESETS AND CANNOT COLLIDE. The first decision is d0001 and duplicate-identity is clean. Vacuity trap: passing on a tree with no reference decisions - so the test must ASSERT the ReferenceDecisionNNNN population is non-empty before concluding anything from the absence of collision. F3 THE PROJECT IS NOT CONFUSED ABOUT WHOSE PURPOSE IT SERVES. Its OWN business model is empty at init and its OWN decisions directory is empty, while keel's rationale is present and namespaced as reference. Vacuity trap: an emptiness assertion passes trivially on a scaffold that shipped nothing, so the test must assert BOTH - reference present AND own empty - or it proves only that init did little. F4 A LIBRARY UNIT IS PICKED UP, AND AVAILABILITY IS NOT ACTIVATION. Import lands the files; the unit's guards stay OFF until activate. Both halves, because either alone is satisfiable by a broken implementation. F5 A PROCESS AUTHORED DOWNSTREAM REACHES THE FLEET. A unit published from project A is importable into project B. Vacuity trap: asserting the publish command exits 0 - which it does when it writes nothing, since a no-op publish is a legitimate answer (D0259). The test must observe the unit ARRIVING in a project that did not have it. F6 A DOWNSTREAM PROJECT CAN FILE AN ISSUE AGAINST KEEL. Requires a mechanism that does not exist; this claim's first outcome is its construction. The issue must carry which project raised it, or upstream cannot tell a field report from keel's own note. F7 A GITHUB ISSUE BECOMES A TRACKED ISSUE. With source provenance, IDEMPOTENTLY (re-ingesting the same issue must not create a second item), and WITHOUT fabricating a resolver - `record issue` requires one, and inventing it to satisfy the API would be the intake defect D0216 exists to prevent. Vacuity trap: a test that ingests from a fixture only, never proving the parse matches what GitHub actually returns. F8 INITIALISATION IS COMPLETE AND THE CONTROLS ARE ARMED. The pin is stamped and BINDING (a skewed binary refuses writes); an unbound actor refuses writes; the hook surface is present; the gate is green. Vacuity trap: asserting files EXIST rather than that they BITE - the arming distinction (D0253). NETWORK POLICY, decided here rather than discovered during implementation: F6 and F7 are split into a PURE half (parse, dedupe, provenance, refusal - fixture-driven, always run) and a LIVE half (one real round trip against the actual repo, run only when a token is present and SKIPPED-with-a-statement otherwise). A suite that silently skips its only real-world contact and reports green is the failure this split exists to prevent.";
        :>> rationale = "WHY CLAIMS-WITH-REFUTATIONS RATHER THAN A LIST OF TESTS. The eliminative stance (D0257): a test that can only confirm is a formality. Naming the refuting observation first is what makes each case discriminating, and naming the vacuity trap is what stops the suite passing on a tree where nothing happened - the specific way federation suites rot, since most of their assertions are about ABSENCE. WHY RECONNAISSANCE BEFORE DESIGN. It already changed the design: F1 exists in its deep-path form only because the shallow-path version passed and the deep-path version did not, and F6/F7 are construction rather than verification because the mechanism turned out to be absent. A suite designed from memory would have asserted an upstream path that does not exist and called it covered.";
        :>> consequences = "The suite is a keel-cli integration test binary, run by CI like every other, with the live half gated on a token. Two defects are already outstanding against F1 and F6 before implementation begins: issue313 (first commit impossible at depth) and the missing upstream issue path, which the ingestion process and skill will carry. This Decision is the artifact the first panel critiques. Its findings are recorded as ProprietyFindings against target `design:federation-suite` BEFORE implementation, and a second round runs against the implemented suite.";
    }

    // acceptance event (D0121 review-queue sign-off; D0066/D0106 — human-judged, not fabricated)
    verification d0262Accept : Test { :>> id = "6a1773a5-f357-424a-9f44-a3d0c2495f8b"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0262AcceptR1 : TestResult { :>> id = "f5e98064-dcc8-4e90-8a35-8669c8a3d9c6"; :>> outcome = VerdictKind::pass; :>> judgedAgainst = "9b2f4bf"; :>> judgedAt = "2026-08-30"; :>> judgedBy = "wweatherholtz"; }
}
