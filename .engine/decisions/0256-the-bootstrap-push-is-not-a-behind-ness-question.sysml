// D0256 (status: the `status` field below is the truth) — The pre-push hook skips ref creation as it always skipped deletion, because the bootstrap push of a fresh project is not a behind-ness question
// Recorded via `keel record decision` (D0105 RMWX axis; issue054). Acceptance is a separate explicit
// human gate (method=confirmation, D0106): flip status + add the d0256Accept event on sign-off.
package Decision0256 {
    private import EngineElement::*;
    private import EngineWork::*;
    private import EngineVerification::*;
    private import EngineRelationships::*;

    // #SafetyChange (D0070) - this Decision governs a process/schema change; the co-committed
    // change rides the process-change guard's hard lock.
    #SafetyChange part d0256 : Decision {
        :>> id = "6d207730-19ab-4a09-ace7-572ee8c71cd2";
        :>> title = "The pre-push hook skips ref creation as it always skipped deletion, because the bootstrap push of a fresh project is not a behind-ness question";
        :>> createdAt = "2026-08-29";
        :>> createdBy = "claudeOpus5";
        :>> status = DecisionStatus::accepted;
        :>> context = "The arming probe for ctlPrePushBehind - a two-clone fixture attempting a REAL push through the REAL .githooks/pre-push, built under dcProveTheRemainingControls - failed on its FIRST run, and the failure was the hook's, not the fixture's. The hook verifies behind-ness by fetching main from the remote and checking ancestry. `git fetch origin main` FAILS when the remote has no main yet, and the hook's fail-loud clause (K2) then refuses. So the BOOTSTRAP push - creating main on an empty remote, the first thing every downstream project does after `git init` and adding a remote - was refused, with a message directing the user to `keel land`, which fetches the same nonexistent ref and hits the same wall (issue306, in-field). The asymmetry that caused it: the hook already skipped ref DELETION (local_sha all zeros) under a comment reading 'deleting or creating refs is not a behind-ness question' - half of which was implemented. Ref CREATION (remote_sha all zeros) fell through to the fetch. The self-build never hit this because main existed on its remote before the hook was installed - which is also why it survived unnoticed. Every fresh project would have hit it on day one.";
        :>> decision = "Two clauses. CLAUSE A - THE HOOK SKIPS CREATION AS IT SKIPS DELETION. A push whose remote_sha is all zeros (creating the ref) passes the behind-ness check untouched, exactly as a push whose local_sha is all zeros (deleting it) always has. A ref that does not exist yet has no behind-ness to verify, and refusing to create it is not fail-loud - it is fail-wrong. CLAUSE B - THE PROBE TESTS WHAT THE CONTROL IS FOR. The same probe run exposed that a PLAIN behind push never reaches this hook: git's own client-side fast-forward check refuses it first, from the ref advertisement. The hook's actual added value is the push git would ACCEPT - a FORCED one, the D0129 history-rewrite class. The probe pushes --force, and the assertion demands the refusal come from the HOOK (naming `keel land`), because a refusal from anything else means the hook never fired.";
        :>> rationale = "WHY THE FIX IS THE SYMMETRIC CASE AND NOTHING MORE. The temptation on a fail-loud defect is to soften the loud clause - treat a failed fetch as a warning. That would gut the control: an unreachable remote genuinely is unverifiable, and allowing on unverifiable is the fail-open the clause exists to prevent. The defect was never in failing loud; it was in reaching the fetch at all for a push that has no behind-ness question. Skipping creation is one line, mirrors the deletion case beside it, and leaves K2 intact for every push where the trunk exists. WHY THIS IS marker=safety-change: .githooks/ is enforcement surface under D0209 clause 2, and this Decision rides beside the edit through the keystone lock. It does not weaken the control - it removes a refusal of legitimate work, which is the over-strict failure D0197 warns trains actors to disable gates. WHY THE FORCE-PUSH REFRAMING MATTERS BEYOND THIS HOOK. A control can be real, armed, and still MISAIMED: written for a case something upstream already catches, earning its keep only on a case nobody names. 'What does this control catch that nothing else does' is not answerable from the control map - it took a probe whose first run surprised its author. That question joins the probe discipline for the remaining controls. COST OF NOT DECIDING. Every downstream keel init project is locked out of its own remote on first push, with an error message whose remedy hits the same wall.";
        :>> consequences = "The bootstrap push works. A forced push of a non-descendant is refused BY THE HOOK, proven by test on both sides (the fast-forward creation passes, the forced rewrite refuses). ctlPrePushBehind carries provenBy naming the probe. Controls with evidence: 7 of 15 after this sprint (1 view-probe, 6 by test). The old arming reason - 'can only be established by attempting a push, which a read-only view must not do' - is corrected in place with its history kept: true of the view, false of a test, and the test's first run found two things reasoning had not. issue306 resolves with sprint 488. issue303 narrows to the three infra-resident controls (ctlAuditHistory, ctlBranchProtection, ctlReleaseGateJob), which may legitimately end in a stated reason no local test can reach them.";
    }

    // acceptance event (D0121 review-queue sign-off; D0066/D0106 — human-judged, not fabricated)
    verification d0256Accept : Test { :>> id = "19eef0c3-f4ec-4110-bd27-c01791869d2c"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0256AcceptR1 : TestResult { :>> id = "95985dc8-9664-4710-82f3-c063ee498d1b"; :>> outcome = VerdictKind::pass; :>> judgedAgainst = "cc58613"; :>> judgedAt = "2026-08-29"; :>> judgedBy = "wweatherholtz"; }
}
