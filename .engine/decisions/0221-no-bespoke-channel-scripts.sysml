// D0221 (status: the `status` field below is the truth) — noBespokeChannelScripts: deterministic logic goes in the binary, I/O stays a thin step, policy stays in the process - no bespoke scripts in the channel
// Recorded via `keel record decision` (D0105 RMWX axis; issue054). Acceptance is a separate explicit
// human gate (method=confirmation, D0106): flip status + add the d0221Accept event on sign-off.
package Decision0221 {
    private import EngineElement::*;
    private import EngineWork::*;
    private import EngineVerification::*;
    private import EngineRelationships::*;

    // #ProspectiveChange (D0070) - this Decision governs a process/schema change; the co-committed
    // change rides the process-change guard's hard lock.
    #ProspectiveChange part d0221 : Decision {
        :>> id = "a7d4c14d-69e3-4354-8e44-375b808f9ed0";
        :>> title = "noBespokeChannelScripts: deterministic logic goes in the binary, I/O stays a thin step, policy stays in the process - no bespoke scripts in the channel";
        :>> createdAt = "2026-08-24";
        :>> createdBy = "claudeFable5";
        :>> status = DecisionStatus::accepted;
        :>> context = "The human, on seeing the channel adopted: 'I don't want all these bespoke scripts - if we need something consistently, let us build it into keel or into a process if we need it flexible.' The evidence for that is already in this session. The channel ships 272 lines of bespoke shell and python (.github/scripts/record_decision.sh 130, open_decision_issues.py 142) and every recurring problem with it came from that: record_decision.sh RE-GREPS the login table the binary now owns via williamweatherholtz wweatherholtz, which is two implementations of one rule and precisely how the workflow gate and the recorder drifted apart in the first place (D0219); the gesture vocabulary is a shell with a locale-dependent doing text parsing that nothing unit-tests; the issue-body composer and the override-thread backfill are Python whose only test is production; and I hit escaping defects in these files repeatedly across this session. A bespoke script is also invisible to every keel surface - no guard reads it, no view reports it, and its behaviour cannot be re-derived from the tree, which is the property the whole engine is built on.";
        :>> decision = "The channel is decomposed by KIND, not by convenience. (1) DETERMINISTIC TEXT LOGIC moves into the binary, where it is unit-tested and re-derivable: parsing a comment gesture into verdict plus option, resolving which decision an issue is about from its embedded marker, composing an issue body from a decision card, and deciding idempotency from the comment list. (2) GITHUB I/O stays in the workflow as a thin step calling Work seamlessly with GitHub from the command line. USAGE gh <command> <subcommand> [flags] CORE COMMANDS auth: Authenticate gh and git with GitHub browse: Open repositories, issues, pull requests, and more in the browser codespace: Connect to and manage codespaces gist: Manage gists issue: Manage issues org: Manage organizations pr: Manage pull requests project: Work with GitHub Projects. release: Manage releases repo: Manage repositories GITHUB ACTIONS COMMANDS cache: Manage GitHub Actions caches run: View details about workflow runs workflow: View details about GitHub Actions workflows ALIAS COMMANDS co: Alias for 'pr checkout' ADDITIONAL COMMANDS agent-task: Work with agent tasks (preview) alias: Create command shortcuts api: Make an authenticated GitHub API request attestation: Work with artifact attestations completion: Generate shell completion scripts config: Manage configuration for gh copilot: Run the GitHub Copilot CLI (preview) extension: Manage gh extensions gpg-key: Manage GPG keys label: Manage labels licenses: View third-party license information preview: Execute previews for gh features ruleset: View info about repo rulesets search: Search for repositories, issues, and pull requests secret: Manage GitHub secrets ssh-key: Manage SSH keys status: Print information about relevant issues, pull requests, and notifications across repositories variable: Manage GitHub Actions variables HELP TOPICS accessibility: Learn about GitHub CLI's accessibility experiences actions: Learn about working with GitHub Actions environment: Environment variables that can be used with gh exit-codes: Exit codes used by gh formatting: Formatting options for JSON data exported from gh mintty: Information about using gh with MinTTY reference: A comprehensive reference of all gh commands FLAGS --help Show help for command --version Show gh version EXAMPLES $ gh issue create $ gh repo clone cli/cli $ gh pr checkout 321 LEARN MORE Use `gh <command> <subcommand> --help` for more information about a command. Read the manual at https://cli.github.com/manual Learn about exit codes using `gh help exit-codes` Learn about accessibility experiences using `gh help accessibility` - creating and commenting and closing issues, and committing. The binary does NOT make network calls: a tool that silently performs network I/O is a tool you stop trusting, and the same reasoning already keeps from fetching. (3) POLICY stays in the process definition, where a project can change it without touching code - which gestures mean what, and whether a non-fork auto-accepts. The target state is that disappears: the workflow calls the binary for every decision it makes and Work seamlessly with GitHub from the command line. USAGE gh <command> <subcommand> [flags] CORE COMMANDS auth: Authenticate gh and git with GitHub browse: Open repositories, issues, pull requests, and more in the browser codespace: Connect to and manage codespaces gist: Manage gists issue: Manage issues org: Manage organizations pr: Manage pull requests project: Work with GitHub Projects. release: Manage releases repo: Manage repositories GITHUB ACTIONS COMMANDS cache: Manage GitHub Actions caches run: View details about workflow runs workflow: View details about GitHub Actions workflows ALIAS COMMANDS co: Alias for 'pr checkout' ADDITIONAL COMMANDS agent-task: Work with agent tasks (preview) alias: Create command shortcuts api: Make an authenticated GitHub API request attestation: Work with artifact attestations completion: Generate shell completion scripts config: Manage configuration for gh copilot: Run the GitHub Copilot CLI (preview) extension: Manage gh extensions gpg-key: Manage GPG keys label: Manage labels licenses: View third-party license information preview: Execute previews for gh features ruleset: View info about repo rulesets search: Search for repositories, issues, and pull requests secret: Manage GitHub secrets ssh-key: Manage SSH keys status: Print information about relevant issues, pull requests, and notifications across repositories variable: Manage GitHub Actions variables HELP TOPICS accessibility: Learn about GitHub CLI's accessibility experiences actions: Learn about working with GitHub Actions environment: Environment variables that can be used with gh exit-codes: Exit codes used by gh formatting: Formatting options for JSON data exported from gh mintty: Information about using gh with MinTTY reference: A comprehensive reference of all gh commands FLAGS --help Show help for command --version Show gh version EXAMPLES $ gh issue create $ gh repo clone cli/cli $ gh pr checkout 321 LEARN MORE Use `gh <command> <subcommand> --help` for more information about a command. Read the manual at https://cli.github.com/manual Learn about exit codes using `gh help exit-codes` Learn about accessibility experiences using `gh help accessibility` for every effect it causes.";
        :>> rationale = "The rule that decides the split is whether a thing is DETERMINISTIC and therefore testable. Text parsing is; network effects are not; and what a gesture MEANS is a judgment a project should be able to change, which is the definition of process rather than code. Putting deterministic logic in shell is what produced the two-implementations-of-one-rule defect, the untested parser, and the escaping bugs - and it is unavailable to every keel surface, so nothing can report on it. This also makes the unit smaller rather than larger: fewer carried files, and the ones that remain are the effects rather than the reasoning.";
        :>> consequences = "Chartered as dcChannelLogicInBinary. Until it lands, the two scripts remain unit extras and the channel keeps working - this Decision changes the target, not today's behaviour. When it lands, carries fewer files, the receiving project runs the same tested binary logic the source project does, and the gesture vocabulary becomes a fact in the process definition rather than a case statement. The residual risk to name plainly: moving parsing into the binary means a project cannot change the gesture vocabulary without a binary upgrade. I considered declaring the vocabulary as data so the parser reads it, and REJECTED that for now under D0088: nobody has needed a different vocabulary, a config file plus reader plus doc surface is real cost, and a flexibility nobody has asked for is the kind of speculative generality this engine keeps paying for. The vocabulary therefore lives in ONE place - the parser - is documented in the process definition and in `keel github-gesture --help`, and becomes data on the first project that actually needs a different one, which is a CHANGE with a justified boundary rather than a guess.";
    }

    // acceptance event (D0121 review-queue sign-off; D0066/D0106 — human-judged, not fabricated)
    verification d0221Accept : Test { :>> id = "16e155bd-49b2-4eef-ba6e-525a72fb3dcc"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/19."; }
    part d0221AcceptR1 : TestResult { :>> id = "aca96fb6-3f3a-49a1-ba85-0c577c542159"; :>> outcome = VerdictKind::pass; :>> judgedAgainst = "9253f3c"; :>> judgedAt = "2026-08-24"; :>> judgedBy = "wweatherholtz"; }
}
