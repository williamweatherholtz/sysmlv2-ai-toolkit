// D0291 (status: the `status` field below is the truth) — The GitHub decision channel is disconnected - no issue per Decision, no notifications - and standing consent (D0207) is applied by keel record decision at record time, with the single declared decider as judge
// Recorded via `keel record decision` (D0105 RMWX axis; issue054). Acceptance is a separate explicit
// human gate (method=confirmation, D0106): flip status + add the d0291Accept event on sign-off.
package Decision0291 {
    private import EngineElement::*;
    private import EngineWork::*;
    private import EngineVerification::*;
    private import EngineRelationships::*;

    // #SafetyChange (D0070) - this Decision governs a process/schema change; the co-committed
    // change rides the process-change guard's hard lock.
    #SafetyChange part d0291 : Decision {
        :>> id = "206561d6-6b60-4ab7-93fa-a27aab044af0";
        :>> title = "The GitHub decision channel is disconnected - no issue per Decision, no notifications - and standing consent (D0207) is applied by keel record decision at record time, with the single declared decider as judge";
        :>> createdAt = "2026-09-03";
        :>> createdBy = "claudeOpus5";
        :>> status = DecisionStatus::accepted;
        :>> context = "The human (st088): they do not want GitHub issue notifications; disconnect that pipeline; it was not really doing anything anyway. MEASURED before acting, because the last clause is not quite true: since 2026-08-23 the channel auto-accepted 80 non-fork Decisions under standing consent (D0207) with no human act, recorded 2 acceptances from the human's own GitHub comments, and refused one unauthenticated commenter (2026-09-02) - so it WAS the mechanism by which every routine Decision became accepted, and disconnecting it without relocating that mechanism would leave every future Decision proposed until someone typed an acceptance, which is the friction the human named the day before (st074). What it was NOT doing much of: being read - the override thread (issue 29) received the human's own word twice in 137 comments, and the notification per Decision was the cost they felt.";
        :>> decision = "Delete the two workflows (decision-issue.yml, decision-record.yml) and their scripts, the decision-channel process, skill and unit record, and the unit's extras declaration; remove decision-channel from the adopted set. Standing consent moves into the binary: keel record decision, having written a NON-FORK proposed Decision, accepts it immediately when attestation-policy.toml declares standingConsent and github-actors.toml declares exactly one decider - the acceptance note carries the AUTO-ACCEPTED token and quotes the standing words verbatim (which is also what the delegatedAcceptanceSubstanceRule demands), and the declared decider is the judge. A FORK (a Decision carrying OPTION enumerations) stays proposed for the human. With zero or several deciders the Decision stays proposed and the command says why - a judge is never guessed. Override is a superseding Decision (D0290) or the human's quoted word (D0289). github-intake stays: issues coming IN were never the notifications. The three channel-only commands (github-decider, github-gesture, github-decision-id) are marked deprecated in the CLI facts. The channel controller and its process model leave the authored control-structure residue; the computed structure reads the channel role as inert, which is now true. The GitHub recorder actor stays registered as the record that it existed.";
        :>> rationale = "WHY RELOCATE RATHER THAN DROP STANDING CONSENT: the human granted it (D0207) and restated the want the day before - not to type acceptances for everything; dropping it would honour 'no notifications' by breaking 'no friction'. Record time is the only place left that both sees every Decision and runs on the human's machine under their declared deciders. WHY THE SINGLE-DECIDER RULE: the workflow hardcoded one login; the binary must not - github-actors.toml already declares who may decide on THIS project, and one declared decider is the condition under which 'the human' is unambiguous. A scaffold ships no deciders and therefore auto-accepts nothing, which is the right default for a project that has not said who decides. WHY THIS IS A SAFETY CHANGE AND NOT ONLY A CONVENIENCE: the channel was an independent recorder on infrastructure the agent could not edit, and the override thread was a durable public place to say no. Both are gone. What replaces them is weaker on independence and stronger on friction: the acceptance is written by the same binary that proposed the Decision, on the same machine, and the audit trail is the tree - audit-history in CI still re-derives every verdict from committed truth, so the record cannot be silently rewritten, but nothing outside the machine now witnesses the moment of acceptance. The human weighed this ('it wasn't really doing anything') and chose; this Decision records that the choice has a cost, and what it is. WHAT THIS DOES NOT CHANGE: forks still need the human; the write layer still refuses an AI judge; the substance rule still demands the quote.";
        :>> consequences = "No GitHub issue is raised for a Decision and no email follows one. Routine Decisions are accepted the moment they are recorded; the tree shows AUTO-ACCEPTED with the standing words. A project with no declared decider accumulates proposed Decisions until it declares one or accepts by quoted word. The engine ships two fewer workflows and one fewer process (31). Three tests hold the record-time arms (non-fork accepts; fork stays; no decider stays). The 82 acceptances the channel recorded stand as history with their issue URLs, which remain readable on GitHub. REMOVAL PATH (D0163): a Decision superseding this one and D0291's record-time arm removed; the channel unit would then be re-imported from the library, where it is still published.";
    }

    // acceptance event (D0121 review-queue sign-off; D0066/D0106 — human-judged, not fabricated)
    verification d0291Accept : Test { :>> id = "3f8e50d1-45ff-4074-a167-14a797a1d53e"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0291AcceptR1 : TestResult { :>> id = "aaa30bad-2a9f-421b-8007-19a98ea84864"; :>> outcome = VerdictKind::pass; :>> judgedAgainst = "10f2571"; :>> judgedAt = "2026-09-03"; :>> judgedBy = "wweatherholtz"; }

    // QUOTE RECEIPT (D0198 shape): the human's own instruction, which this Decision carries out.
    verification d0291AcceptAttest1 : Test { :>> id = "f816a827-b306-468a-bf69-6aaef67042ff"; :>> method = VerificationMethod::confirmation; :>> procedureText = "wweatherholtz, 2026-09-03, in chat, verbatim: 'i don't want github issue notifications. disconnect that pipeline.  it wasn't really doing anything anyway, no?' (st088). The acceptance above is standing consent applied at record time - the first one - and this receipt is their word on the same decision."; }
    part d0291AcceptAttest1R1 : TestResult { :>> id = "4fbb3660-bd2f-46e1-bd9a-907ae3dd8877"; :>> outcome = VerdictKind::pass; :>> judgedAgainst = "10f2571"; :>> judgedAt = "2026-09-03"; :>> judgedBy = "claudeOpus5"; }
    #SupersedeClause dependency from d0291 to d0205;
    #DerivedFrom dependency from d0291 to st088;
}
