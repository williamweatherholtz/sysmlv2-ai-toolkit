// D0155 — ACCEPTED (wweatherholtz, 2026-08-17): the 313 sittings unreviewed when this Decision landed
// are accepted as unreviewed; from here the sitting-review queue is live. Sign-off is d0155Accept below.
// #ProspectiveChange (D0070): forward-only by construction — the grandfather set is the sittings
// present at this Decision's own introduction commit, so no future sitting can fall into it.
package Decision0155 {
    private import EngineElement::*;
    private import EngineWork::*;
    private import EngineVerification::*;
    private import EngineRelationships::*;

    #ProspectiveChange part d0155 : Decision {
        :>> id = "b3f1c9a4-7e52-4d08-9c61-5a2e7f81d940";
        :>> title = "D0155: one grandfather line for sitting review — the historical 313 are accepted unreviewed, the queue is live from here";
        :>> createdAt = "2026-08-17";
        :>> createdBy = "claudeOpus5";
        :>> status = DecisionStatus::accepted;
        :>> context = "MEASURED, and the measurement is what forced a human decision: 317 sittings, 4 covered by a sitting review, 313 uncovered — per-sitting review (D0049's single human gate) has been performed twice in this repository's whole history. The obligation surface therefore reported 313 as due, which is TRUE and useless as a queue: N-C1 says the act surface shows what needs the human's judgment AND NOTHING ELSE, and three real obligations were lost beside 310 nobody will ever clear. issue135 recorded it rather than filtering it, because scoping silently to 'recent' would invent an actionable definition nobody agreed. I TESTED THE OBVIOUS NON-ARBITRARY BOUNDARY FIRST and it does not work: taking the convention to start at the earliest sprint any review actually attests (2026-06-24) still leaves 168 sittings on the live side, because the gap is not a dating artifact — the reviews genuinely did not happen. So no computation over the existing model can distinguish a sitting AWAITING judgment from one that will never receive it. Only the human can, because it is their own obligation being waived.";
        :>> decision = "ACCEPTED: one explicit grandfather line, drawn at this Decision's introduction commit. A sitting is DUE iff it is uncovered by a #Covers-linked review AND its Story did not exist when this Decision landed. Everything uncovered at that moment — 313 sittings — is GRANDFATHERED UNREVIEWED: accepted as never reviewed, reported as its own count in the same view, never deleted and never folded into the due figure. The queue starts at zero and grows by one for every sitting closed without a review, so it measures the human's live obligation and nothing else. The mechanism is the existing `govern::grandfathered_under` (the element set present at a Decision's introduction commit, D0068/D0081) — the same control D0079 and D0080 already use, so this adds a caller and not a mechanism.";
        :>> rationale = "WHY A ONE-TIME LINE AND NOT A ROLLING WINDOW, which was the tempting alternative: a recency window (due only while a sitting is fresh enough to judge) re-grandfathers CONTINUOUSLY. A growing review debt would sit permanently behind a small comfortable number, and the reader could not tell a genuinely reviewed history from an un-reviewed one that keeps aging out. That is precisely the failure N-C2 exists to prevent, and it would have converted a visible 313 into an invisible one. A single line is auditable: it is one attestation, at one commit, by one named human, and the debt it waives stays on screen. WHY THE LINE IS A COMMIT AND NOT A DATE: a date is a number I would have chosen; the introduction commit is derived from git and cannot be nudged, and it makes the grandfather set forward-only by construction rather than by discipline — no sitting created after this Decision can ever fall into it (issue068). WHY THE COUNT STAYS VISIBLE: the human waived REVIEW of that history, not knowledge of it. Deleting the figure would make the waiver unfalsifiable and would let a future reader conclude the history was reviewed. WHY UNRESOLVED-BOUNDARY FAILS OPEN, opposite to the gate stance: where a git failure makes a GATE grandfather everything (D0050, so it never spuriously blocks), an obligation surface that cannot resolve its boundary must report EVERY uncovered sitting as due with the reason stated. A gate failing open is cautious; an obligation surface failing quiet would tell the human nothing is owed when it does not know — the one thing N-C2 forbids.";
        :>> consequences = "The sitting-review obligation class becomes workable: due starts at 0 with 313 grandfathered, and the issue135 caveat on the obligation bar is removed because the number is now defensible. `sitting-coverage` gains `due`, `due_sprints`, `grandfathered_unreviewed` and `grandfatherBasis` while `uncovered` keeps its existing meaning — the total truth is still reported, so nothing that read the old field is silently redefined. THE COST IS REAL AND STATED: 313 sittings of this repository's history will never receive the per-sitting human review D0049 requires, and no later computation can recover it. Every sitting from 318 on is live, so an unreviewed sprint now shows up immediately as one owed item rather than vanishing into a crowd.";
    }

    #Resolves dependency from d0155 to issue135;

    // acceptance event (D0121 review-queue sign-off; D0066/D0106 — human-judged, not fabricated)
    verification d0155Accept : Test { :>> id = "8c40d7b2-1f65-4e39-a2d7-63b90f18ac54"; :>> method = VerificationMethod::confirmation; :>> procedureText = "wweatherholtz, 2026-08-17, chose the option titled 'One-time grandfather line' from three presented, whose text they were shown verbatim: 'You attest once that the 313 historical sittings are accepted as unreviewed. From the accepting commit forward the queue is live and starts at 0... The grandfathered count stays visible in the view as grandfatheredUnreviewed: 313 — recorded, never deleted.' The choice was made on the measurement given in the same message (317 sprints, 4 covered, 313 uncovered, 145 pre-convention / 168 post) together with the explicit finding that the grandfathering approach named in the resolving item's own DoD does not work, since 168 sittings remain live under it. The two rejected options were a rolling recency window and keeping the caveat unchanged. This attests the WAIVER — that the human accepts those sittings as never reviewed — and nothing about the quality of the work in them."; }
    part d0155AcceptR1 : TestResult { :>> id = "4e71a9f3-8d20-4c17-b5e6-91af2d740c68"; :>> outcome = VerdictKind::pass; :>> judgedAgainst = "PENDING"; :>> judgedAt = "2026-08-17"; :>> judgedBy = "wweatherholtz"; }
}
