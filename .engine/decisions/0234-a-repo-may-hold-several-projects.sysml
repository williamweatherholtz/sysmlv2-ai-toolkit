// D0234 (status: the `status` field below is the truth) — workspace: one git repository may hold several keel projects, and the four things that are repo-scoped now know it
// Recorded via `keel record decision` (D0105 RMWX axis; issue054). Acceptance is a separate explicit
// human gate (method=confirmation, D0106): flip status + add the d0234Accept event on sign-off.
package Decision0234 {
    private import EngineElement::*;
    private import EngineWork::*;
    private import EngineVerification::*;
    private import EngineRelationships::*;

    // #SafetyChange (D0070) - this Decision governs a process/schema change; the co-committed
    // change rides the process-change guard's hard lock.
    #SafetyChange part d0234 : Decision {
        :>> id = "1faf33bf-c09f-45ea-b69d-9f0f642957a7";
        :>> title = "workspace: one git repository may hold several keel projects, and the four things that are repo-scoped now know it";
        :>> createdAt = "2026-08-26";
        :>> createdBy = "claudeFable5";
        :>> status = DecisionStatus::accepted;
        :>> context = "The author wants one repo for a handful of small short-term projects that do not each deserve their own, and expects the arrangement to recur. Rather than reason about it I built it and ran it. THREE THINGS ALREADY WORKED: root resolution walks up to .engine, drift is file-scoped through each project's own deliverable-manifest, and the write lock sits beside each model root. FOUR BROKE, and they are exactly the ones a supervisor cares about. Decision numbering collides - two fresh projects both get d0001. The channel cannot tell them apart, because its marker is keel-decision d0001 and its GitHub lookup is repo-scoped, so the second project's issue never opens and a reject is ambiguous. The gate cannot cover them, because git allows ONE core.hooksPath per repository and validate at the parent printed 0 files validated clean and exited 0 - a hook there would gate nothing while reporting success. And land gates one root while pushing the whole repo, so the other projects ride out ungated.";
        :>> decision = "A WORKSPACE is one git repository holding one or more keel projects, DISCOVERED rather than declared: a project is a directory holding both .engine and .tracking, found by a depth-bounded walk from the git root. `keel projects` reports them. Four changes, each confined to the multi-project case so a single-project repo behaves exactly as before: `keel gate --workspace` gates every project a commit touches and NAMES the ones it skipped, and the scaffolded pre-commit calls it when its own directory is not itself a project; `sync`/`land` gate EVERY project in the workspace before anything is pushed; `validate` REFUSES a non-project instead of reporting a clean tree over nothing; and the channel QUALIFIES a decision id as `alpha/d0001` when the repo holds several projects, with the split performed in the binary so the recorder writes a human's acceptance into the right tree.";
        :>> rationale = "Discovery rather than a manifest because a manifest is a second place to keep the list true and the filesystem already knows - the same reasoning the console's project list records - and because it was verified against both real repositories here, finding exactly one project each with no nested false positives. Every change is gated on `is_multi()` for one reason: a feature that alters how existing repos behave is a migration, not an addition, and the channel's id format is the sharpest case - changing it for a single-project repo would make every existing issue unfindable, so the opener would re-open one for every past decision. Backward compatibility there IS the correctness requirement rather than a courtesy. The gate had to be workspace-scoped rather than per-project because git gives one hooksPath and a push carries the whole repo: those are properties of git, not choices, so the gate has to match them.";
        :>> consequences = "TWO PRE-EXISTING DEFECTS surfaced while testing, both worse than the feature. First: every project's guards saw every OTHER project's staged files, because git diff --cached answers for the whole repository regardless of which subdirectory asks - a two-project workspace failed BOTH projects over a file belonging to neither. Staged paths are now scoped and re-based per project (issue271). Second, and it had nothing to do with workspaces: a freshly scaffolded project COULD NOT MAKE ITS FIRST COMMIT, because init stages every .engine/processes file and the keystone lock read that as a control being weakened, so the first thing a new user does failed and told them to record a Decision for a scaffold they did not write. The lock now applies to MODIFIED and DELETED locked files, never merely ADDED (issue272), with the residual stated: an added process can weaken by claiming a core guard, and audit-adherence's guard-state monotonicity is what catches that. STATED LIMITS: a staged file belonging to no project is reported but covered by no project's gate; decision NUMBERS still collide in the model even though the channel ids no longer do, so two projects' d0001 are distinct only at the channel; and the qualified form is untested against live GitHub, verified only against the qualification rule and a stub. Verified live: two projects in one repo, one repo-root hook, a commit gated across both, a broken project BLOCKING it while naming the project it skipped, and a fresh single-project first commit now landing. Resolves issue270.";
    }

    // acceptance event (D0121 review-queue sign-off; D0066/D0106 — human-judged, not fabricated)
    verification d0234Accept : Test { :>> id = "2864277c-f30c-49ac-9a8e-ccd69573a2d6"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0234AcceptR1 : TestResult { :>> id = "9ab66dae-682f-4fc1-9553-93469555f1fb"; :>> outcome = VerdictKind::pass; :>> judgedAgainst = "f356770"; :>> judgedAt = "2026-08-26"; :>> judgedBy = "wweatherholtz"; }
}
