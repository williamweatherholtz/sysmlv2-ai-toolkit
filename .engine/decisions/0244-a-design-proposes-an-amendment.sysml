// D0244 (status: the `status` field below is the truth) — a design may propose an amendment to a process; it may not quietly disagree with one
// Recorded via `keel record decision` (D0105 RMWX axis; issue054). Acceptance is a separate explicit
// human gate (method=confirmation, D0106): flip status + add the d0244Accept event on sign-off.
package Decision0244 {
    private import EngineElement::*;
    private import EngineWork::*;
    private import EngineVerification::*;
    private import EngineRelationships::*;

    // #ProspectiveChange (D0070) - this Decision governs a process/schema change; the co-committed
    // change rides the process-change guard's hard lock.
    #ProspectiveChange part d0244 : Decision {
        :>> id = "1c6faedb-8637-48cd-a734-9756cb5be4cf";
        :>> title = "a design may propose an amendment to a process; it may not quietly disagree with one";
        :>> createdAt = "2026-08-28";
        :>> createdBy = "claudeOpus5";
        :>> status = DecisionStatus::accepted;
        :>> context = "An adversarial panel of five lenses reviewed a proposed redesign of the knowledge-store recall path and found, among much else, a governance defect in my own work: D0243 changed what two accepted steps of `knowledge-graph-memory` MEAN, carries no `#ProspectiveChange`/`#SafetyChange` marker where its sibling D0242 carries two, and never edited `.engine/processes/knowledge-graph-memory.sysml` - which to this day mentions neither D0242 nor D0243. The keystone lock did not fire because the guarded artifact was never touched: the amendment was made AROUND the control rather than through it. D0161 had already written the rule this breaks, and the human sharpened its wording on being shown it: D0161 says 'A design may amend a process; it may not quietly disagree with one.' Their correction is 'a design may PROPOSE AN AMENDMENT to a process' - which is the accurate form, because a design cannot amend an accepted process at all. Amendment happens through the Change Request route with human sign-off (CLAUDE.md section 3a); a design proposes and the CR disposes. The original wording implied an authority a design does not have, and that implication is exactly the licence under which D0243 proceeded. What D0243 actually decided is sound and measured: seeding is corpus-derived rather than dependent on an authored vocabulary, and `.knowledge/` is an optional refinement. The panel did not dispute the substance. It disputed that the substance never reached the file the process is read from.";
        :>> decision = "1. THE RULE, restated in its accurate form and made canonical: **a design may PROPOSE AN AMENDMENT to a process; it may not quietly disagree with one.** D0161's wording stands as recorded history and is not edited; this is the form that governs from here, and it is stated in the process definition itself rather than only in a Decision's rationale, so it is read where the process is read. 2. D0243'S AMENDMENT IS RECORDED WHERE THE PROCESS IS READ. `knowledge-graph-memory.sysml` gains a v3 clause stating what D0243 decided: for an ALREADY-TYPED corpus, steps 1 (`kgQuestions`) and 2 (`kgVocabulary`) are OPTIONAL rather than prerequisite - a project may declare Questions to get `question-coverage` measured and Aliases to map words its corpus does not use, and recall works with neither. This Decision carries the `#ProspectiveChange` marker the amendment always needed. 3. WHAT IS NOT AMENDED HERE, deliberately. `kgTraversal`'s SEEDING job still reads 'match the question's words'. The proposed work-context seeding would change that, and it is NOT decided by this Decision: it changes an AI-owned step, it makes step 7's honest-negative obligation ('a question outside the vocabulary must return no memory matches rather than a guess') unstateable, and the panel showed it buys no latency because 83% of the cost is parse. It needs its own CR, its own measure, and its own sign-off, and pre-amending the definition for a design that has not been accepted would repeat the defect this Decision exists to correct.";
        :>> rationale = "ALTERNATIVES for clause 1: (A) edit D0161's text to the sharper wording - REJECTED, and the reason is the whole point of this Decision. D0161 is accepted. Editing an accepted record so it reads as though it always said the better thing is precisely the quiet disagreement the rule forbids, committed against the rule itself. (B) leave the wording alone and rely on the reader - rejected: the loose wording is what licensed the defect, and a rule that implies an authority a design does not have will license it again. (C) restate it in the new record and put it where the process is read - CHOSEN. CRITERIA: does the correction preserve what was actually decided and when; does it sit where the person about to break it will see it; and does it change what a design is permitted to do without sign-off. Clause 2's placement matters more than its content. The keystone lock detects EDITS to guarded files, so an amendment expressed only in a Decision is invisible to it by construction - the guard cannot notice a disagreement, only a change. That is a real limit of the control, not a bypass I found: the fix is that the amendment must land in the guarded file, where the lock then covers it. Recording the amendment is therefore not bookkeeping; it is what puts the change back inside the control's reach.";
        :>> consequences = "The process definition now states what it actually requires, so a downstream project reading `knowledge-graph-memory.sysml` no longer sees two prerequisite steps that this engine treats as optional. `keel why` and `keel recall` are unchanged in behaviour by this Decision - nothing in it touches code. The panel's remaining findings are tracked separately and are ordinary defect work, not process changes: issue295 (recall never indexes body text, and its ranker is alphabetical in 43 of 50 cases; BM25 on the same fields measures 74% against the shipped 48%), issue296 (the benchmark's control was denied the body field its queries came from, so 48%-vs-34% carries no information; precision was never measured and samples near 9%; McNemar exact p = 0.119), issue297 (three surfaces assert a confidence gate removed two commits ago, including a PASSING DoD), issue299 (identifier seeding fails on three of six natural spellings). STATED PLAINLY because the panel had to find it rather than being told: the 48%-vs-34% result that D0242 part 4's honest-outcome clause was satisfied against does not survive scrutiny. The clause was honoured in form - a control was pre-registered and a threshold pre-committed - and defeated in substance, because the control was specified so it could not win. The injection tier stays live while issue295 and issue296 are worked, because turning it off is one command the human already holds (`keel deactivate knowledge-graph-memory`), but no claim of measured benefit stands until the harness can discriminate. A limit of the keystone lock is now on the record: it fires on edits to guarded files and cannot see a Decision that contradicts a guarded file it never touches. The forward control for that class is tracked as `processAmendmentsReachTheDefinition` and is not built by this Decision.";
    }

    // acceptance event (D0121 review-queue sign-off; D0066/D0106 — human-judged, not fabricated)
    verification d0244Accept : Test { :>> id = "c6fc56cb-f57c-43ee-9a21-8f3011801c96"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0244AcceptR1 : TestResult { :>> id = "8fcc664c-7407-44c6-abd9-6a33fc4f1251"; :>> outcome = VerdictKind::pass; :>> judgedAgainst = "71b789b"; :>> judgedAt = "2026-08-28"; :>> judgedBy = "wweatherholtz"; }
}
